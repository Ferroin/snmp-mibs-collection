JUNIPER-JS-UTM-AV-MIB DEFINITIONS ::= BEGIN

    IMPORTS
        Integer32, 
        NOTIFICATION-TYPE,                 
        MODULE-IDENTITY, OBJECT-TYPE   FROM SNMPv2-SMI
        DisplayString                  FROM SNMPv2-TC
        jnxJsUTMRoot                   FROM JUNIPER-JS-SMI;

    jnxJsAntiVirus MODULE-IDENTITY
        LAST-UPDATED  "200811241622Z" -- Nov 24, 2008
        ORGANIZATION  "Juniper Networks, Inc."    
        CONTACT-INFO
            "Juniper Technical Assistance Center
             Juniper Networks, Inc.
             1194 N. Mathilda Avenue     
             Sunnyvale, CA 94089      

             E-mail: support@juniper.net
             HTTP://www.juniper.net"           
        DESCRIPTION            
            "This module defines the MIB for Juniper Enterprise specific
             antivirus functionality. Juniper documentation is recommended
             as the reference."

        REVISION      "200811241622Z" 
        DESCRIPTION   "Creation Date"
        ::= { jnxJsUTMRoot 1 }                 

    jnxJsAntiVirusObjects     OBJECT IDENTIFIER ::= { jnxJsAntiVirus 1 }
    jnxJsAntiVirusTraps       OBJECT IDENTIFIER ::= { jnxJsAntiVirus 2 }
    jnxJsAntiVirusTrapsPrefix OBJECT IDENTIFIER ::= { jnxJsAntiVirus 0 }
    jnxJsAntiVirusTrapVars    OBJECT IDENTIFIER ::= { jnxJsAntiVirus 3 }

    -- ***************************************************************
    --  anti-virus objects
    -- ***************************************************************

    -- ***************************************************************
    --  scan engine objects
    -- ***************************************************************

    jnxJsAntiVirusEngine OBJECT IDENTIFIER ::= { jnxJsAntiVirusObjects 1 }

    jnxJsAVEngineType OBJECT-TYPE
        SYNTAX INTEGER {
            unknown-engine         (1),
            kaspersky-lab-engine   (2),
            juniper-express-engine (3)
        }
        MAX-ACCESS    read-only
        STATUS        current
        DESCRIPTION
            "The scan engine type in use. User can use CLI to set the
             engine type to either full AV (kaspersky-lab-engine) or
             express AV (juniper-express-engine). If AV is not configured
             then engine type is not known."
        ::= { jnxJsAntiVirusEngine 1 }

    jnxJsAVCurrentPatternVersionString       OBJECT-TYPE
        SYNTAX        DisplayString (SIZE(1..255))
        MAX-ACCESS    read-only
        STATUS        current
        DESCRIPTION
            "Anti-Virus pattern database version currently in use."
        ::= { jnxJsAntiVirusEngine 2 }

    jnxJsAVDatabaseType OBJECT-TYPE
        SYNTAX INTEGER {
            full            (1),
            express         (2),
            unknown         (3)
        }
        MAX-ACCESS    read-only
        STATUS        current
        DESCRIPTION
            "The Database type in use. User can use CLI to set the
             engine type to full AV or express AV. Corresponding 
             database types are Full for KL Engine and Express for
             Juniper Express Engine."
        ::= { jnxJsAntiVirusEngine 3 }

    -- ***************************************************************
    --  scan statistics objects
    -- ***************************************************************

    jnxJsAntiVirusStats OBJECT IDENTIFIER ::= { jnxJsAntiVirusObjects 2 }

    jnxJsAVScanCodeClean           OBJECT-TYPE
        SYNTAX        Integer32
        MAX-ACCESS    read-only
        STATUS        current
        DESCRIPTION
            "Number of requests passed Anti-Virus scan."
        ::= { jnxJsAntiVirusStats 1 }

    jnxJsAVScanCodeInfected        OBJECT-TYPE
        SYNTAX        Integer32
        MAX-ACCESS    read-only
        STATUS        current
        DESCRIPTION
            "Number of requests found infected by Anti-Virus scan engine."
        ::= { jnxJsAntiVirusStats 2 }

    jnxJsAVScanCodeProtected       OBJECT-TYPE
        SYNTAX        Integer32
        MAX-ACCESS    read-only
        STATUS        current
        DESCRIPTION
            "Number of requests cannot be scanned due to protected by password."
        ::= { jnxJsAntiVirusStats 3 }

    jnxJsAVScanCodeDecompress      OBJECT-TYPE
        SYNTAX        Integer32
        MAX-ACCESS    read-only
        STATUS        current
        DESCRIPTION
            "Number of requests cannot be scanned due to exceeding max 
            decmopress layer."
        ::= { jnxJsAntiVirusStats 4 }

    jnxJsAVScanCodeCorrupted       OBJECT-TYPE
        SYNTAX        Integer32
        MAX-ACCESS    read-only
        STATUS        current
        DESCRIPTION
            "Number of requests cannot be scanned due to file corrupted."
        ::= { jnxJsAntiVirusStats 5 }

    jnxJsAVScanCodeNoResource      OBJECT-TYPE
        SYNTAX        Integer32
        MAX-ACCESS    read-only
        STATUS        current
        DESCRIPTION
            "Number of requests cannot be scanned due to out-of-resource."
        ::= { jnxJsAntiVirusStats 6 }

    jnxJsAVScanCodeInternalError   OBJECT-TYPE
        SYNTAX        Integer32
        MAX-ACCESS    read-only
        STATUS        current
        DESCRIPTION
            "Number of requests cannot be scanned due to internal error."
        ::= { jnxJsAntiVirusStats 7 }

    jnxJsAVScanCodeMaxContentSize  OBJECT-TYPE
        SYNTAX        Integer32
        MAX-ACCESS    read-only
        STATUS        current
        DESCRIPTION
            "Number of requests cannot be scanned due to exceeding max content
             size limit."
        ::= { jnxJsAntiVirusStats 8 }

    jnxJsAVScanCodeTooManyReq      OBJECT-TYPE
        SYNTAX        Integer32
        MAX-ACCESS    read-only
        STATUS        current
        DESCRIPTION
            "Number of requests cannot be scanned due to exceeding maximum 
             requests limit."
        ::= { jnxJsAntiVirusStats 9 }

    jnxJsAVScanCodeTimeout         OBJECT-TYPE
        SYNTAX        Integer32
        MAX-ACCESS    read-only
        STATUS        current
        DESCRIPTION
            "Number of requests cannot be scanned due to scan timeout."
        ::= { jnxJsAntiVirusStats 10 }

    jnxJsAVScanCodeEngineNotReady  OBJECT-TYPE
        SYNTAX        Integer32
        MAX-ACCESS    read-only
        STATUS        current
        DESCRIPTION
            "Number of requests cannot be scanned due to scan engine not ready."
        ::= { jnxJsAntiVirusStats 11 }

    -- ***************************************************************
    --  antivirus traps
    -- ***************************************************************

    --
    -- When new pattern is updated, a trap is generated.
    --

    jnxJsAvPatternUpdateTrap NOTIFICATION-TYPE
        OBJECTS       { jnxAVPatternVersionString,
                        jnxAVPatternTimestamp
                      }
        STATUS        current
        DESCRIPTION
            "This traps is raised when the Anti-Virus pattern database is 
             updated successfully."
        ::= { jnxJsAntiVirusTrapsPrefix 1 }

    --
    -- Trap variables
    --

    jnxAVPatternVersionString       OBJECT-TYPE
        SYNTAX        DisplayString (SIZE(1..255))
        MAX-ACCESS    accessible-for-notify
        STATUS        current
        DESCRIPTION
            "Anti-Virus last successfully updated pattern database version."
        ::= { jnxJsAntiVirusTrapVars 1 }

    jnxAVPatternTimestamp           OBJECT-TYPE
        SYNTAX        DisplayString (SIZE(1..255))
        MAX-ACCESS    accessible-for-notify
        STATUS        current
        DESCRIPTION
            "Anti-Virus last successfully updated pattern database timestamp."
        ::= { jnxJsAntiVirusTrapVars 2 }

--
-- End of File
--

END
