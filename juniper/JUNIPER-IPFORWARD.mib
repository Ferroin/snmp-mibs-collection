JUNIPER-IPFORWARD-MIB DEFINITIONS ::= BEGIN

IMPORTS
    MODULE-IDENTITY, OBJECT-TYPE
        FROM SNMPv2-SMI              -- RFC2578
    SnmpAdminString
	FROM SNMP-FRAMEWORK-MIB      -- RFC2571 
    ipCidrRouteEntry
	FROM IP-FORWARD-MIB          -- RFC2096
    jnxMibs
        FROM JUNIPER-SMI;

jnxIpForwardMIB MODULE-IDENTITY
    LAST-UPDATED "200608210000Z" -- Aug 21 00:00:00 2006 UTC
    ORGANIZATION "Juniper Networks, Inc."
    CONTACT-INFO
            "        Juniper Technical Assistance Center
		     Juniper Networks, Inc.
		     1194 N. Mathilda Avenue
		     Sunnyvale, CA 94089
		     E-mail: support@juniper.net"
    DESCRIPTION
            "This is Juniper Networks' implementation of enterprise specific
             portions of ipForward MIB.  Any data stored in this MIB 
	     has directly related entries in mib-2,  ipForward MIB."

    -- revision history
    REVISION "200505010000Z" -- May 1 00:00:00 2005 UTC
    DESCRIPTION
            "Initial implementation."
    ::= { jnxMibs 38 }

--
-- Ping Results Table extensions
--

jnxIpCidrRouteTable OBJECT-TYPE
    SYNTAX      SEQUENCE OF JnxIpCidrRouteEntry
    MAX-ACCESS  not-accessible
    STATUS      current
    DESCRIPTION
        "Augments the ipCidrRouteTable with additional data."
   ::= { jnxIpForwardMIB 1 }

jnxIpCidrRouteEntry OBJECT-TYPE
    SYNTAX      JnxIpCidrRouteEntry
    MAX-ACCESS  not-accessible
    STATUS      current
    DESCRIPTION
        "Each entry provides additional CIDR forwarding information."
    AUGMENTS { ipCidrRouteEntry }
    ::= { jnxIpCidrRouteTable 1 }

JnxIpCidrRouteEntry ::=
    SEQUENCE {
        jnxIpCidrRouteTunnelName        SnmpAdminString
     }

jnxIpCidrRouteTunnelName OBJECT-TYPE
     SYNTAX        SnmpAdminString
     -- MAX-ACCESS    read-create
     MAX-ACCESS    read-only
     STATUS        current
     DESCRIPTION
           "The canonical name assigned to the tunnel. The router
	    will forward traffic bound for the destination defined
	    by the INDEX through this tunnel." 
      DEFVAL {""}
      ::= { jnxIpCidrRouteEntry 1 }

END
