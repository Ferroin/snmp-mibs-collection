CISCO-FTP-CLIENT-CAPABILITY DEFINITIONS ::= BEGIN

IMPORTS
        MODULE-IDENTITY
                FROM SNMPv2-SMI
        AGENT-CAPABILITIES
                FROM SNMPv2-CONF
        ciscoAgentCapability
                FROM CISCO-SMI;

cftpclientCapability MODULE-IDENTITY
        LAST-UPDATED    "200601020000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com
                        cs-snmp@cisco.com"
        DESCRIPTION
                "The capabilities description of
                 CISCO-FTP-CLIENT-MIB."

        REVISION        "200601020000Z"
        DESCRIPTION
                "Initial version of this MIB module."
        ::= { ciscoAgentCapability 483 }

cftpclientCapabilityIOSXRV2R0CRS1 AGENT-CAPABILITIES
    PRODUCT-RELEASE     "Cisco IOS XR 2.0 for CRS-1"
    STATUS              current
    DESCRIPTION         "CISCO-FTP-CLIENT-MIB capabilities for
                        IOS XR release 2.0"

    SUPPORTS            CISCO-FTP-CLIENT-MIB
        INCLUDES        { ciscoFtpClientRequestGroup }
    ::= { cftpclientCapability 1 }

END
