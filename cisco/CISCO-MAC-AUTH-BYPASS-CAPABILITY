CISCO-MAC-AUTH-BYPASS-CAPABILITY DEFINITIONS ::= BEGIN

IMPORTS
    MODULE-IDENTITY
        FROM SNMPv2-SMI
    AGENT-CAPABILITIES
        FROM SNMPv2-CONF
    ciscoAgentCapability
        FROM CISCO-SMI;

ciscoMacAuthBypassCapability MODULE-IDENTITY
    LAST-UPDATED    "201003090000Z"
    ORGANIZATION    "Cisco Systems, Inc."
    CONTACT-INFO
            "Cisco Systems
            Customer Service

            Postal: 170 W Tasman Drive
            San Jose, CA  95134
            USA

            Tel: +1 800 553-NETS

                E-mail: cs-ibns@cisco.com,
                        cs-lan-switch-snmp@cisco.com"
    DESCRIPTION
        "The capabilities description of CISCO-MAC-AUTH-BYPASS-MIB."
    REVISION        "201003090000Z"
    DESCRIPTION
        "Added capability statement ciscoMabCapV12R0252SGPCat4K.

        Added more VARIATION for ciscoMabCapV12R0233SXIPCat6K."
    REVISION        "200810300000Z"
    DESCRIPTION
        "Initial version of this MIB module."
    ::= { ciscoAgentCapability 574 }

ciscoMabCapV12R0233SXIPCat6K AGENT-CAPABILITIES
    PRODUCT-RELEASE "Cisco IOS 12.2(33)SXI on Catalyst 6000/6500
                     series devices."
    STATUS          current
    DESCRIPTION
        "CISCO-MAC-AUTH-BYPASS-MIB capabilities."

    SUPPORTS        CISCO-MAC-AUTH-BYPASS-MIB
    INCLUDES        {
                        cmabIfConfigGroup,
                        cmabClientInfoGroup
                    }
    VARIATION       cmabIfAuthMethod
    DESCRIPTION
        "Value 'eap' can only be set if the corresponding instance
        value of cmabIfAuthEnabled is 'true'."

    VARIATION       cmabIfConfigEntry
    DESCRIPTION
        "Write access is not supported on read-write objects of
        the entry if TrustSec dot1x mode is enabled on the port."
    ::= { ciscoMacAuthBypassCapability 1 }

ciscoMabCapV12R0252SGPCat4K AGENT-CAPABILITIES
    PRODUCT-RELEASE "Cisco IOS 12.2(52)SG on Cat4K family switches."
    STATUS          current
    DESCRIPTION
        "CISCO-MAC-AUTH-BYPASS-MIB capabilities."

    SUPPORTS        CISCO-MAC-AUTH-BYPASS-MIB
    INCLUDES        {
                        cmabIfConfigGroup,
                        cmabClientInfoGroup
                    }
    VARIATION       cmabIfAuthMethod
    DESCRIPTION
        "Value 'eap' can only be set if the corresponding instance
        value of cmabIfAuthEnabled is 'true'."
    ::= { ciscoMacAuthBypassCapability 2 }

END
