ADMIN-AUTH-STATS-MIB DEFINITIONS ::= BEGIN

   IMPORTS
      MODULE-IDENTITY, OBJECT-TYPE, Integer32, Gauge32, IpAddress, Counter32, TimeTicks
        FROM SNMPv2-SMI
      OBJECT-GROUP, MODULE-COMPLIANCE
        FROM SNMPv2-CONF
      alAdminAuthStats, alAdminAuthGroup
        FROM ALTIGA-MIB
      alAdminAuthMibModule
        FROM ALTIGA-GLOBAL-REG;

   altigaAdminAuthStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"
      DESCRIPTION
         "The Altiga Administrator Authentication Statistics MIB models counters and objects that are
          of management interest for administration authentication.

          Acronyms
          The following acronyms are used in this document:

            IP:         Internet Protocol

            MIB:        Management Information Base

            TACACS:     Terminal Access Controller Access Control System

            UDP:        User Datagram Protocol
         "

        REVISION "200209051300Z"
        DESCRIPTION
                "Added module compliance."

        REVISION "200207100000Z"
        DESCRIPTION
                "Updated with new header"
      ::= { alAdminAuthMibModule 2 }

-- +++++++++++++++++++++++++++++++++++++++++++++++++++++++
-- MIB Objects
-- +++++++++++++++++++++++++++++++++++++++++++++++++++++++

alAminAuthStatsGlobal	OBJECT IDENTIFIER ::= { alAdminAuthStats 1 }

alAdminAuthServStatsTable OBJECT-TYPE
   SYNTAX     SEQUENCE OF AlAdminAuthServStatsEntry
   MAX-ACCESS not-accessible
   STATUS     current
   DESCRIPTION
      "The (conceptual) table listing the TACACS authentication
       servers with which the client shares a secret."
   ::= { alAdminAuthStats 2 }

alAdminAuthServStatsEntry       OBJECT-TYPE
   SYNTAX     AlAdminAuthServStatsEntry
   MAX-ACCESS not-accessible
   STATUS     current
   DESCRIPTION
      "An entry (conceptual row) representing a TACACS
       authentication server with which the client shares a secret."
   INDEX      { alAdminAuthServIndex }
   ::= { alAdminAuthServStatsTable 1 }

AlAdminAuthServStatsEntry  ::= SEQUENCE {
   alAdminAuthServIndex                             Integer32,
   alAdminAuthServAddress                           IpAddress,
   alAdminAuthClientServerPortNumber                Integer32,
   alAdminAuthClientRoundTripTime                   TimeTicks,
   alAdminAuthClientAccessRequests                  Counter32,
   alAdminAuthClientAccessRetransmissions           Counter32,
   alAdminAuthClientAccessAccepts                   Counter32,
   alAdminAuthClientAccessRejects                   Counter32,
   alAdminAuthClientAccessChallenges                Counter32,
   alAdminAuthClientMalformedAccessResponses        Counter32,
   alAdminAuthClientBadAuthenticators               Counter32,
   alAdminAuthClientPendingRequests                   Gauge32,
   alAdminAuthClientTimeouts                        Counter32,
   alAdminAuthClientUnknownType                     Counter32,
   alAdminAuthServerGroupIdentification               Gauge32
}

alAdminAuthServIndex OBJECT-TYPE
   SYNTAX     Integer32 (0..MAX)
   MAX-ACCESS not-accessible
   STATUS     current
   DESCRIPTION
      "A number uniquely identifying each ADMIN
       Authentication server with which this client
       communicates."
   ::= { alAdminAuthServStatsEntry 1 }

alAdminAuthServAddress OBJECT-TYPE
   SYNTAX     IpAddress
   MAX-ACCESS read-only
   STATUS     current
   DESCRIPTION
      "The IP address of the ADMIN authentication server
       referred to in this table entry."
   ::= { alAdminAuthServStatsEntry 2 }

alAdminAuthClientServerPortNumber  OBJECT-TYPE
   SYNTAX     Integer32
   MAX-ACCESS read-only
   STATUS     current
   DESCRIPTION
      "The UDP port the client is using to send requests to
       this server."
   ::= { alAdminAuthServStatsEntry 3 }

alAdminAuthClientRoundTripTime  OBJECT-TYPE
   SYNTAX     TimeTicks
   MAX-ACCESS read-only
   STATUS     current
   DESCRIPTION
      "The time interval between the most recent
       Access-Reply/Access-Challenge and the Access-Request that
       matched it from this ADMIN authentication server."
   ::= { alAdminAuthServStatsEntry 4 }

-- Request/Response statistics
-- Ignoring Unknown Types, then
-- AccessRequests + AccesssRetransmissions = AccessAccepts +
-- AccessRejects + AccessChallenges + PendingRequests + Timeouts

alAdminAuthClientAccessRequests OBJECT-TYPE
   SYNTAX     Counter32
   MAX-ACCESS read-only
   STATUS     current
   DESCRIPTION
      "The total number of ADMIN Access-Request packets sent
       to this server since client start-up. This does not
       include retransmissions."
   ::= { alAdminAuthServStatsEntry 5 }

alAdminAuthClientAccessRetransmissions OBJECT-TYPE
   SYNTAX     Counter32
   MAX-ACCESS read-only
   STATUS     current
   DESCRIPTION
      "The total number of ADMIN Access-Request packets
       retransmitted to this ADMIN authentication server
       since client start-up."
   ::= { alAdminAuthServStatsEntry 6 }

alAdminAuthClientAccessAccepts OBJECT-TYPE
   SYNTAX     Counter32
   MAX-ACCESS read-only
   STATUS     current
   DESCRIPTION
      "The total number of ADMIN Access-Accept packets
       received from this server since client start-up."
   ::= { alAdminAuthServStatsEntry 7 }

alAdminAuthClientAccessRejects OBJECT-TYPE
   SYNTAX     Counter32
   MAX-ACCESS read-only
   STATUS     current
   DESCRIPTION
      "The total number of ADMIN Access-Reject packets
       received from this server since client start-up."
   ::= { alAdminAuthServStatsEntry  8 }

alAdminAuthClientAccessChallenges OBJECT-TYPE
   SYNTAX     Counter32
   MAX-ACCESS read-only
   STATUS     current
   DESCRIPTION
      "The total number of ADMIN Access-Challenge packets
       received from this server since client start-up."
   ::= { alAdminAuthServStatsEntry 9 }

-- "Access-Response" includes an Access-Accept, Access-Challenge
-- or Access-Reject

alAdminAuthClientMalformedAccessResponses OBJECT-TYPE
   SYNTAX     Counter32
   MAX-ACCESS read-only
   STATUS     current
   DESCRIPTION
      "The total number of malformed ADMIN Access-Response
       packets received from this server since client
       start-up. Malformed packets include packets with
       an invalid length. Bad authenticators or
       Signature attributes are not
       included as malformed access responses."
   ::= { alAdminAuthServStatsEntry 10 }

alAdminAuthClientBadAuthenticators OBJECT-TYPE
   SYNTAX     Counter32
   MAX-ACCESS read-only
   STATUS     current
   DESCRIPTION
      "The total number of ADMIN Access-Response packets
       containing invalid authenticators or Signature
       attributes received from this server since client
       start-up."
   ::= { alAdminAuthServStatsEntry 11 }

alAdminAuthClientPendingRequests OBJECT-TYPE
   SYNTAX     Gauge32
   MAX-ACCESS read-only
   STATUS     current
   DESCRIPTION
      "The total number of ADMIN Access-Request packets
       destined for this server that have not yet timed out
       or received a response. This variable is incremented
       when an Access-Request is sent and decremented due to
       receipt of an Access-Reply or Access-Challenge,
       a timeout or retransmission."
   ::= { alAdminAuthServStatsEntry 12 }

alAdminAuthClientTimeouts OBJECT-TYPE
   SYNTAX     Counter32
   MAX-ACCESS read-only
   STATUS     current
   DESCRIPTION
      "The total number of authentication timeouts to this server
       since client startup. After a timeout the client may
       retry to the same server, send to a different server, or
       give up. A retry to the same server is counted as a
       retransmit as well as a timeout. A send to a different
       server is counted as a Request as well as a timeout."
   ::= { alAdminAuthServStatsEntry  13 }

alAdminAuthClientUnknownType OBJECT-TYPE
   SYNTAX     Counter32
   MAX-ACCESS read-only
   STATUS     current
   DESCRIPTION
      "The total number of ADMIN packets of unknown type which
       were received from this server on the authentication port
       since client start-up."
   ::= { alAdminAuthServStatsEntry  14 }

alAdminAuthServerGroupIdentification OBJECT-TYPE
   SYNTAX     Gauge32
   MAX-ACCESS read-only
   STATUS     current
   DESCRIPTION
      "Id of group accociated with this server."
   ::= { alAdminAuthServStatsEntry  15 }

altigaAdminAuthStatsMibConformance OBJECT IDENTIFIER ::= { altigaAdminAuthStatsMibModule 1 }
altigaAdminAuthStatsMibCompliances OBJECT IDENTIFIER ::= { altigaAdminAuthStatsMibConformance 1 }

altigaAdminAuthStatsMibCompliance MODULE-COMPLIANCE
   STATUS     current
   DESCRIPTION
      "The compliance statement for agents which 
       implement the Altiga Administrator Authentication Statistics MIB."
   MODULE
   MANDATORY-GROUPS { 
      alAdminAuthClientMIBGroup
   }
   ::= { altigaAdminAuthStatsMibCompliances 1 }

alAdminAuthClientMIBGroup OBJECT-GROUP
   OBJECTS {
      alAdminAuthServAddress,
      alAdminAuthClientServerPortNumber,
      alAdminAuthClientRoundTripTime,
      alAdminAuthClientAccessRequests,
      alAdminAuthClientAccessRetransmissions,
      alAdminAuthClientAccessAccepts,
      alAdminAuthClientAccessRejects,
      alAdminAuthClientAccessChallenges,
      alAdminAuthClientMalformedAccessResponses,
      alAdminAuthClientBadAuthenticators,
      alAdminAuthClientPendingRequests,
      alAdminAuthClientTimeouts,
      alAdminAuthClientUnknownType,
      alAdminAuthServerGroupIdentification
   }
   STATUS     current
   DESCRIPTION
      "The basic collection of objects providing management of
       ADMIN Authentication Clients."
   ::= { alAdminAuthGroup 2 }

END
