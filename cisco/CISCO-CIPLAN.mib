CISCO-CIPLAN-MIB DEFINITIONS ::= BEGIN

IMPORTS
    MODULE-IDENTITY, OBJECT-TYPE
	    FROM SNMPv2-SMI

    MODULE-COMPLIANCE, OBJECT-GROUP
	    FROM SNMPv2-CONF

    DisplayString, RowStatus, MacAddress
	    FROM SNMPv2-TC

    ifIndex
	    FROM RFC1213-MIB

    ciscoMgmt
	    FROM CISCO-SMI;

ciscoCipLanMIB MODULE-IDENTITY
	LAST-UPDATED	"9504280000Z"
	ORGANIZATION	"cisco IBM engineering Working Group"
	CONTACT-INFO
		"	Cisco Systems
			Customer Service

		Postal: 170 W Tasman Drive
			San Jose, CA  95134
			USA

		   Tel: +1 800 553-NETS

		E-mail: cs-snmp@cisco.com"
	DESCRIPTION
		"This is the Management Information Base (MIB) 
		module for objects used to manage the cisco internal 
		LAN support in Cisco Mainframe Channel Connection 
                (CMCC) environments.

       1) LAN
       2) Adapter 

      The following example configuration of a router that
      shows the entities managed by the CIPLAN MIB.

                                   Router A
      -----------------------------------------
      | ------------------------------------- |
      | |                                   | |
      | | -------------------               | |
      | | | Adapter         |      --       | |
      | | | 400000000401    |    /    \     | |
      | | | ADAPNO 0        |---| Ring |    | |
      | | -------------------   |      |----| |
      | | | Adapter         |---| 1000 |    | |
      | | | 400000000402    |    \    /     | |
      | | | ADAPNO 1        |      --       | |
      | | -------------------               | |
      | |                       Token Ring  | |
      | |                       LAN 0       | |
      | |                                   | |
      | |                          --       | |
      | | -------------------    /    \     | |
      | | | Adapter         |---| Ring |    | |
      | | | 400000000401    |   |      |----| |
      | | | ADAPNO 3        |---| 1001 |    | |
      | | -------------------    \    /     | |
      | |                          --       | |
      | |                                   | |
      | |                       Token Ring  | |
      | |                       LAN 1       | |
      | |                                   | |
      | |                                   | |
      | | -------------------               | |
      | | | Adapter         |           |   | |
      | | | 0200000000C1    |---------------| |
      | | | ADAPNO 4        |     |         | |
      | | -------------------               | |
      | |                       Ethernet    | |
      | |                       LAN 0       | |
      | |                                   | |
      | |                                   | |
      | | -------------------      =        | |
      | | | Adapter         |    /   \      | |
      | | | 400000000001    |===|     |=====| |
      | | | ADAPNO 5        |    \   /      | |
      | | -------------------      =        | |
      | |                                   | |
      | |                       FDDI        | |
      | |                       LAN 0       | |
      | |                                   | |
      | |     CMCC CARD 6                   | |
      | ------------------------------------- |
      |                                       |
      -----------------------------------------

    NOTE:  A special ifIndex has been created to address
           internal LAN objects that are on the CMCC card.

           Physically the CMCC card would have two ifIndex's
           of type `other` for each CMCC Slot/Daughter Board.
           The additional ifIndex is made looks like the
           physical with the Daughter Board being replaced
           with a simple integer.  For example:

           If the CMCC is in slot/bay 6; The first daughter
           board would have the ifIndex of 6/0.  The
           second daughter board would have the ifIndex
           of 6/1.  The internal objects on this CMCC card
           would have the ifIndex of 6/2.

           The ifIndex is an INTEGER to which the values will
           be translated to agent specific number by the 
           agent itself.

   The first table is the LAN Admin table.
     Each entry created in this table will represent a
     internal CIP LAN that will be used by MAC adapters
     to bridge data to and from the host.
     The indices of the table are:
       * The special ifIndex that addresses the virtual
         objects on a CMCC card
       * The LAN type (token-ring, ethernet, fddi)
       * The unique LAN identifier
         NOTE:  This value is used to uniquely identify
                each and every LAN based on LAN type
                and on a single CMCC card.
     The fields included in this table represent:
       * The LAN type used as on index
       * The unique LAN identifier used as an index
       * The bridging type
       * For Source Route Bridging, the local ring number
       * For Source Route Bridging, the next bridge number
       * For Source Route Bridging, the target ring number
       * For Transparent Bridging, the bridge group
       * The row control variable
     In the example above, four entries would exist.
     The first entry would be:
       - ifIndex is created by the agent
       - LAN type of token ring
       - LAN identifier of 0
       - bridging type of Source Route
       - local ring number 1000
       - next bridge number is unknown
       - target ring number is unknown
       - transparent bridge group has no meaning
     The second entry would be:
       - ifIndex is created by the agent
       - LAN type of token ring
       - LAN identifier of 1
       - bridging type of Source Route
       - local ring number 1001
       - next bridge number is unknown
       - target ring number is unknown
       - transparent bridge group has no meaning
     The third entry would be:
       - ifIndex is created by the agent
       - LAN type of ethernet
       - LAN identifier of 0
       - bridging type of transparent
       - local ring number has no meaning
       - next bridge number has no meaning
       - target ring number has no meaning
       - transparent bridge group is unknown
     The fourth entry would be:
       - ifIndex is created by the agent
       - LAN type of fddi
       - LAN identifier of 0
       - bridging type of transparent
       - local ring number has no meaning
       - next bridge number has no meaning
       - target ring number has no meaning
       - transparent bridge group is unknown

   The last table is the CIP LAN Adapter Admin table.
     Each entry created in this table will represent a
     LAN adapter on one of the CMCC internal LAN's
     defined in the first table.
     The indices of the table are:
       * The special ifIndex that addresses the virtual
         objects on a CMCC card
       * The LAN type (token-ring, ethernet, fddi)
       * The unique LAN identifier from the first table
       * The unique Adapter Number for this LAN type
         NOTE:  When multiple LANs of the same type
                exist, this number must be kept unique
                by the agent.  (The LAN type is defined
                by the Virtual LAN Admin table.)
     The fields included in this table represent:
       * The unique Adapter Number for this LAN type
         as defined by the LAN Admin Entry
         corresponding the the first two indices in
         this table
       * The MAC Address for this Adapter;  this
         MAC Address is unique for all Adapters
         define on this LAN, but does not need to be
         unique across LANs for redundancy
       * The Adapter name
       * The row control variable
     In the example above, five entries would exist.
     The first entry would be:
       - ifIndex is created by the agent
       - the LAN type from the first table
       - the LAN identifier from the first table = 0
       - adapter number of 0
       - Mac Address of 400000000401
       - Configured Name
     The second entry would be:
       - ifIndex is created by the agent
       - the LAN type from the first table
       - the LAN identifier from the first table = 0
       - adapter number of 1
       - Mac Address of 400000000402
       - Configured Name
     The first entry would be:
       - ifIndex is created by the agent
       - the LAN type from the first table
       - the LAN identifier from the first table = 1
       - adapter number of 2
       - Mac Address of 400000000401
       - Configured Name
     The first entry would be:
       - ifIndex is created by the agent
       - the LAN type from the first table
       - the LAN identifier from the first table = 0
       - adapter number of 3
       - Mac Address of 0200000000C1
       - Configured Name
     The first entry would be:
       - ifIndex is created by the agent
       - the LAN type from the first table
       - the LAN identifier from the first table = 0
       - adapter number of 4
       - Mac Address of 400000000001
       - Configured Name
      "
	REVISION        "9801060000Z"
	DESCRIPTION
		"With the addition of Cisco's new Channel Port
                 Adapter cards, all the references to CIP in the
                 MIB description and object descriptions are changed
                 to CMCC (Cisco Mainframe Channel Connection). The
                 object names in the form of cip... or cipCard...
                 will remain the same, but will be valid objects
                 for the Channel Port Adapter cards."

	REVISION	"9504280000Z"
	DESCRIPTION
		"Initial version of this MIB module."
	::= { ciscoMgmt 34 }

cipLanObjects            OBJECT IDENTIFIER ::= { ciscoCipLanMIB 1 }

cipLan                  OBJECT IDENTIFIER ::= { cipLanObjects 1 }

-- ;;;;;;;;;;;;;;;;;;;;; cipCardLanAdminTable ;;;;;;;;;;;;;;;;;;;;;;
-- Variables stored in this table are:
--     <lan id> <lan type> <bridge type>
--     <source route bridge local ring> <source route bridge number>
--     <source route bridge target ring> <bridge group>

cipCardLanAdminTable OBJECT-TYPE 
  SYNTAX      SEQUENCE OF CipCardLanAdminEntry
  MAX-ACCESS  not-accessible
  STATUS      current
  DESCRIPTION
      "This table contains configuration information for
       the LAN feature on the CMCC card."
  ::= { cipLan 1 }

cipCardLanAdminEntry OBJECT-TYPE
  SYNTAX      CipCardLanAdminEntry
  MAX-ACCESS  not-accessible
  STATUS      current
  DESCRIPTION
      "A list of CMCC LAN configuration values."
  INDEX   { ifIndex, 
            cipCardLanAdminLanType,
            cipCardLanAdminLanId }
  ::= { cipCardLanAdminTable 1 }

CipCardLanAdminEntry ::= SEQUENCE
{
  cipCardLanAdminLanType             INTEGER,
  cipCardLanAdminLanId               INTEGER (0..31),
  cipCardLanAdminBridgeType          INTEGER,
  cipCardLanAdminSrbLocalRing        INTEGER (1..4095),
  cipCardLanAdminSrbBridgeNum        INTEGER (1..15),
  cipCardLanAdminSrbTargetRing       INTEGER (1..4095),
  cipCardLanAdminTbBridgeGrp         INTEGER (1..63),
  cipCardLanAdminRowStatus           RowStatus
}

cipCardLanAdminLanType OBJECT-TYPE
  SYNTAX      INTEGER {
              iso88023csmacd    (1),
              iso88025tokenRing (2),
              fddi              (3)
              }
  MAX-ACCESS  not-accessible
  STATUS      current
  DESCRIPTION
      "The type of Emulation applied to this
       CMCC LAN."
  ::= { cipCardLanAdminEntry 1 }

cipCardLanAdminLanId OBJECT-TYPE
  SYNTAX      INTEGER (0..31)
  MAX-ACCESS  not-accessible
  STATUS      current
  DESCRIPTION
      "The index value used with the ifIndex 
       to uniquely identify a CMCC LAN.

       This is just an identifier and has
       no relationship to the bridging
       protocols."
  ::= { cipCardLanAdminEntry 2 }

cipCardLanAdminBridgeType OBJECT-TYPE
  SYNTAX      INTEGER {
              transparentOnly      (1),
              sourcerouteOnly      (2),
              transpAndSourceRoute (3) 
              }
  MAX-ACCESS  read-create
  STATUS      current
  DESCRIPTION
      "The bridging type supported by
       this CMCC LAN.  

       The value of transparentOnly (1) is valid for
       all LAN types. 

       The value of sourcerouteOnly (2) is only valid for 
       iso88025tokenRing and fddi LAN types.

       The value of transpAndSourceRoute (3) is valid for 
       all iso88025tokenRing and fddi LAN types."
  ::= { cipCardLanAdminEntry 3 }

cipCardLanAdminSrbLocalRing OBJECT-TYPE
  SYNTAX      INTEGER (1..4095)
  MAX-ACCESS  read-create
  STATUS      current
  DESCRIPTION
      "The local Segment (Ring) number that
       uniquely identify this CIP LAN.

       This variable is only valid when
       cipCardLanAdminBridgeType is sourcerouteOnly (2)
       or transpAndSourceRoute (3)."
  ::= { cipCardLanAdminEntry 4 }

cipCardLanAdminSrbBridgeNum OBJECT-TYPE
  SYNTAX      INTEGER (1..15)
  MAX-ACCESS  read-create
  STATUS      current
  DESCRIPTION
      "The Bridge number that represents this routers'
       bridge number.

       This variable is only valid when
       cipCardLanAdminBridgeType is sourcerouteOnly (2)
       or transpAndSourceRoute (3)."
  ::= { cipCardLanAdminEntry 5 }

cipCardLanAdminSrbTargetRing OBJECT-TYPE
  SYNTAX      INTEGER (1..4095)
  MAX-ACCESS  read-create
  STATUS      current
  DESCRIPTION
      "The target Segment (Ring) number that is the next
       hop from this segment.

       This variable is only valid when
       cipCardLanAdminBridgeType is sourcerouteOnly (2)
       or transpAndSourceRoute (3)."
  ::= { cipCardLanAdminEntry 6 }

cipCardLanAdminTbBridgeGrp OBJECT-TYPE
  SYNTAX      INTEGER (1..63)
  MAX-ACCESS  read-create
  STATUS      current
  DESCRIPTION
      "The transparent bridge group that this 
       CIP  LAN is a member.

       This variable is only valid when
       cipCardLanAdminBridgeType is transparentOnly (1)
       or transpAndSourceRoute (3)."
  ::= { cipCardLanAdminEntry 7 }

cipCardLanAdminRowStatus OBJECT-TYPE
  SYNTAX      RowStatus
  MAX-ACCESS  read-create
  STATUS      current
  DESCRIPTION
      "This object is used by a Management Station to create
       or delete the row entry in the cipCardLanAdminTable 
       following the the RowStatus textual convention."
  ::= { cipCardLanAdminEntry 8 }

-- ;;;;;;;;;;;;;;;;;;;;; cipCardLanAdaptAdminTable ;;;;;;;;;;;;;;;;;;;;;;;;;;;
-- Variables stored in this table are:
--      <adapter number> <mac address> <adapter name>

cipCardLanAdaptAdminTable OBJECT-TYPE 
  SYNTAX      SEQUENCE OF CipCardLanAdaptAdminEntry
  MAX-ACCESS  not-accessible
  STATUS      current
  DESCRIPTION
      "This table contains configuration information for
       the LAN Adapter feature on the CMCC card."
  ::= { cipLan 2 }

cipCardLanAdaptAdminEntry OBJECT-TYPE
  SYNTAX      CipCardLanAdaptAdminEntry
  MAX-ACCESS  not-accessible
  STATUS      current
  DESCRIPTION
      "A list of CMCC LAN Adapter configuration values."
  INDEX   { ifIndex,
            cipCardLanAdminLanType,
            cipCardLanAdminLanId,
            cipCardLanAdaptAdminAdaptNo
          }
  ::= { cipCardLanAdaptAdminTable 1 }

CipCardLanAdaptAdminEntry ::= SEQUENCE
{
  cipCardLanAdaptAdminAdaptNo           INTEGER (0..31),
  cipCardLanAdaptAdminMacAddress        MacAddress,
  cipCardLanAdaptAdminAdaptName         DisplayString (SIZE (1..8)),
  cipCardLanAdaptAdminRowStatus         RowStatus
}

cipCardLanAdaptAdminAdaptNo OBJECT-TYPE
  SYNTAX      INTEGER (0..31)
  MAX-ACCESS  not-accessible
  STATUS      current
  DESCRIPTION
      "The Adapter Number used when creating
       a CMCC LAN Adapter.  This value is
       given by the instance value when 
       this row is being created. 

       This number corresponds to the
       'ADAPNO' value used VTAM XCA
       node definition.

       This number uniquely identify this 
       Adapter from all other Adapters for 
       the LAN type, which is identified 
       in the associated CMCC LAN Adapter Table."
  ::= { cipCardLanAdaptAdminEntry 1 }

cipCardLanAdaptAdminMacAddress OBJECT-TYPE
  SYNTAX      MacAddress
  MAX-ACCESS  read-create
  STATUS      current
  DESCRIPTION
      "The Adapter MAC Address is assigned
       by the router administrator. It is 
       a unique number used by protocols to 
       address this Adapter on the CMCC
       LAN identified by the second index
       (cipCardLanAdminLanId).  

       NOTE:  In order to have duplicate 
              MAC Addresses, they must
              be on different Source Route
              Bridge LAN's."
  ::= { cipCardLanAdaptAdminEntry 2 }

cipCardLanAdaptAdminAdaptName OBJECT-TYPE
  SYNTAX      DisplayString (SIZE (1..8))
  MAX-ACCESS  read-create
  STATUS      current
  DESCRIPTION
      "This name is assigned by the router
       administrator and must be unique per
       router. Every interface of  the router 
       can be named by the router administrator. 
       This object provides a means of naming the
       CMCC LAN adapter interfaces.

       The Adapter Name is used in the 
       Hierarchy Resource List when creating a 
       Systems Network Architecture Generic 
       Alert for the purpose of identify the 
       CMCC LAN adapter which generated the 
       alert."
  ::= { cipCardLanAdaptAdminEntry 3 }

cipCardLanAdaptAdminRowStatus OBJECT-TYPE
  SYNTAX      RowStatus
  MAX-ACCESS  read-create
  STATUS      current
  DESCRIPTION
      "This object is used by a Management Station to create
       or delete the row entry in the cipCardCsnaAdminTable 
       following the the RowStatus textual convention."
  ::= { cipCardLanAdaptAdminEntry 4 }

-- ;;;;;;;;;;;;;;;;;;;;;;;;;;;;;;;;;;;;;;;;;;;;;;;;;;;;;;;;;;;;;;;;;;;;;;;;;;
--
-- Conformance Information
--

ciscoCipLanMibConformance OBJECT IDENTIFIER ::= { ciscoCipLanMIB 2 }
ciscoCipLanMibCompliances OBJECT IDENTIFIER 
                                  ::= { ciscoCipLanMibConformance 1 }
ciscoCipLanMibGroups      OBJECT IDENTIFIER 
                                  ::= { ciscoCipLanMibConformance 2 }

--
-- Compliance Statements
--

ciscoCipLanMibCompliance MODULE-COMPLIANCE
  STATUS current
  DESCRIPTION
    "The compliance statement for the CMCC LAN Support."
  MODULE
    MANDATORY-GROUPS {
      ciscoLanGroup,
      ciscoLanAdaptGroup
    }

    OBJECT cipCardLanAdminBridgeType
    DESCRIPTION "The value transpAndSourceRoute (3) is 
                 valid for bridges that support last 
                 hop media of either type.  This allows
                 the bridge to forward either frame
                 type without having to translate the
                 frame type."
  ::= { ciscoCipLanMibCompliances 1 }

ciscoLanGroup OBJECT-GROUP
  OBJECTS {
    -- Table Header
    --  cipCardLanAdminTable
    --  cipCardLanAdminEntry
    -- Table Indicies
    --  ifIndex
    --  cipCardLanAdminLanType
    --  cipCardLanAdminLanId

    cipCardLanAdminBridgeType,
    cipCardLanAdminSrbLocalRing,
    cipCardLanAdminSrbBridgeNum,
    cipCardLanAdminSrbTargetRing,
    cipCardLanAdminTbBridgeGrp,
    cipCardLanAdminRowStatus
  }
  STATUS current
  DESCRIPTION
    "A collection of objects providing CMCC
     LAN Administration."
  ::= { ciscoCipLanMibGroups 1 }

ciscoLanAdaptGroup OBJECT-GROUP
  OBJECTS {
    -- Table Header
    --  cipCardLanAdaptAdminTable
    --  cipCardLanAdaptAdminEntry
    -- Table Indicies
    --  ifIndex
    --  cipCardLanAdminLanType
    --  cipCardLanAdminLanId
    --  cipCardLanAdaptAdminAdaptNo

    cipCardLanAdaptAdminMacAddress,
    cipCardLanAdaptAdminAdaptName,
    cipCardLanAdaptAdminRowStatus
  }
  STATUS current
  DESCRIPTION
    "A collection of objects providing CMCC
     LAN Adapter Administration."
  ::= { ciscoCipLanMibGroups 2 }

END
