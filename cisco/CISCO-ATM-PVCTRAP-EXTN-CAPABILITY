CISCO-ATM-PVCTRAP-EXTN-CAPABILITY DEFINITIONS ::= BEGIN
IMPORTS
        MODULE-IDENTITY
                FROM SNMPv2-SMI
        AGENT-CAPABILITIES
                FROM SNMPv2-CONF
        ciscoAgentCapability
                FROM CISCO-SMI;   

ciscoATMPVCTRAPExtnCapability MODULE-IDENTITY
        LAST-UPDATED    "200211060000Z"
        ORGANIZATION    "Cisco Systems, Inc."
        CONTACT-INFO
                "       Cisco Systems
                        Customer Service

                Postal: 170 W Tasman Drive
                        San Jose, CA  95134
                        USA

                        Tel: +1 800 553-NETS

                E-mail: cs-atm@cisco.com"
        DESCRIPTION
                "The Agent Capabilities for 
                CISCO-ATM-PVCTRAP-EXTN-MIB."

        REVISION "200211060000Z"
        DESCRIPTION
            "Initial version of the MIB Module."
        ::= { ciscoAgentCapability 289 }

ciscoATMPVCTRAPExtnCapabilityV12R00S AGENT-CAPABILITIES
    PRODUCT-RELEASE      "Cisco IOS 12.0S"
    STATUS               current
    DESCRIPTION          "CISCO-ATM-PVCTRAP-EXTN-MIB Capabilities"

    SUPPORTS CISCO-ATM-PVCTRAP-EXTN-MIB
        INCLUDES { ciscoAtmPvcTrapExtnGroup, 
                   ciscoAtmPvcTrapExtnNotifGroup1 }

        VARIATION catmIntfPvcOAMFailureTrap  -- TRAP-TYPE
--              OBJECTS { ifIndex,
--                        catmIntfOAMFailedPVcls,
--                        catmIntfCurrentOAMFailingPVcls,
--                        atmVclVpi,
--                        atmVclVci,
--                        catmPVclStatusTransition,
--                        catmPVclStatusChangeStart,
--                        catmPVclStatusChangeEnd,
--                        catmStatusChangePVclRangeIndex,
--                        catmPVclLowerRangeValue,
--                        catmPVclHigherRangeValue,
--                        catmPVclRangeStatusChangeStart,
--                        catmPVclRangeStatusChangeEnd }
        DESCRIPTION "A catmIntfPvcOAMFailureTrap signifies that the
                     loopback F5 OAM failure is detected on the PVC in
                     the last PVC TRAP notification interval. 

                     If the set of loopback failed PVCs contains 
                     successive VCIs, then the varbinds sent in this 
                     TRAP contains information about ranges 
                     representing these groups of PVCs. In this
                     case, the atmVclVpi,
                     catmStatusChangePVclRangeIndex, 
                     catmPVclLowerRangeValue, 
                     catmPVclHigherRangeValue, 
                     catmPVclRangeStatusChangeStart, 
                     catmPVclRangeStatusChangeEnd are used. 

                     If the set of loopback failed PVCs contains 
                     singled out PVCs (i.e. PVC with VPI1, VCI1 is 
                     contained in the set; but neither a PVC with VPI1 
                     and VCI1 - 1 nor a PVC with VPI1 and VCI1 + 1 is 
                     contained in the set of loopback failed PVCs) 
                     then the varbinds sent in this notification
                     contains information about the individual PVCs.
                     In this case, the atmVclVpi, atmVclVci, 
                     catmPVclStatusTransition, 
                     catmPVclStatusChangeStart, 
                     catmPVclStatusChangeEnd will be used. 

                     In the case where the set of loopback failed PVCs 
                     contains both successive and singled out PVCs 
                     both sets of objects will be used."
    ::= { ciscoATMPVCTRAPExtnCapability 1 }

        VARIATION catmIntfPvcSegCCOAMFailureTrap  -- TRAP-TYPE
--              OBJECTS { ifIndex,
--                        catmIntfSegCCOAMFailedPVcls,
--                        catmIntfCurSegCCOAMFailingPVcls,
--                        atmVclVpi,
--                        atmVclVci,
--                        catmPVclSegCCStatusTransition,
--                        catmPVclSegCCStatusChangeStart,
--                        catmPVclSegCCStatusChangeEnd,
--                        catmStatusChangePVclRangeIndex,
--                        catmPVclSegCCLowerRangeValue,
--                        catmPVclSegCCHigherRangeValue,
--                        catmPVclSegCCRangeStatusChStart,
--                        catmPVclSegCCRangeStatusChEnd }
        DESCRIPTION "A catmIntfPvcSegCCOAMFailureTrap signifies that 
                     the segment CC F5 OAM failure is detected on 
                     the PVC in the last PVC TRAP notification 
                     interval. 

                     If the set of segment CC failed PVCs contains 
                     successive VCIs, then the varbinds sent in this 
                     TRAP contains information about ranges 
                     representing these groups of PVCs. In this
                     case, the atmVclVpi,
                     catmStatusChangePVclRangeIndex, 
                     catmPVclSegCCLowerRangeValue, 
                     catmPVclSegCCHigherRangeValue, 
                     catmPVclSegCCRangeStatusChStart, 
                     catmPVclSegCCRangeStatusChEnd are used. 

                     If the set of segment CC failed PVCs contains 
                     singled out PVCs (i.e. PVC with VPI1, VCI1 is 
                     contained in the set; but neither a PVC with VPI1 
                     and VCI1 - 1 nor a PVC with VPI1 and VCI1 + 1 is 
                     contained in the set of segment CC failed PVCs) 
                     then the varbinds sent in this notification
                     contains information about the individual PVCs.
                     In this case, the atmVclVpi, atmVclVci, 
                     catmPVclSegCCStatusTransition, 
                     catmPVclSegCCStatusChangeStart, 
                     catmPVclSegCCStatusChangeEnd will be used. 

                     In the case where the set of segment CC failed 
                     PVCs contains both successive and singled out
                     PVCs, both sets of objects will be used."
    ::= { ciscoATMPVCTRAPExtnCapability 2 }

        VARIATION catmIntfPvcEndCCOAMFailureTrap  -- TRAP-TYPE
--              OBJECTS { ifIndex,
--                        catmIntfEndCCOAMFailedPVcls,
--                        catmIntfCurEndCCOAMFailingPVcls,
--                        atmVclVpi,
--                        atmVclVci,
--                        catmPVclEndCCStatusTransition,
--                        catmPVclEndCCStatusChangeStart,
--                        catmPVclEndCCStatusChangeEnd,
--                        catmStatusChangePVclRangeIndex,
--                        catmPVclEndCCLowerRangeValue,
--                        catmPVclEndCCHigherRangeValue,
--                        catmPVclEndCCRangeStatusChStart,
--                        catmPVclEndCCRangeStatusChEnd }
        DESCRIPTION "A catmIntfPvcEndCCOAMFailureTrap signifies that 
                     the End CC F5 OAM failure is detected on the 
                     PVC in the last PVC TRAP notification interval. 

                     If the set of End CC failed PVCs contains 
                     successive VCIs, then the varbinds sent in this 
                     TRAP contains information about ranges 
                     representing these groups of PVCs. In this
                     case, the atmVclVpi,
                     catmStatusChangePVclRangeIndex, 
                     catmPVclEndCCLowerRangeValue, 
                     catmPVclEndCCHigherRangeValue, 
                     catmPVclEndCCRangeStatusChStart, 
                     catmPVclEndCCRangeStatusChEnd are used. 

                     If the set of End CC failed PVCs contains 
                     singled out PVCs (i.e. PVC with VPI1, VCI1 is 
                     contained in the set; but neither a PVC with VPI1 
                     and VCI1 - 1 nor a PVC with VPI1 and VCI1 + 1 is 
                     contained in the set of End CC failed PVCs) 
                     then the varbinds sent in this notification
                     contains information about the individual PVCs.
                     In this case, the atmVclVpi, atmVclVci, 
                     catmPVclEndCCStatusTransition, 
                     catmPVclEndCCStatusChangeStart, 
                     catmPVclEndCCStatusChangeEnd will be used. 

                     In the case where the set of End CC failed PVCs 
                     contains both successive and singled out PVCs, 
                     both sets of objects will be used."
    ::= { ciscoATMPVCTRAPExtnCapability 3 }

        VARIATION catmIntfPvcAISRDIOAMFailureTrap  -- TRAP-TYPE
--              OBJECTS { ifIndex,
--                        catmIntfAISRDIOAMFailedPVcls,
--                        catmIntfCurAISRDIOAMFailingPVcls,
--                        atmVclVpi,
--                        atmVclVci,
--                        catmPVclAISRDIStatusTransition,
--                        catmPVclAISRDIStatusChangeStart,
--                        catmPVclAISRDIStatusChangeEnd,
--                        catmStatusChangePVclRangeIndex,
--                        catmPVclAISRDILowerRangeValue,
--                        catmPVclAISRDIHigherRangeValue,
--                        catmPVclAISRDIRangeStatusChStart,
--                        catmPVclAISRDIRangeStatusChEnd }
        DESCRIPTION "A catmIntfPvcAISRDIOAMFailureTrap signifies 
                     that the AIS/RDI F5 OAM failure is detected 
                     on the PVC in the last PVC TRAP notification 
                     interval. 

                     If the set of AIS/RDI failed PVCs contains 
                     successive VCIs, then the varbinds sent in this 
                     TRAP contains information about ranges 
                     representing these groups of PVCs. In this
                     case, the atmVclVpi,
                     catmStatusChangePVclRangeIndex, 
                     catmPVclAISRDILowerRangeValue, 
                     catmPVclAISRDIHigherRangeValue, 
                     catmPVclAISRDIRangeStatusChStart, 
                     catmPVclAISRDIRangeStatusChEnd are used. 

                     If the set of AIS/RDI failed PVCs contains 
                     singled out PVCs (i.e. PVC with VPI1, VCI1 is 
                     contained in the set; but neither a PVC with VPI1 
                     and VCI1 - 1 nor a PVC with VPI1 and VCI1 + 1 is 
                     contained in the set of AIS/RDI failed PVCs) 
                     then the varbinds sent in this notification
                     contains information about the individual PVCs.
                     In this case, the atmVclVpi, atmVclVci, 
                     catmPVclAISRDIStatusTransition, 
                     catmPVclAISRDIStatusChangeStart, 
                     catmPVclAISRDIStatusChangeEnd will be used. 

                     In the case where the set of AIS/RDI failed PVCs 
                     contains both successive and singled out PVCs, 
                     both sets of objects will be used."
    ::= { ciscoATMPVCTRAPExtnCapability 4 }

        VARIATION catmIntfPvcAnyOAMFailureTrap  -- TRAP-TYPE
--              OBJECTS { ifIndex,
--                        catmIntfAnyOAMFailedPVcls,
--                        catmIntfCurAnyOAMFailingPVcls,
--                        catmIntfTypeOfOAMFailure,
--                        atmVclVpi,
--                        atmVclVci,
--                        catmPVclStatusTransition,
--                        catmPVclStatusChangeStart,
--                        catmPVclStatusChangeEnd,
--                        catmStatusChangePVclRangeIndex,
--                        catmPVclLowerRangeValue,
--                        catmPVclHigherRangeValue,
--                        catmPVclRangeStatusChangeStart,
--                        catmPVclRangeStatusChangeEnd,
--                        catmPVclSegCCStatusTransition,
--                        catmPVclSegCCStatusChangeStart,
--                        catmPVclSegCCStatusChangeEnd,
--                        catmStatusChangePVclRangeIndex,
--                        catmPVclSegCCLowerRangeValue,
--                        catmPVclSegCCHigherRangeValue,
--                        catmPVclSegCCRangeStatusChStart,
--                        catmPVclSegCCRangeStatusChEnd,
--                        catmPVclEndCCStatusTransition,
--                        catmPVclEndCCStatusChangeStart,
--                        catmPVclEndCCStatusChangeEnd,
--                        catmStatusChangePVclRangeIndex,
--                        catmPVclEndCCLowerRangeValue,
--                        catmPVclEndCCHigherRangeValue,
--                        catmPVclEndCCRangeStatusChStart,
--                        catmPVclEndCCRangeStatusChEnd,
--                        catmPVclAISRDIStatusTransition,
--                        catmPVclAISRDIStatusChangeStart,
--                        catmPVclAISRDIStatusChangeEnd,
--                        catmStatusChangePVclRangeIndex,
--                        catmPVclAISRDILowerRangeValue,
--                        catmPVclAISRDIHigherRangeValue,
--                        catmPVclAISRDIRangeStatusChStart,
--                        catmPVclAISRDIRangeStatusChEnd } 
        DESCRIPTION "A catmIntfPvcAnyOAMFailureTrap signifies that the
                     one or more type of F5 OAM failure is detected on 
                     the PVC in the last PVC TRAP notification 
                     interval. 
                     The type of F5 OAM failure can be 
                     Loopback F5 OAM failure,
                     Segment CC F5 OAM failure,
                     End CC F5 OAM failure,
                     AIS/RDI F5 OAM failure.

                     If the set of loopback failed PVCs contains 
                     successive VCIs, then the varbinds sent in this 
                     TRAP contains information about ranges 
                     representing these groups of PVCs. In this
                     case, the atmVclVpi,
                     catmStatusChangePVclRangeIndex, 
                     catmPVclLowerRangeValue, 
                     catmPVclHigherRangeValue, 
                     catmPVclRangeStatusChangeStart, 
                     catmPVclRangeStatusChangeEnd are used. 

                     If the set of loopback failed PVCs contains 
                     singled out PVCs (i.e. PVC with VPI1, VCI1 is 
                     contained in the set; but neither a PVC with VPI1 
                     and VCI1 - 1 nor a PVC with VPI1 and VCI1 + 1 is 
                     contained in the set of loopback failed PVCs) 
                     then the varbinds sent in this notification
                     contains information about the individual PVCs.
                     In this case, the atmVclVpi, atmVclVci, 
                     catmPVclStatusTransition, 
                     catmPVclStatusChangeStart, 
                     catmPVclStatusChangeEnd will be used. 

                     In the case where the set of loopback failed PVCs 
                     contains both successive and singled out PVCs 
                     both sets of objects will be used.

                     If the set of segment CC failed PVCs contains 
                     successive VCIs, then the varbinds sent in this 
                     TRAP contains information about ranges 
                     representing these groups of PVCs. In this
                     case, the atmVclVpi,
                     catmStatusChangePVclRangeIndex, 
                     catmPVclSegCCLowerRangeValue, 
                     catmPVclSegCCHigherRangeValue, 
                     catmPVclSegCCRangeStatusChStart, 
                     catmPVclSegCCRangeStatusChEnd are used. 

                     If the set of segment CC failed PVCs contains 
                     singled out PVCs (i.e. PVC with VPI1, VCI1 is 
                     contained in the set; but neither a PVC with VPI1 
                     and VCI1 - 1 nor a PVC with VPI1 and VCI1 + 1 is 
                     contained in the set of segment CC failed PVCs) 
                     then the varbinds sent in this notification
                     contains information about the individual PVCs.
                     In this case, the atmVclVpi, atmVclVci, 
                     catmPVclSegCCStatusTransition, 
                     catmPVclSegCCStatusChangeStart, 
                     catmPVclSegCCStatusChangeEnd will be used. 

                     In the case where the set of segment CC failed 
                     PVCs contains both successive and singled out 
                     PVCs, both sets of objects will be used.

                     If the set of End CC failed PVCs contains 
                     successive VCIs, then the varbinds sent in this 
                     TRAP contains information about ranges 
                     representing these groups of PVCs. In this
                     case, the atmVclVpi,
                     catmStatusChangePVclRangeIndex, 
                     catmPVclEndCCLowerRangeValue, 
                     catmPVclEndCCHigherRangeValue, 
                     catmPVclEndCCRangeStatusChStart, 
                     catmPVclEndCCRangeStatusChEnd are used. 

                     If the set of End CC failed PVCs contains 
                     singled out PVCs (i.e. PVC with VPI1, VCI1 is 
                     contained in the set; but neither a PVC with VPI1 
                     and VCI1 - 1 nor a PVC with VPI1 and VCI1 + 1 is 
                     contained in the set of End CC failed PVCs) 
                     then the varbinds sent in this notification
                     contains information about the individual PVCs.
                     In this case, the atmVclVpi, atmVclVci, 
                     catmPVclEndCCStatusTransition, 
                     catmPVclEndCCStatusChangeStart, 
                     catmPVclEndCCStatusChangeEnd will be used. 

                     In the case where the set of End CC failed PVCs 
                     contains both successive and singled out PVCs, 
                     both sets of objects will be used.

                     If the set of AIS/RDI failed PVCs contains 
                     successive VCIs, then the varbinds sent in this 
                     TRAP contains information about ranges 
                     representing these groups of PVCs. In this
                     case, the atmVclVpi,
                     catmStatusChangePVclRangeIndex, 
                     catmPVclAISRDILowerRangeValue, 
                     catmPVclAISRDIHigherRangeValue, 
                     catmPVclAISRDIRangeStatusChStart, 
                     catmPVclAISRDIRangeStatusChEnd are used. 

                     If the set of AIS/RDI failed PVCs contains 
                     singled out PVCs (i.e. PVC with VPI1, VCI1 is 
                     contained in the set; but neither a PVC with VPI1 
                     and VCI1 - 1 nor a PVC with VPI1 and VCI1 + 1 is 
                     contained in the set of AIS/RDI failed PVCs) 
                     then the varbinds sent in this notification
                     contains information about the individual PVCs.
                     In this case, the atmVclVpi, atmVclVci, 
                     catmPVclAISRDIStatusTransition, 
                     catmPVclAISRDIStatusChangeStart, 
                     catmPVclAISRDIStatusChangeEnd will be used. 

                     In the case where the set of AIS/RDI failed PVCs 
                     contains both successive and singled out PVCs, 
                     both sets of objects will be used."
    ::= { ciscoATMPVCTRAPExtnCapability 5 }

        VARIATION catmIntfPvcOAMRecoverTrap  -- TRAP-TYPE
--              OBJECTS { ifIndex,
--                        catmIntfOAMRcovedPVcls,
--                        catmIntfCurrentOAMRcovingPVcls,
--                        atmVclVpi,
--                        atmVclVci,
--                        catmPVclStatusUpTransition,
--                        catmPVclStatusUpStart,
--                        catmPVclStatusUpEnd,
--                        catmStatusChangePVclRangeIndex,
--                        catmPVclUpLowerRangeValue,
--                        catmPVclUpHigherRangeValue,
--                        catmPVclRangeStatusUpStart,
--                        catmPVclRangeStatusUpEnd }
        DESCRIPTION "A catmIntfPvcOAMRecoverTrap signifies that the
                     loopback F5 OAM recovery is detected on the PVC in
                     the last PVC TRAP notification interval. 

                     If the set of loopback recovered PVCs contains 
                     successive VCIs, then the varbinds sent in this 
                     TRAP contains information about ranges 
                     representing these groups of PVCs. In this
                     case, the atmVclVpi,
                     catmStatusChangePVclRangeIndex, 
                     catmPVclUpLowerRangeValue, 
                     catmPVclUpHigherRangeValue, 
                     catmPVclRangeStatusUpStart, 
                     catmPVclRangeStatusUpEnd are used. 

                     If the set of loopback recovered PVCs contains 
                     singled out PVCs (i.e. PVC with VPI1, VCI1 is 
                     contained in the set; but neither a PVC with VPI1 
                     and VCI1 - 1 nor a PVC with VPI1 and VCI1 + 1 is 
                     contained in the set of loopback recovered PVCs) 
                     then the varbinds sent in this notification
                     contains information about the individual PVCs.
                     In this case, the atmVclVpi, atmVclVci, 
                     catmPVclStatusUpTransition, 
                     catmPVclStatusUpStart, 
                     catmPVclStatusUpEnd will be used. 

                     In the case where the set of loopback recovered 
                     PVCs contains both successive and singled out 
                     PVCs both sets of objects will be used."
    ::= { ciscoATMPVCTRAPExtnCapability 7 }

        VARIATION catmIntfPvcSegCCOAMRecoverTrap  -- TRAP-TYPE
--              OBJECTS { ifIndex,
--                        catmIntfSegCCOAMRcovedPVcls,
--                        catmIntfCurSegCCOAMRcovingPVcls,
--                        atmVclVpi,
--                        atmVclVci,
--                        catmPVclSegCCStatusUpTransition,
--                        catmPVclSegCCStatusUpStart,
--                        catmPVclSegCCStatusUpEnd,
--                        catmStatusChangePVclRangeIndex,
--                        catmPVclSegCCUpLowerRangeValue,
--                        catmPVclSegCCUpHigherRangeValue,
--                        catmPVclSegCCRangeStatusUpStart,
--                        catmPVclSegCCRangeStatusUpEnd }
        DESCRIPTION "A catmIntfPvcSegCCOAMRecoverTrap signifies that 
                     the segment CC F5 OAM recovery is detected on 
                     the PVC in the last PVC TRAP notification 
                     interval. 

                     If the set of segment CC recovered PVCs contains 
                     successive VCIs, then the varbinds sent in this 
                     TRAP contains information about ranges 
                     representing these groups of PVCs. In this
                     case, the atmVclVpi,
                     catmStatusChangePVclRangeIndex, 
                     catmPVclSegCCUpLowerRangeValue, 
                     catmPVclSegCCUpHigherRangeValue, 
                     catmPVclSegCCRangeStatusUpStart, 
                     catmPVclSegCCRangeStatusUpEnd are used. 

                     If the set of segment CC recovered PVCs contains 
                     singled out PVCs (i.e. PVC with VPI1, VCI1 is 
                     contained in the set; but neither a PVC with VPI1 
                     and VCI1 - 1 nor a PVC with VPI1 and VCI1 + 1 is 
                     contained in the set of segment CC recovered PVCs) 
                     then the varbinds sent in this notification
                     contains information about the individual PVCs.
                     In this case, the atmVclVpi, atmVclVci, 
                     catmPVclSegCCStatusUpTransition, 
                     catmPVclSegCCStatusUpStart, 
                     catmPVclSegCCStatusUpEnd will be used. 

                     In the case where the set of segment CC recovered 
                     PVCs contains both successive and singled out
                     PVCs, both sets of objects will be used."
    ::= { ciscoATMPVCTRAPExtnCapability 8 }

        VARIATION catmIntfPvcEndCCOAMRecoverTrap  -- TRAP-TYPE
--              OBJECTS { ifIndex,
--                        catmIntfEndCCOAMRcovedPVcls,
--                        catmIntfCurEndCCOAMRcovingPVcls,
--                        atmVclVpi,
--                        atmVclVci,
--                        catmPVclEndCCStatusUpTransition,
--                        catmPVclEndCCStatusUpStart,
--                        catmPVclEndCCStatusUpEnd,
--                        catmStatusChangePVclRangeIndex,
--                        catmPVclEndCCUpLowerRangeValue,
--                        catmPVclEndCCUpHigherRangeValue,
--                        catmPVclEndCCRangeStatusUpStart,
--                        catmPVclEndCCRangeStatusUpEnd }
        DESCRIPTION "A catmIntfPvcEndCCOAMRecoverTrap signifies that 
                     the End CC F5 OAM recovery is detected on the 
                     PVC in the last PVC TRAP notification interval. 

                     If the set of End CC recovered PVCs contains 
                     successive VCIs, then the varbinds sent in this 
                     TRAP contains information about ranges 
                     representing these groups of PVCs. In this
                     case, the atmVclVpi,
                     catmStatusChangePVclRangeIndex, 
                     catmPVclEndCCUpLowerRangeValue, 
                     catmPVclEndCCUpHigherRangeValue, 
                     catmPVclEndCCRangeStatusUpStart, 
                     catmPVclEndCCRangeStatusUpEnd are used. 

                     If the set of End CC recovered PVCs contains 
                     singled out PVCs (i.e. PVC with VPI1, VCI1 is 
                     contained in the set; but neither a PVC with VPI1 
                     and VCI1 - 1 nor a PVC with VPI1 and VCI1 + 1 is 
                     contained in the set of End CC recovered PVCs) 
                     then the varbinds sent in this notification
                     contains information about the individual PVCs.
                     In this case, the atmVclVpi, atmVclVci, 
                     catmPVclEndCCStatusUpTransition, 
                     catmPVclEndCCStatusUpStart, 
                     catmPVclEndCCStatusUpEnd will be used. 

                     In the case where the set of End CC recovered PVCs 
                     contains both successive and singled out PVCs, 
                     both sets of objects will be used."
    ::= { ciscoATMPVCTRAPExtnCapability 9 }

        VARIATION catmIntfPvcAISRDIOAMRecoverTrap  -- TRAP-TYPE
--              OBJECTS { ifIndex,
--                        catmIntfAISRDIOAMRcovedPVcls,
--                        catmIntfCurAISRDIOAMRcovingPVcls,
--                        atmVclVpi,
--                        atmVclVci,
--                        catmPVclAISRDIStatusUpTransition,
--                        catmPVclAISRDIStatusUpStart,
--                        catmPVclAISRDIStatusUpEnd,
--                        catmStatusChangePVclRangeIndex,
--                        catmPVclAISRDIUpLowerRangeValue,
--                        catmPVclAISRDIUpHigherRangeValue,
--                        catmPVclAISRDIRangeStatusUpStart,
--                        catmPVclAISRDIRangeStatusUpEnd }
        DESCRIPTION "A catmIntfPvcAISRDIOAMRecoverTrap signifies 
                     that the AIS/RDI F5 OAM recovery is detected 
                     on the PVC in the last PVC TRAP notification 
                     interval. 

                     If the set of AIS/RDI recovered PVCs contains 
                     successive VCIs, then the varbinds sent in this 
                     TRAP contains information about ranges 
                     representing these groups of PVCs. In this
                     case, the atmVclVpi,
                     catmStatusChangePVclRangeIndex, 
                     catmPVclAISRDIUpLowerRangeValue, 
                     catmPVclAISRDIUpHigherRangeValue, 
                     catmPVclAISRDIRangeStatusUpStart, 
                     catmPVclAISRDIRangeStatusUpEnd are used. 

                     If the set of AIS/RDI recovered PVCs contains 
                     singled out PVCs (i.e. PVC with VPI1, VCI1 is 
                     contained in the set; but neither a PVC with VPI1 
                     and VCI1 - 1 nor a PVC with VPI1 and VCI1 + 1 is 
                     contained in the set of AIS/RDI recovered PVCs) 
                     then the varbinds sent in this notification
                     contains information about the individual PVCs.
                     In this case, the atmVclVpi, atmVclVci, 
                     catmPVclAISRDIStatusUpTransition, 
                     catmPVclAISRDIStatusUpStart, 
                     catmPVclAISRDIStatusUpEnd will be used. 

                     In the case where the set of AIS/RDI recovered 
                     PVCs contains both successive and singled out
                     PVCs, both sets of objects will be used."
    ::= { ciscoATMPVCTRAPExtnCapability 10 }

        VARIATION catmIntfPvcAnyOAMRecoverTrap  -- TRAP-TYPE
--              OBJECTS { ifIndex,
--                        catmIntfAnyOAMRcovedPVcls,
--                        catmIntfCurAnyOAMRcovingPVcls,
--                        catmIntfTypeOfOAMRecover,
--                        atmVclVpi,
--                        atmVclVci,
--                        catmPVclStatusUpTransition,
--                        catmPVclStatusUpStart,
--                        catmPVclStatusUpEnd,
--                        catmStatusChangePVclRangeIndex,
--                        catmPVclUpLowerRangeValue,
--                        catmPVclUpHigherRangeValue,
--                        catmPVclRangeStatusUpStart,
--                        catmPVclRangeStatusUpEnd,
--                        catmPVclSegCCStatusUpTransition,
--                        catmPVclSegCCStatusUpStart,
--                        catmPVclSegCCStatusUpEnd,
--                        catmStatusChangePVclRangeIndex,
--                        catmPVclSegCCUpLowerRangeValue,
--                        catmPVclSegCCUpHigherRangeValue,
--                        catmPVclSegCCRangeStatusUpStart,
--                        catmPVclSegCCRangeStatusUpEnd,
--                        catmPVclEndCCStatusUpTransition,
--                        catmPVclEndCCStatusUpStart,
--                        catmPVclEndCCStatusUpEnd,
--                        catmStatusChangePVclRangeIndex,
--                        catmPVclEndCCUpLowerRangeValue,
--                        catmPVclEndCCUpHigherRangeValue,
--                        catmPVclEndCCRangeStatusUpStart,
--                        catmPVclEndCCRangeStatusUpEnd,
--                        catmPVclAISRDIStatusUpTransition,
--                        catmPVclAISRDIStatusUpStart,
--                        catmPVclAISRDIStatusUpEnd,
--                        catmStatusChangePVclRangeIndex,
--                        catmPVclAISRDIUpLowerRangeValue,
--                        catmPVclAISRDIUpHigherRangeValue,
--                        catmPVclAISRDIRangeStatusUpStart,
--                        catmPVclAISRDIRangeStatusUpEnd }
        DESCRIPTION "A catmIntfPvcAnyOAMRecoverTrap signifies that the
                     one or more type of F5 OAM recovery is detected on 
                     the PVC in the last PVC TRAP notification 
                     interval. 
                     The type of F5 OAM recovery can be 
                     Loopback F5 OAM recovery,
                     Segment CC F5 OAM recovery,
                     End CC F5 OAM recovery,
                     AIS/RDI F5 OAM recovery.

                     If the set of loopback recovered PVCs contains 
                     successive VCIs, then the varbinds sent in this 
                     TRAP contains information about ranges 
                     representing these groups of PVCs. In this
                     case, the atmVclVpi,
                     catmStatusChangePVclRangeIndex, 
                     catmPVclUpLowerRangeValue,
                     catmPVclUpHigherRangeValue,
                     catmPVclRangeStatusUpStart,
                     catmPVclRangeStatusUpEnd are used.

                     If the set of loopback recovered PVCs contains 
                     singled out PVCs (i.e. PVC with VPI1, VCI1 is 
                     contained in the set; but neither a PVC with VPI1 
                     and VCI1 - 1 nor a PVC with VPI1 and VCI1 + 1 is 
                     contained in the set of loopback recovered PVCs) 
                     then the varbinds sent in this notification
                     contains information about the individual PVCs.
                     In this case, the atmVclVpi, atmVclVci, 
                     catmPVclStatusUpTransition,
                     catmPVclStatusUpStart,
                     catmPVclStatusUpEnd will be used.

                     In the case where the set of loopback recovered 
                     PVCs contains both successive and singled out PVCs 
                     both sets of objects will be used.

                     If the set of segment CC recovered PVCs contains 
                     successive VCIs, then the varbinds sent in this 
                     TRAP contains information about ranges 
                     representing these groups of PVCs. In this
                     case, the atmVclVpi,
                     catmStatusChangePVclRangeIndex, 
                     catmPVclSegCCUpLowerRangeValue,
                     catmPVclSegCCUpHigherRangeValue,
                     catmPVclSegCCRangeStatusUpStart,
                     catmPVclSegCCRangeStatusUpEnd are used.

                     If the set of segment CC recovered PVCs contains 
                     singled out PVCs (i.e. PVC with VPI1, VCI1 is 
                     contained in the set; but neither a PVC with VPI1 
                     and VCI1 - 1 nor a PVC with VPI1 and VCI1 + 1 is 
                     contained in the set of segment CC recovered PVCs) 
                     then the varbinds sent in this notification
                     contains information about the individual PVCs.
                     In this case, the atmVclVpi, atmVclVci, 
                     catmPVclSegCCStatusUpTransition,
                     catmPVclSegCCStatusUpStart,
                     catmPVclSegCCStatusUpEnd will be used.

                     In the case where the set of segment CC recovered 
                     PVCs contains both successive and singled out 
                     PVCs, both sets of objects will be used.

                     If the set of End CC recovered PVCs contains 
                     successive VCIs, then the varbinds sent in this 
                     TRAP contains information about ranges 
                     representing these groups of PVCs. In this
                     case, the atmVclVpi,
                     catmStatusChangePVclRangeIndex, 
                     catmPVclEndCCUpLowerRangeValue,
                     catmPVclEndCCUpHigherRangeValue,
                     catmPVclEndCCRangeStatusUpStart,
                     catmPVclEndCCRangeStatusUpEnd are used.

                     If the set of End CC recovered PVCs contains 
                     singled out PVCs (i.e. PVC with VPI1, VCI1 is 
                     contained in the set; but neither a PVC with VPI1 
                     and VCI1 - 1 nor a PVC with VPI1 and VCI1 + 1 is 
                     contained in the set of End CC recovered PVCs) 
                     then the varbinds sent in this notification
                     contains information about the individual PVCs.
                     In this case, the atmVclVpi, atmVclVci, 
                     catmPVclEndCCStatusUpTransition,
                     catmPVclEndCCStatusUpStart,
                     catmPVclEndCCStatusUpEnd will be used.

                     In the case where the set of End CC recovered PVCs 
                     contains both successive and singled out PVCs, 
                     both sets of objects will be used.

                     If the set of AIS/RDI recovered PVCs contains 
                     successive VCIs, then the varbinds sent in this 
                     TRAP contains information about ranges 
                     representing these groups of PVCs. In this
                     case, the atmVclVpi,
                     catmStatusChangePVclRangeIndex, 
                     catmPVclAISRDIUpLowerRangeValue,
                     catmPVclAISRDIUpHigherRangeValue,
                     catmPVclAISRDIRangeStatusUpStart,
                     catmPVclAISRDIRangeStatusUpEnd are used.

                     If the set of AIS/RDI recovered PVCs contains 
                     singled out PVCs (i.e. PVC with VPI1, VCI1 is 
                     contained in the set; but neither a PVC with VPI1 
                     and VCI1 - 1 nor a PVC with VPI1 and VCI1 + 1 is 
                     contained in the set of AIS/RDI recovered PVCs) 
                     then the varbinds sent in this notification
                     contains information about the individual PVCs.
                     In this case, the atmVclVpi, atmVclVci, 
                     catmPVclAISRDIStatusUpTransition,
                     catmPVclAISRDIStatusUpStart,
                     catmPVclAISRDIStatusUpEnd will be used.

                     In the case where the set of AIS/RDI recovered 
                     PVCs contains both successive and singled out 
                     PVCs, both sets of objects will be used."
    ::= { ciscoATMPVCTRAPExtnCapability 11 }

        VARIATION catmIntfPvcUp2Trap  -- TRAP-TYPE
--              OBJECTS { ifIndex,
--                        catmIntfCurrentlyDownToUpPVcls,
--                        atmVclVpi,
--                        atmVclVci,
--                        catmPVclCurRecoverTime,
--                        catmPVclPrevFailTime,
--                        catmPVclRecoveryReason,
--                        catmStatusChangePVclRangeIndex,
--                        catmUpPVclLowerRangeValue,
--                        catmUpPVclHigherRangeValue,
--                        catmUpPVclRangeStart,
--                        catmUpPVclRangeEnd,
--                        catmPrevDownPVclRangeStart,
--                        catmPrevDownPVclRangeEnd,
--                        catmPVclRangeRecoveryReason }
        DESCRIPTION "A catmIntfPvcUp2Trap signifies that 
                     atmVclOperStatus is detected as up on the PVC in
                     the last PVC TRAP notification interval. 

                     If the set of atmVclOperStatus up PVCs contains 
                     successive VCIs, then the varbinds sent in this 
                     TRAP contains information about ranges 
                     representing these groups of PVCs. In this
                     case, the atmVclVpi,
                     catmStatusChangePVclRangeIndex, 
                     catmUpPVclLowerRangeValue, 
                     catmUpPVclHigherRangeValue, 
                     catmUpPVclRangeStart, 
                     catmUpPVclRangeEnd,
                     catmPrevDownPVclRangeStart,
                     catmPrevDownPVclRangeEnd,
                     catmPVclRangeRecoveryReason are used. 

                     If the set of atmVclOperStatus up PVCs contains 
                     singled out PVCs (i.e. PVC with VPI1, VCI1 is 
                     contained in the set; but neither a PVC with VPI1 
                     and VCI1 - 1 nor a PVC with VPI1 and VCI1 + 1 is 
                     contained in the set of atmVclOperStatus 
                     UP PVCs) then the varbinds sent in this 
                     notification contains information about the 
                     individual PVCs. In this case, the atmVclVpi, 
                     atmVclVci, catmPVclCurRecoverTime,
                     catmPVclPrevFailTime,
                     catmPVclRecoveryReason will be used. 

                     In the case where the set of atmVclOperStatus
                     up PVCs contains both successive and singled
                     out PVCs, both sets of objects will be used."
    ::= { ciscoATMPVCTRAPExtnCapability 12 }

        VARIATION catmIntfPvcDownTrap  -- TRAP-TYPE
--              OBJECTS { ifIndex,
--                        atmIntfPvcFailures,
--                        atmIntfCurrentlyFailingPVcls,
--                        atmVclVpi,
--                        atmVclVci,
--                        catmPVclCurFailTime,
--                        catmPVclPrevRecoverTime,
--                        catmPVclFailureReason,
--                        catmStatusChangePVclRangeIndex,
--                        catmDownPVclLowerRangeValue,
--                        catmDownPVclHigherRangeValue,
--                        catmDownPVclRangeStart,
--                        catmDownPVclRangeEnd,
--                        catmPrevUpPVclRangeStart,
--                        catmPrevUpPVclRangeEnd,
--                        catmPVclRangeFailureReason }
        DESCRIPTION "A catmIntfPvcDownTrap signifies 
                     atmVclOperStatus is detected as down on the PVC in
                     the last PVC TRAP notification interval. 

                     If the set of atmVclOperStatus down PVCs contains 
                     successive VCIs, then the varbinds sent in this 
                     TRAP contains information about ranges 
                     representing these groups of PVCs. In this
                     case, the atmVclVpi,
                     catmStatusChangePVclRangeIndex, 
                     catmDownPVclLowerRangeValue,
                     catmDownPVclHigherRangeValue,
                     catmDownPVclRangeStart,
                     catmDownPVclRangeEnd,
                     catmPrevUpPVclRangeStart,
                     catmPrevUpPVclRangeEnd,
                     catmPVclRangeFailureReason are used. 

                     If the set of atmVclOperStatus down PVCs contains 
                     singled out PVCs (i.e. PVC with VPI1, VCI1 is 
                     contained in the set; but neither a PVC with VPI1 
                     and VCI1 - 1 nor a PVC with VPI1 and VCI1 + 1 is 
                     contained in the set of atmVclOperStatus 
                     down PVCs) then the varbinds sent in this 
                     notification contains information about the 
                     individual PVCs. In this case, the atmVclVpi, 
                     atmVclVci, catmPVclCurFailTime,
                     catmPVclPrevRecoverTime,
                     catmPVclFailureReason will be used. 

                     In the case where the set of atmVclOperStatus
                     down PVCs contains both successive and singled
                     out PVCs, both sets of objects will be used."
    ::= { ciscoATMPVCTRAPExtnCapability 13 }

END
