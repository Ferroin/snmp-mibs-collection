CISCO-ATM-IF-MIB DEFINITIONS ::= BEGIN

IMPORTS
    MODULE-IDENTITY, 
    Counter32,
    Gauge32,
    Integer32,
    NOTIFICATION-TYPE,
    OBJECT-TYPE                      FROM SNMPv2-SMI
    atmInterfaceConfEntry            FROM ATM-MIB        -- RFC 1695
    TEXTUAL-CONVENTION, TruthValue   FROM SNMPv2-TC
    MODULE-COMPLIANCE, OBJECT-GROUP, NOTIFICATION-GROUP
                                     FROM SNMPv2-CONF
    ciscoExperiment                  FROM CISCO-SMI;

ciscoAtmIfMIB   MODULE-IDENTITY
     LAST-UPDATED       "200202130000Z"
     ORGANIZATION       "Cisco Systems, Inc."
     CONTACT-INFO
                "       Cisco Systems
                        Customer Service

                Postal: 170 W Tasman Drive
                        San Jose, CA  95134
                        USA

                Tel: +1 800 553-NETS

                E-mail: cs-atm@cisco.com"
    DESCRIPTION
            "A MIB module for an ATM interface configuration."
    REVISION        "200202130000Z" 
    DESCRIPTION
            "Deprecated ciscoAtmIfSvcMinVci in favor of object 
             ciscoatmInterfaceConfMinSvccVcc with greater 
             capability in the CISCO-ATM2-MIB.

             Added a notification object to send out a trap
             when ILMI or SSCOP changes state. Also adding an
             object to enable or disable this notification."
    REVISION        "200108080000Z" 
    DESCRIPTION
            "Added enum aini for the object ciscoAtmIfType."
    REVISION        "200105210000Z"
    DESCRIPTION
            "Add new per-service category SVC UPC Intent objects
             ciscoAtmIfSvcUpcIntentCbr, ciscoAtmIfSvcUpcIntentVbrRt,
             ciscoAtmIfSvcUpcIntentVbrNrt, ciscoAtmIfSvcUpcIntentAbr,
             ciscoAtmIfSvcUpcIntentUbr. Deprecate the old per-interface 
             SVC UPC intent object ciscoAtmIfSvcUpcIntent."
    REVISION        "200004110000Z"
    DESCRIPTION
            "Added 
             o A collection of objects that count UPC violations
               and number of cells discarded due to various
               conditions on ATM interfaces.
             o Added ILMI state and SSCOP state monitoring 
               variables.
             o Fixed the lines in DESCRIPTION section for 
               various objects that failed the line length check 
               by mib-police.
             o Introduced a new Group object to obsolete 
               ciscoAtmIfMIBGroup3 as it contained objects with
               incompatible status."
    REVISION        "9903110000Z"
    DESCRIPTION
            "Clarified the description of SVC UPC Intent object that
             it is defined for logical ATM interfaces too." 
    REVISION        "9711300000Z"
    DESCRIPTION
            "Added 
             ciscoAtmIfConfigAESA
             ciscoAtmIfDerivedAESA
             ciscoAtmIfE164Address
             ciscoAtmIfE164AutoConversionOnly
             objects."
    REVISION        "9709100000Z"
    DESCRIPTION
            "Updated description of ciscoAtmIfSignallingAdminStatus
             object. Restriction that the object value be modified
             only when the ifAdminStatus is down has been removed."
    REVISION        "9611010000Z"
    DESCRIPTION
            "Added Nsap Address and Well Known VC configuration 
             variables."
    REVISION        "9610140000Z"
    DESCRIPTION
            "Added SVC UPC intent configuration variable."
    ::= { ciscoExperiment 14 }    -- assigned by cana@cisco.com

ciscoAtmIfMIBObjects OBJECT IDENTIFIER ::= { ciscoAtmIfMIB 1 }

NsapAtmAddr ::= TEXTUAL-CONVENTION
        STATUS  current
        DESCRIPTION
        "The ATM address used by the network entity.  The
        address types are NSAP (20 octets)."
        SYNTAX    OCTET STRING (SIZE(20))

-- temp: copied from the ATM-TC-MIB
AtmAddr ::= TEXTUAL-CONVENTION
    STATUS  current
    DESCRIPTION
                "The ATM address used by the network entity.  The
                address types are: no address (0 octets), E.164 (8
                octets), network prefix (13 octets), and NSAP (20
                octets).  Note: The E.164 address is encoded in
                BCD format."
SYNTAX    OCTET STRING (SIZE(0|8|13|20))

UpcMethod ::= TEXTUAL-CONVENTION
        STATUS    current
        DESCRIPTION
        "A textual convention defining options for Usage Parameter 
         Control:
         passing : take no action on cells considered to violate the 
                   traffic contract.
         tagging : set the CLP bit in the header of cells considered
                   to violate the traffic contract.
         dropping: discard cells considered to violate the traffic 
                   contract."
        SYNTAX    INTEGER  {
                passing(1),
                tagging(2),
                dropping(3)
                }

-- This group is an ATM switch specific configuration
-- information 

ciscoAtmIfIlmiAccessGlobalDefaultFilter  OBJECT-TYPE
    SYNTAX       INTEGER {
                 permitAll(1),
                 permitPrefix(2),
                 permitPrefixAndWellknownGroups(3),
                 permitPrefixAndAllGroups(4)
    }
    MAX-ACCESS   read-write
    STATUS       current
    DESCRIPTION
        "The global default access filter which set the per-switch
         default access filter for ILMI address registration 
         on all interfaces.
         permitAll - This permits all ILMI registered addresses.
         permitPrefix - The address being registered by ILMI
         should have their prefix portion of the address match
         the ILMI prefixes used on this interface.  If there
         are any per-interface ILMI address prefixes
         configured, then the prefixes derived from the
         switch addresses are not considered ILMI prefixes for
         this interface.
         permitPrefixAndWellknownGroups - This is same as
         'permitPrefix' but in addition it also allows the
         well-known group addresses.  The well-known group
         addresses will be the old LECS address and any address
         matching the ATM Forum address prefix for well known
         addresses.
         (i.e.,C5.0079.0000.0000.0000.0000.0000.00A03E)
         permitPrefixAndAllGroups - This is same 
         as 'permitPrefix' but in addition it allows all 
         group addresses."
      DEFVAL { permitAll }
    ::= { ciscoAtmIfMIBObjects 2 }

ciscoAtmIfNotifsEnabled OBJECT-TYPE
    SYNTAX        TruthValue
    MAX-ACCESS    read-write
    STATUS        current
    DESCRIPTION
               "Allows enabling/disabling of notifications for ATM
                Interface events"
    DEFVAL { false } 
    ::= { ciscoAtmIfMIBObjects 3 }

-- This group is an ATM interface specific configuration
-- information 

ciscoAtmIfTable OBJECT-TYPE
    SYNTAX     SEQUENCE OF CiscoAtmIfEntry
    MAX-ACCESS not-accessible
    STATUS     current
    DESCRIPTION
       "This table contains ATM local interface configuration 
       parameters, one entry per ATM interface port."
    ::= { ciscoAtmIfMIBObjects 1 }

ciscoAtmIfEntry OBJECT-TYPE
    SYNTAX     CiscoAtmIfEntry
    MAX-ACCESS not-accessible
    STATUS     current
    DESCRIPTION
        " This list conatins additonal ATM interface configuration
          parameters and state variables."
    AUGMENTS { atmInterfaceConfEntry }
    ::= { ciscoAtmIfTable 1 }

CiscoAtmIfEntry ::=
    SEQUENCE {
        ciscoAtmIfType                       INTEGER,
        ciscoAtmIfSide                       INTEGER,
        ciscoAtmIfUniType                    INTEGER,
        ciscoAtmIfPVPs                       Integer32,
        ciscoAtmIfPVCs                       Integer32,
        ciscoAtmIfActiveSVPs                 Gauge32,
        ciscoAtmIfActiveSVCs                 Gauge32,
        ciscoAtmIfTotalConnections           Gauge32,
        ciscoAtmIfConfVplIf                  Integer32,
        ciscoAtmIfPortType                   INTEGER,
        ciscoAtmIfXmitLed                    INTEGER,
        ciscoAtmIfRecvLed                    INTEGER,
        ciscoAtmIfXmitCells                  Counter32,
        ciscoAtmIfRecvCells                  Counter32,
        ciscoAtmIfSvcMinVci                  INTEGER,
        ciscoAtmIfIlmiConfiguration          INTEGER,
        ciscoAtmIfIlmiAddressRegistration    INTEGER,
        ciscoAtmIfIlmiAutoConfiguration      INTEGER,
        ciscoAtmIfIlmiKeepAlive              Integer32,
        ciscoAtmIfSoftVcDestAddress          NsapAtmAddr,
        ciscoAtmIfUniSignallingVersion       INTEGER,
        ciscoAtmIfSvcUpcIntent               INTEGER,
        ciscoAtmIfAddressType                INTEGER,
        ciscoAtmIfAddress                    OCTET STRING,
        ciscoAtmIfWellKnownVcMode            INTEGER,
        ciscoAtmIfSignallingAdminStatus      INTEGER,
        ciscoAtmIfCdLed                      INTEGER,
        ciscoAtmIfIlmiAccessFilter           INTEGER,
        ciscoAtmIfConfigAESA                 OCTET STRING,
        ciscoAtmIfDerivedAESA                AtmAddr,
        ciscoAtmIfE164Address                AtmAddr,
        ciscoAtmIfE164AutoConversionOnly     TruthValue,
        ciscoAtmIfRxCellUpcViolations        Counter32,
        ciscoAtmIfRxCellDiscards             Counter32,
        ciscoAtmIfIlmiFSMState               INTEGER,
        ciscoAtmIfIlmiUpDownChanges          Counter32,
        ciscoAtmIfSscopFSMState              INTEGER,
        ciscoAtmIfSscopUpDownChanges         Counter32,
        ciscoAtmIfSvcUpcIntentCbr            UpcMethod,
        ciscoAtmIfSvcUpcIntentVbrRt          UpcMethod,
        ciscoAtmIfSvcUpcIntentVbrNrt         UpcMethod,
        ciscoAtmIfSvcUpcIntentAbr            UpcMethod,
        ciscoAtmIfSvcUpcIntentUbr            UpcMethod
            }

ciscoAtmIfType    OBJECT-TYPE
           SYNTAX       INTEGER {
                        other(1),
                        uni(2),
                        pnni(3),
                        iisp(4),
                        nniPvcOnly(5),
                        aini(6)
           }
           MAX-ACCESS   read-write
           STATUS       current
           DESCRIPTION
               "The type of ATM interface which is either a UNI 
                (User to Network), PNNI, IISP or NNI PVC only.
                To modify the ciscoAtmIftype, ifAdminStatus has 
                to be down and atmIfIlmiAutoConfiguration disabled."
           DEFVAL {uni}
           ::= { ciscoAtmIfEntry 1 }

ciscoAtmIfSide    OBJECT-TYPE
           SYNTAX       INTEGER {
                        user(1),
                        network(2),
                        notApplicable(3)
           }
           MAX-ACCESS   read-write
           STATUS       current
           DESCRIPTION
               "The side of ATM interface which is either a user or 
               network side.NotApplicable value implies that 
               ciscoAtmIftype is other than uni or iisp."
           DEFVAL {network}
           ::= { ciscoAtmIfEntry 2 }

ciscoAtmIfUniType    OBJECT-TYPE
           SYNTAX       INTEGER {
                        public(1),
                        private(2)
           }
           MAX-ACCESS   read-write
           STATUS       current
           DESCRIPTION
                "The type of User to Network interface is either 
                private or public. If ciscoAtmIfType is not uni
                then ciscoAtmIfUniType value should be ignored."
           DEFVAL {private}
           ::= { ciscoAtmIfEntry 3 }

ciscoAtmIfPVPs    OBJECT-TYPE
           SYNTAX       Integer32 (0..255)
           MAX-ACCESS   read-only
           STATUS       current
           DESCRIPTION
                "The number of permanent virtual paths at this 
                 interface."
           ::= { ciscoAtmIfEntry 4 }

ciscoAtmIfPVCs    OBJECT-TYPE
           SYNTAX       Integer32 (0..65535)
           MAX-ACCESS   read-only
           STATUS       current
           DESCRIPTION
                "The number of permanent virtual channels at this 
                 interface."
           ::= { ciscoAtmIfEntry 5 }

ciscoAtmIfActiveSVPs    OBJECT-TYPE
           SYNTAX       Gauge32
           MAX-ACCESS   read-only
           STATUS       current
           DESCRIPTION
               "The number of active switched virtual paths at 
               this interface."
           ::= { ciscoAtmIfEntry 6 }

ciscoAtmIfActiveSVCs    OBJECT-TYPE
           SYNTAX       Gauge32
           MAX-ACCESS   read-only
           STATUS       current
           DESCRIPTION
               "The number of active switched virtual channels at 
               this interface."
           ::= { ciscoAtmIfEntry 7 }

ciscoAtmIfTotalConnections    OBJECT-TYPE
           SYNTAX       Gauge32
           MAX-ACCESS   read-only
           STATUS       current
           DESCRIPTION
               "The total number of existing connections at 
               this interface."
           ::= { ciscoAtmIfEntry 8 }

ciscoAtmIfConfVplIf   OBJECT-TYPE
           SYNTAX       Integer32 (0..65535)
           MAX-ACCESS   read-only
           STATUS       current
           DESCRIPTION
               "The number of configured VP interfaces at this physical 
                interface."
           ::= { ciscoAtmIfEntry 9 }

ciscoAtmIfPortType OBJECT-TYPE
                SYNTAX        INTEGER {
                               other(1),    -- none of the following
                               cpu(2),
                               ethernet(3),
                               oc3Utp(4),
                               oc3SingleModeFiber(5),
                               oc3MultiModeFiber(6),
                               oc12SingleModeFiber(7),
                               ds3(8),
                               e3(9),
                               ds1(10),
                               e1(11),
                               oc3Utp3(12),
                               oc3Utp5(13),
                               oc3SmIr(14),
                               oc3SmIrPlus(15),
                               oc3SmLr(16),
                               oc3Pof(17),
                               oc12MultiModeFiber(18),
                               oc12SmIr(19),
                               oc12SmIrPlus(20),
                               oc12SmLr(21),
                               oc12Pof(22),
                               oc12SmLr2(23),
                               oc12SmLr3(24),
                               atm25(25)
                               }
                MAX-ACCESS    read-only
                STATUS        current
                DESCRIPTION   
                     "The type of physical layer medium on the port."
                ::= { ciscoAtmIfEntry 10 }

ciscoAtmIfXmitLed OBJECT-TYPE
                SYNTAX        INTEGER {
                                off(1),      
                                steadyGreen(2),         
                                steadyYellow(3), 
                                steadyRed(4),
                                flashGreen(5),         
                                flashYellow(6), 
                                flashRed(7)  
                                }
                MAX-ACCESS    read-only
                STATUS        current
                DESCRIPTION   
                     "The transmit LED color of this port."
                ::= { ciscoAtmIfEntry 11 }

ciscoAtmIfRecvLed OBJECT-TYPE
                SYNTAX        INTEGER {
                                off(1),      
                                steadyGreen(2),         
                                steadyYellow(3), 
                                steadyRed(4),
                                flashGreen(5),         
                                flashYellow(6), 
                                flashRed(7)  
                                }
                MAX-ACCESS    read-only
                STATUS        current
                DESCRIPTION   
                     "The receive LED color of this port."
                ::= { ciscoAtmIfEntry 12 }

ciscoAtmIfXmitCells OBJECT-TYPE
                SYNTAX        Counter32
                MAX-ACCESS    read-only
                STATUS        current
                DESCRIPTION   
                     "The number of cells transmitted of this interface,
                      including p2p and p2mp cells."
                ::= { ciscoAtmIfEntry 13 }

ciscoAtmIfRecvCells OBJECT-TYPE
                SYNTAX        Counter32
                MAX-ACCESS    read-only
                STATUS        current
                DESCRIPTION   
                     "The number of cells received of this interface,
                      including p2p and p2mp cells."
                ::= { ciscoAtmIfEntry 14 }

ciscoAtmIfSvcMinVci    OBJECT-TYPE
           SYNTAX       INTEGER (0..255)
           MAX-ACCESS   read-only
           STATUS       deprecated 
           DESCRIPTION
               "The minimum of the range of values from which VCI's
                are assigned to new SVC connections. By this value
                being larger, more VCI's are reserved for setting up 
                PVCs. This applies to every VPI of the physical 
                interface and every logical port.

                The object is deprecated because it is recommended to
                use ciscoAtmInterfaceConfMinSvccVci of the 
                CISCO-ATM2-MIB which is meant for the same purpose."
           ::= { ciscoAtmIfEntry 15 }

ciscoAtmIfIlmiConfiguration   OBJECT-TYPE
           SYNTAX       INTEGER { enabled(1), disabled(2) }
           MAX-ACCESS   read-write
           STATUS       current
           DESCRIPTION
               "Enable/Disable ILMI configuration on this interface. 
                The configuration takes effect only on the next 
                interface restart. Disabling this object will also 
                disable atmIfIlmiAddressRegistration and 
                atmIfIlmiAutoConfiguration and atmIfIlmiKeepAlive"
           DEFVAL {disabled}
           ::= { ciscoAtmIfEntry 16 }

ciscoAtmIfIlmiAddressRegistration   OBJECT-TYPE
           SYNTAX       INTEGER { enabled(1), disabled(2) }
           MAX-ACCESS   read-write
           STATUS       current
           DESCRIPTION
               "Enable/Disable ILMI Address Registration on on 
               this interface. The configuration  takes effect only 
               on the next interface restart."
           DEFVAL {disabled}
           ::= { ciscoAtmIfEntry 17 }

ciscoAtmIfIlmiAutoConfiguration    OBJECT-TYPE
           SYNTAX       INTEGER { enabled(1), disabled(2) }
           MAX-ACCESS   read-write
           STATUS       current
           DESCRIPTION
               "Enable/Disable ILMI link and interface type 
               determination. The configuration  takes effect only on 
               the next interface restart."
           DEFVAL {disabled}
           ::= { ciscoAtmIfEntry 18 }

ciscoAtmIfIlmiKeepAlive  OBJECT-TYPE
           SYNTAX       Integer32 (0..65535)
           UNITS        "seconds"
           MAX-ACCESS   read-write
           STATUS       current
           DESCRIPTION
               "The amount of time that should elapse between 
               successive ILMI keepalive messages sent on this 
               interface. A value of 0 disables ILMI keepalive messages 
               on this interface."
           DEFVAL {0}
           ::= { ciscoAtmIfEntry 19 }

ciscoAtmIfSoftVcDestAddress  OBJECT-TYPE
           SYNTAX       NsapAtmAddr
           MAX-ACCESS   read-only
           STATUS       current
           DESCRIPTION
               "The 20 byte ATM address of the destination ATM 
               interface for soft ATM PVC/PVP"
           ::= { ciscoAtmIfEntry 20 }

ciscoAtmIfUniSignallingVersion     OBJECT-TYPE
                 SYNTAX  INTEGER {
                          notApplicable(1),
                          atmfUni3Dot0(2),
                          atmfUni3Dot1(3),
                          atmfUni4Dot0(4)
                 }
                 MAX-ACCESS      read-write
                 STATUS          current
                 DESCRIPTION
                   "The version of UNI signalling that is currently 
                   being used on the interface. The appropriate 
                   value, either atmfUni3Dot0, atmfUni3Dot1 or 
                   atmfUni4Dot0, is used when the interface is
                   an UNI or IISP interface.  The value notApplicable 
                   is used when the interface is a PNNI interface or 
                   when signalling is disabled.  This may reflect a 
                   manually configured value for the signalling 
                   version, or may be determined by other means
                   such as auto-configuration.Setting this 
                   variable to a value of 'notApplicable' is not 
                   allowed. To modify the 
                   ciscoAtmIfUniSignallingVersion, ifAdminStatus 
                   has to be down and 
                   atmIfIlmiAutoConfiguration disabled."
           ::= { ciscoAtmIfEntry 21 }

ciscoAtmIfSvcUpcIntent OBJECT-TYPE
           SYNTAX           INTEGER {
                     passing(1),
                     tagging(2),
                     dropping(3)
                     }
           MAX-ACCESS       read-write
           STATUS           deprecated
           DESCRIPTION
           "Determines the policing (Usage Parameter Control or UPC) 
           action to take for SVCs established through this 
           interface. Values other than passing are allowed only if 
           policing is supported on the interface. Also serves to 
           determine UPC to use on the terminating (destination) 
           half-leg of Soft PVCs.
           This object has been deprecated in favor of the per-service
           category objects ciscoAtmIfSvcUpcIntentCbr, 
           ciscoAtmIfSvcUpcIntentVbrRt, ciscoAtmIfSvcUpcIntentVbrNrt,
           ciscoAtmIfSvcUpcIntentAbr, ciscoAtmIfSvcUpcIntentUbr. 
           Note that if those objects are set to different values, 
           the return value for this object cannot be correct." 
        DEFVAL { passing }
        ::= { ciscoAtmIfEntry 22 }

ciscoAtmIfAddressType  OBJECT-TYPE
           SYNTAX    INTEGER { nsap(1), esi(2), e164(3), null(4) }
           MAX-ACCESS   read-write
           STATUS       obsolete 
           DESCRIPTION
               "An indication of the type of the ATM
               addresses on this interface. To configure a new
               atm address, set ciscoAtmIfAddress to the 
               address, then set this object to ether nsap(1),
               or esi(2), or e164(3), depending on the type
               of address of ciscoAtmIfAddress.
               To delete the address, set this object to 
               null(4).

               Adding nsap address type to this interface has the effect
               of canceling the existing esi address, if there is one.
               Similarly, adding the esi address on this interface also
               has the effect of removing the existing nsap address.

               The value of ciscoAtmIfAddress has no effect when
               this object is set to null(4).

               For the switch, the nsap/esi address can only exist on 
               the cpu port for signalling applications."
           ::= { ciscoAtmIfEntry 23 }

ciscoAtmIfAddress  OBJECT-TYPE
           SYNTAX       OCTET STRING (SIZE(0|6|8|20))
           MAX-ACCESS   read-write
           STATUS       obsolete 
           DESCRIPTION
               "The ATM address of this interface, which
               can be either nsap, esi or e164.
               For the switch, the nsap/esi address can only 
               exist on the cpu port."
           ::= { ciscoAtmIfEntry 24 }

ciscoAtmIfWellKnownVcMode     OBJECT-TYPE
           SYNTAX  INTEGER {
                       -- the following two values are states:
                       -- these values may be read or written
                       automatic(1),
                       manual(2),
                       -- the following value is an action:
                       -- it may be written, but is never read
                       manualDeleteUponEntry(3)
           }
           MAX-ACCESS      read-write
           STATUS          current
           DESCRIPTION
           "Indicates whether well-known VCs should be 
           automatically or manually created for the 
           interface.

           In automatic(1) mode, well-known VCs will be 
           created with default VPI/VCI values upon startup or 
           upon entry to the automatic mode.  While in this 
           mode, well-known VCs will not be allowed to be 
           deleted or modified by user commands. This is 
           the default mode at startup for equipment which 
           supports automatic well-known VC creation.

           In manual(2) mode, well-known VCs won't be 
           automatically created.  Instead, the user will be 
           allowed to delete and create PVCs with the 
           reserved encapsulation types aalQsAal, aal5Ilmi, 
           and aal5Pnni as applicable.  And 
           these PVCs will be allowed to have VCI values 
           in the range <5-16383>, instead of <32-16383>.  

           The manualDeleteUponEntry(3) action causes 
           any existing VCs with reserved encapsulation 
           types (aalQsAal, aal5Ilmi or aal5Pnni) to be 
           deleted for this interface as it enters
           the manual state."
           DEFVAL {automatic}
           ::= { ciscoAtmIfEntry 31 }

ciscoAtmIfSignallingAdminStatus OBJECT-TYPE
           SYNTAX       INTEGER {enabled(1), disabled(2)}
           MAX-ACCESS   read-write
           STATUS       current
           DESCRIPTION
           "Enable/Disable signalling/sscop on this interface.The 
            disabled(2) action causes all the active SVCs on 
            this interface to be cleared."
           DEFVAL {enabled}
            ::= {ciscoAtmIfEntry 32}

ciscoAtmIfCdLed OBJECT-TYPE
                SYNTAX        INTEGER {
                                off(1),      
                                steadyGreen(2)         
                                }
                MAX-ACCESS    read-only
                STATUS        current
                DESCRIPTION   
                     "The Cd LED color of this port."
                ::= { ciscoAtmIfEntry 33 }

ciscoAtmIfIlmiAccessFilter OBJECT-TYPE
           SYNTAX       INTEGER {
                        permitAll(1),
                        permitPrefix(2),
                        permitPrefixAndWellknownGroups(3),
                        permitPrefixAndAllGroups(4),
                        useGlobalDefaultFilter(5)
           }
           MAX-ACCESS   read-write
           STATUS       current
           DESCRIPTION
               "The access filter which allows or denies certain 
                ILMI registered addresses on this interface when 
                ciscoAtmIfIlmiAddressRegistration is set to enable(1).
                permitAll - This permits all ILMI registered addresses.
                permitPrefix - The address being registered by ILMI
                should have their prefix portion of the address match
                the ILMI prefixes used on this interface.  If there
                are any per-interface ILMI address prefixes
                configured, then the prefixes derived from the
                switch addresses are not considered ILMI prefixes for
                this interface.
                permitPrefixAndWellknownGroups - This is same as
                'permitPrefix' but in addition it also allows the
                well-known group addresses.  The well-known group
                addresses will be the old LECS address and any address
                matching the ATM Forum address prefix for well known
                addresses.
                (i.e.,C5.0079.0000.0000.0000.0000.0000.00A03E)
                permitPrefixAndAllGroups - This is same 
                as 'permitPrefix' but in addition it allows all 
                group addresses.
                useGlobalDefaultFilter - It indicates that this 
                interface uses the per-switch global default 
                filter"
           DEFVAL { useGlobalDefaultFilter }
           ::= { ciscoAtmIfEntry 34 }

ciscoAtmIfConfigAESA OBJECT-TYPE
    SYNTAX      OCTET STRING (SIZE(0|7|20))
    MAX-ACCESS  read-write
    STATUS      current
    DESCRIPTION
               "The ATM End System Address (AESA) of this interface
               can be configured by entering the full 20 octet AESA, 
               or the 6 octet ESI and 1 octet Selector Byte. 
               If the ESI and Selector Byte are entered, the full AESA 
               will be formed using a 13 octet prefix from ILMI.
               The full AESA can be read using ciscoAtmIfDerivedAESA.
               A length of zero indicates that no AESA is configured.
               For the switch, the AESA address can only 
               exist on the cpu port."
           ::= { ciscoAtmIfEntry 35 }

ciscoAtmIfDerivedAESA OBJECT-TYPE
    SYNTAX      AtmAddr
    MAX-ACCESS  read-only
    STATUS      current
    DESCRIPTION
               "The ATM End System Address (AESA) of this interface.
               The AESA is configured using ciscoAtmIfConfigAESA
               or can be automatically generated.
               A length of zero indicates that no AESA is specified.
               For the switch, the AESA address can only 
               exist on the cpu port."
           ::= { ciscoAtmIfEntry 36 }

ciscoAtmIfE164Address OBJECT-TYPE
    SYNTAX      AtmAddr
    MAX-ACCESS  read-write
    STATUS      current
    DESCRIPTION
               "The ATM E164 address of this interface.
               When a native E.164 number is configured for this 
               inteface, only native E.164 numbers are 
               transmitted/received as the called/calling party 
               numbers. The presence of an ATM E164 address allows 
               both an algorithmic translation between the native E164 
               number and E164 AESA address formats (see 
               ciscoAtmIfE164AutoConversionOnly) and use of the ATM 
               E164 Address for the calling/called party number of 
               transmitted/received calls.  Entering an address will 
               disable ciscoAtmIfE164AutoConversionOnly. 
               An address of length zero indicates that no address is
               specified. 
               For the switch, the E164 address cannot 
               exist on the cpu port."
           ::= { ciscoAtmIfEntry 37 }

ciscoAtmIfE164AutoConversionOnly OBJECT-TYPE
    SYNTAX      TruthValue
    MAX-ACCESS  read-write
    STATUS      current
    DESCRIPTION
               "Enable/Disable E164 auto conversion only on this 
               interface.
               The E164 auto-conversion allows for algorithmic 
               translation between the native E164 number and E164
               AESA address formats.
               This object is used when there is no native E.164 
               number specified for this interface (see 
               ciscoAtmIfE164Address), to specify that only native 
               E.164 numbers are transmitted/received as the 
               called/calling party numbers and to enable/disable 
               E164 auto-conversion.
               For the switch, E164 auto-conversion cannot
               exist on the cpu port."
    ::= { ciscoAtmIfEntry 38 }

ciscoAtmIfRxCellUpcViolations OBJECT-TYPE
    SYNTAX        Counter32
    MAX-ACCESS    read-only
    STATUS        current
    DESCRIPTION
            "The total number of nonconforming cells detected by
             Usage Parameter Control (UPC) for cells received on
             this interface.  This object is not instantiated on 
             systems that do not have support for collecting such
             statistics."
    ::= { ciscoAtmIfEntry 39 }

ciscoAtmIfRxCellDiscards OBJECT-TYPE
    SYNTAX        Counter32
    MAX-ACCESS    read-only
    STATUS        current
    DESCRIPTION
             "The total number of cells that were discarded
              within the switch.  The cells can be discarded
              due to non conformance detected by Usage Parameter
              Control (UPC) or queue overflows within the switch.
              This object is not instantiated on systems that do 
              not have support for collecting such statistics."
    ::= { ciscoAtmIfEntry 40 }

ciscoAtmIfIlmiFSMState OBJECT-TYPE
    SYNTAX      INTEGER {
                down(1),
                restarting(2),
                waitDevType(3),
                deviceAndPortTypeComplete(4),
                awaitPnniConfig(5),
                pnniConfigComplete(6),
                awaitRestartAck(7),
                upAndNormal(8)
    }
    MAX-ACCESS  read-only
    STATUS      current
    DESCRIPTION
            "The ILMI states meaningful when the value of 
             ciscoAtmIfIlmiConfiguration indicates that the ILMI 
             is enabled for an ATM interface:
             down               -- Stopped or just booted or 
                                   interface down
             restarting         -- Establishing link connectivity
             waitDevType        -- Awaiting device type from peer
             deviceAndPortTypeComplete -- Determined device
                                          and/or port type
             awaitPnniConfig    -- Awaiting PNNI configuration
                                   from peer
             pnniConfigComplete -- Completed interface PNNI
                                   configuration
             awaitRestartAck    -- Awaiting peer range values
                                   after restart
             upAndNormal        -- Up and normal."
    ::= { ciscoAtmIfEntry 41 }

ciscoAtmIfIlmiUpDownChanges OBJECT-TYPE
    SYNTAX        Counter32
    MAX-ACCESS    read-only
    STATUS        current
    DESCRIPTION
            "The number of times ILMI enters and leaves
             the state of upAndNormal."
    ::= { ciscoAtmIfEntry 42 }

ciscoAtmIfSscopFSMState OBJECT-TYPE
    SYNTAX      INTEGER {
                idle(1),
                outgoingConnectionPending(2),
                incomingConnectionPending(3),
                dataTransferReady(4),
                outgoingDisconnectionPending(5),
                outgoingResyncPending(6),
                incomingResyncPending(7),
                outgoingRecoveryPending(8),
                incomingRecoveryPending(9),
                concurrentResyncPending(10)
    }
    MAX-ACCESS  read-only
    STATUS      current
    DESCRIPTION
               "The SSCOP state for an ATM interface as 
                defined by the ITU-T. The state is idle 
                when the interface is down or SSCOP is 
                not enabled on the ATM interface"
    REFERENCE
             "ITU-T Recommendation Q.2110 (07/94)"
    ::= { ciscoAtmIfEntry 43 }

ciscoAtmIfSscopUpDownChanges OBJECT-TYPE
    SYNTAX        Counter32
    MAX-ACCESS    read-only
    STATUS        current
    DESCRIPTION
               "The number of times SSCOP enters and leaves
                the state of DataTransferReady."
    ::= { ciscoAtmIfEntry 44 }

ciscoAtmIfSvcUpcIntentCbr OBJECT-TYPE
           SYNTAX           UpcMethod
           MAX-ACCESS       read-write
           STATUS           current
           DESCRIPTION
           "Determines the policing (Usage Parameter Control or UPC)
           action to take for Constant Bit Rate SVCs established 
           through this interface. Values other than passing are 
           allowed only if policing is supported on the interface. 
           Also serves to determine UPC to use on the terminating 
           (destination) half-leg of Soft PVCs."
        DEFVAL { passing }
        ::= { ciscoAtmIfEntry 45 }

ciscoAtmIfSvcUpcIntentVbrRt OBJECT-TYPE
           SYNTAX           UpcMethod
           MAX-ACCESS       read-write
           STATUS           current
           DESCRIPTION
           "Determines the policing (Usage Parameter Control or UPC)
           action to take for Variable Bit Rate - Real Time SVCs 
           established through this interface. Values other than 
           passing are allowed only if policing is supported on the 
           interface. Also serves to determine UPC to use on the 
           terminating (destination) half-leg of Soft PVCs."
        DEFVAL { passing }
        ::= { ciscoAtmIfEntry 46 }

ciscoAtmIfSvcUpcIntentVbrNrt OBJECT-TYPE
           SYNTAX           UpcMethod
           MAX-ACCESS       read-write
           STATUS           current
           DESCRIPTION
           "Determines the policing (Usage Parameter Control or UPC)
           action to take for Variable Bit Rate - Non Real Time SVCs 
           established through this interface. Values other than 
           passing are allowed only if policing is supported on the 
           interface. Also serves to determine UPC to use on the 
           terminating (destination) half-leg of Soft PVCs."
        DEFVAL { passing }
        ::= { ciscoAtmIfEntry 47 }

ciscoAtmIfSvcUpcIntentAbr OBJECT-TYPE
           SYNTAX           UpcMethod
           MAX-ACCESS       read-write
           STATUS           current
           DESCRIPTION
           "Determines the policing (Usage Parameter Control or UPC)
           action to take for Available Bit Rate SVCs established 
           through this interface. Values other than passing are 
           allowed only if policing is supported on the interface. 
           Also serves to determine UPC to use on the terminating 
           (destination) half-leg of Soft PVCs."
        DEFVAL { passing }
        ::= { ciscoAtmIfEntry 48 }

ciscoAtmIfSvcUpcIntentUbr OBJECT-TYPE
           SYNTAX           UpcMethod
           MAX-ACCESS       read-write
           STATUS           current
           DESCRIPTION
           "Determines the policing (Usage Parameter Control or UPC)
           action to take for Unspecified Bit Rate SVCs established 
           through this interface. Values other than passing are 
           allowed only if policing is supported on the interface. 
           Also serves to determine UPC to use on the terminating 
           (destination) half-leg of Soft PVCs."
        DEFVAL { passing }
        ::= { ciscoAtmIfEntry 49 }

ciscoAtmIfMIBNotifications OBJECT IDENTIFIER ::= { ciscoAtmIfMIB 0 } 

ciscoAtmIfEvent NOTIFICATION-TYPE
   OBJECTS {
       ciscoAtmIfIlmiFSMState,
       ciscoAtmIfSscopFSMState}
   STATUS current
   DESCRIPTION
       "This notification is generated when ever ILMI or SSCOP
        FSM state changes"
   ::= { ciscoAtmIfMIBNotifications 1 }

-- conformance information

ciscoAtmIfMIBConformance
              OBJECT IDENTIFIER ::= { ciscoAtmIfMIB 3 }
ciscoAtmIfMIBCompliances
              OBJECT IDENTIFIER ::= { ciscoAtmIfMIBConformance 1 }
ciscoAtmIfMIBGroups
              OBJECT IDENTIFIER ::= { ciscoAtmIfMIBConformance 2 }

-- compliance statements

ciscoAtmIfMIBCompliance MODULE-COMPLIANCE
    STATUS  obsolete -- superceded by ciscoAtmIfMIBCompliance2
    DESCRIPTION
            "The compliance statement for the Cisco ATM 
            interface  group."
    MODULE  -- this module
               MANDATORY-GROUPS { ciscoAtmIfMIBGroup }
    ::= { ciscoAtmIfMIBCompliances 1 }

ciscoAtmIfMIBCompliance2 MODULE-COMPLIANCE
    STATUS  obsolete -- superceded by ciscoAtmIfMIBCompliance3
    DESCRIPTION
            "The compliance statement for the Cisco ATM 
            interface  group."
    MODULE  -- this module
               MANDATORY-GROUPS { ciscoAtmIfMIBGroup,
                                  ciscoAtmIfMIBGroup2
                                }
    ::= { ciscoAtmIfMIBCompliances 2 }

ciscoAtmIfMIBCompliance3 MODULE-COMPLIANCE
    STATUS  obsolete -- superceded by ciscoAtmIfMIBCompliance4
    DESCRIPTION
            "The compliance statement for the Cisco ATM 
            interface group."
    MODULE  -- this module
               MANDATORY-GROUPS { ciscoAtmIfMIBGroup,
                                  ciscoAtmIfMIBGroup2,
                                  ciscoAtmIfMIBGroup3
                                }
    ::= { ciscoAtmIfMIBCompliances 3 }

ciscoAtmIfMIBCompliance4 MODULE-COMPLIANCE
    STATUS  obsolete
    DESCRIPTION
            "The compliance statement for the Cisco ATM 
            interface group."
    MODULE  -- this module
               MANDATORY-GROUPS { ciscoAtmIfMIBGroup,
                                  ciscoAtmIfMIBGroup2,
                                  ciscoAtmIfMIBGroup3,
                                  ciscoAtmIfMIBGroup4
                                }
    ::= { ciscoAtmIfMIBCompliances 4 }

ciscoAtmIfMIBCompliance5 MODULE-COMPLIANCE
    STATUS  obsolete
    DESCRIPTION
            "The compliance statement for the Cisco ATM 
            interface group."
    MODULE  -- this module
               MANDATORY-GROUPS { ciscoAtmIfMIBGroup,
                                  ciscoAtmIfMIBGroup2,
                                  ciscoAtmIfMIBGroup3,
                                  ciscoAtmIfMIBGroup4,
                                  ciscoAtmIfMIBGroup5
                                }
    ::= { ciscoAtmIfMIBCompliances 5 }

ciscoAtmIfMIBCompliance6 MODULE-COMPLIANCE
    STATUS obsolete -- superceded by ciscoAtmIfMIBCompliance7 
    DESCRIPTION
            "The compliance statement for the Cisco ATM 
            interface group."
    MODULE  -- this module
               MANDATORY-GROUPS { ciscoAtmIfMIBGroup,
                                  ciscoAtmIfMIBGroup2,
                                  ciscoAtmIfMIBGroup4,
                                  ciscoAtmIfMIBGroup5,
                                  ciscoAtmIfMIBGroup6,
                                  ciscoAtmIfMIBGroup7
                                }
    ::= { ciscoAtmIfMIBCompliances 6 }

ciscoAtmIfMIBCompliance7 MODULE-COMPLIANCE
    STATUS  deprecated 
    DESCRIPTION
            "The compliance statement for the Cisco ATM
            interface group."
    MODULE  -- this module
               MANDATORY-GROUPS { ciscoAtmIfMIBGroup,
                                  ciscoAtmIfMIBGroup4,
                                  ciscoAtmIfMIBGroup5,
                                  ciscoAtmIfMIBGroup6,
                                  ciscoAtmIfMIBGroup7,
                                  ciscoAtmIfMIBGroup8
                                }
    ::= { ciscoAtmIfMIBCompliances 7 }

ciscoAtmIfMIBCompliance8 MODULE-COMPLIANCE
    STATUS  current 
    DESCRIPTION
            "The compliance statement for the Cisco ATM
            interface group."
    MODULE  -- this module
               MANDATORY-GROUPS { ciscoAtmIfMIBGroup4,
                                  ciscoAtmIfMIBGroup5,
                                  ciscoAtmIfMIBGroup6,
                                  ciscoAtmIfMIBGroup7,
                                  ciscoAtmIfMIBGroup8,
                                  ciscoAtmIfMIBGroup9,
                                  ciscoAtmIfMIBGroup10,
                                  ciscoAtmIfNotifyGroup
                                }
    ::= { ciscoAtmIfMIBCompliances 8 }

-- units of conformance

ciscoAtmIfMIBGroup  OBJECT-GROUP
    OBJECTS {   ciscoAtmIfType, 
                ciscoAtmIfSide, 
                ciscoAtmIfUniType, 
                ciscoAtmIfPVPs,  
                ciscoAtmIfPVCs, 
                ciscoAtmIfActiveSVPs, 
                ciscoAtmIfActiveSVCs,
                ciscoAtmIfTotalConnections, 
                ciscoAtmIfConfVplIf,
                ciscoAtmIfPortType,
                ciscoAtmIfXmitLed,
                ciscoAtmIfRecvLed,
                ciscoAtmIfXmitCells,
                ciscoAtmIfRecvCells,
                ciscoAtmIfSvcMinVci,
                ciscoAtmIfIlmiConfiguration,
                ciscoAtmIfIlmiAddressRegistration,
                ciscoAtmIfIlmiAutoConfiguration,
                ciscoAtmIfIlmiKeepAlive,
                ciscoAtmIfSoftVcDestAddress,
                ciscoAtmIfCdLed
        }
    STATUS    deprecated 
    DESCRIPTION
        "A collection of objects providing the information 
        about ATM interface related information also an 
        ability to configure certain parameters of 
        ATM interface."
    ::= { ciscoAtmIfMIBGroups 1 }

ciscoAtmIfMIBGroup2  OBJECT-GROUP
    OBJECTS {   ciscoAtmIfUniSignallingVersion,
                ciscoAtmIfSvcUpcIntent
    }
    STATUS    deprecated
    DESCRIPTION
        "Additional collection of objects providing 
        ATM interface related information." 
    ::= { ciscoAtmIfMIBGroups 2 }

ciscoAtmIfMIBGroup3  OBJECT-GROUP
    OBJECTS {   ciscoAtmIfAddressType,
                ciscoAtmIfAddress,
                ciscoAtmIfWellKnownVcMode,
                ciscoAtmIfSignallingAdminStatus
        }
    STATUS    obsolete
    DESCRIPTION
    "Additional collection of objects providing ATM 
     interface related information."
    ::= { ciscoAtmIfMIBGroups 3 }

ciscoAtmIfMIBGroup4  OBJECT-GROUP
    OBJECTS {   ciscoAtmIfIlmiAccessGlobalDefaultFilter,
                ciscoAtmIfIlmiAccessFilter
        }
    STATUS    current
    DESCRIPTION
    "Additional collection of objects providing ATM 
     switch and interface related information on Access 
     Filter for ILMI Address Registration."
    ::= { ciscoAtmIfMIBGroups 4 }

ciscoAtmIfMIBGroup5  OBJECT-GROUP
    OBJECTS {   ciscoAtmIfConfigAESA,
                ciscoAtmIfDerivedAESA,
                ciscoAtmIfE164Address,
                ciscoAtmIfE164AutoConversionOnly
        }
    STATUS    current
    DESCRIPTION
    "Additional collection of objects providing ATM 
     switch and interface related information for ATM Addresses."
    ::= { ciscoAtmIfMIBGroups 5 }

ciscoAtmIfMIBGroup6  OBJECT-GROUP
    OBJECTS {   ciscoAtmIfWellKnownVcMode,
                ciscoAtmIfSignallingAdminStatus
        }
    STATUS    current
    DESCRIPTION
    "Additional collection of objects providing ATM 
     interface related information."
    ::= { ciscoAtmIfMIBGroups 6 }

ciscoAtmIfMIBGroup7  OBJECT-GROUP
    OBJECTS {   ciscoAtmIfRxCellUpcViolations,
                ciscoAtmIfRxCellDiscards,
                ciscoAtmIfIlmiFSMState,
                ciscoAtmIfIlmiUpDownChanges,
                ciscoAtmIfSscopFSMState,
                ciscoAtmIfSscopUpDownChanges
        }
    STATUS    current
    DESCRIPTION
    "Additional collection of objects providing ATM switch 
     interface Resource Manager, ILMI and Signalling related 
     information."
    ::= { ciscoAtmIfMIBGroups 7 }

ciscoAtmIfMIBGroup8  OBJECT-GROUP
    OBJECTS {   ciscoAtmIfUniSignallingVersion,
                ciscoAtmIfSvcUpcIntentCbr,
                ciscoAtmIfSvcUpcIntentVbrRt,
                ciscoAtmIfSvcUpcIntentVbrNrt,
                ciscoAtmIfSvcUpcIntentAbr,
                ciscoAtmIfSvcUpcIntentUbr
    }
    STATUS    current
    DESCRIPTION
        "Additional collection of objects providing
        ATM interface related information."
    ::= { ciscoAtmIfMIBGroups 8 }

ciscoAtmIfMIBGroup9  OBJECT-GROUP
    OBJECTS {   ciscoAtmIfType,
                ciscoAtmIfSide,
                ciscoAtmIfUniType,
                ciscoAtmIfPVPs,
                ciscoAtmIfPVCs,
                ciscoAtmIfActiveSVPs,
                ciscoAtmIfActiveSVCs,
                ciscoAtmIfTotalConnections,
                ciscoAtmIfConfVplIf,
                ciscoAtmIfPortType,
                ciscoAtmIfXmitLed,
                ciscoAtmIfRecvLed,
                ciscoAtmIfXmitCells,
                ciscoAtmIfRecvCells,
                ciscoAtmIfIlmiConfiguration,
                ciscoAtmIfIlmiAddressRegistration,
                ciscoAtmIfIlmiAutoConfiguration,
                ciscoAtmIfIlmiKeepAlive,
                ciscoAtmIfSoftVcDestAddress,
                ciscoAtmIfCdLed
        }
    STATUS    current
    DESCRIPTION
        "A collection of objects providing the information
        about ATM interface related information also an
        ability to configure certain parameters of
        ATM interface."
    ::= { ciscoAtmIfMIBGroups 9 }

ciscoAtmIfMIBGroup10  OBJECT-GROUP
    OBJECTS {   ciscoAtmIfNotifsEnabled
        }
    STATUS    current
    DESCRIPTION
    "Additional objects providing means to enable/disable
     notifications related to the interface ILMI and 
     SSCOP state"
    ::= { ciscoAtmIfMIBGroups 10 }

ciscoAtmIfNotifyGroup NOTIFICATION-GROUP
         NOTIFICATIONS { ciscoAtmIfEvent }
         STATUS current
         DESCRIPTION
             "Interface ILMI and SSCOP FSM notifications"
    ::= { ciscoAtmIfMIBGroups 11 }

END
