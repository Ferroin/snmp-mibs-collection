CISCO-RS-232-CAPABILITY DEFINITIONS ::= BEGIN

IMPORTS
	MODULE-IDENTITY
		FROM SNMPv2-SMI
	AGENT-CAPABILITIES
		FROM SNMPv2-CONF
	ciscoAgentCapability
		FROM CISCO-SMI;

ciscoRS232Capability MODULE-IDENTITY
		LAST-UPDATED	"200205160000Z"
		ORGANIZATION    "Cisco Systems, Inc."
		CONTACT-INFO
			"	Cisco Systems
				Customer Service

			Postal:	170 West Tasman Drive
				San Jose, CA  95134
				USA

			   Tel:	+1 800 553-NETS

			E-mail:	cs-snmp@cisco.com"
		DESCRIPTION
			"Agent capabilities for RS-232-MIB"
		REVISION	"200205160000Z"
		DESCRIPTION
			"Added ciscoRS232CapabilityV2R00
                         capability for MGX8850 and BPX SES
                         products." 
		REVISION	"9408180000Z"
		DESCRIPTION
			"Initial version of this MIB module."
	::= { ciscoAgentCapability 115 }

ciscoRS232CapabilityV10R02 AGENT-CAPABILITIES

PRODUCT-RELEASE "Cisco IOS 10.2"
STATUS		current
DESCRIPTION	"IOS 10.2 rs232 mib capabilities"

SUPPORTS	RS-232-MIB
INCLUDES	{ rs232Group, rs232AsyncGroup }
--		rs232SyncGroup and rs232SyncSDLCGroup are not supported

VARIATION	rs232PortType
SYNTAX		INTEGER { rs232(2) }
-- no		 { other(1), rs422(3), rs423(4), v35(5), 
--		    x21(6) }
DESCRIPTION	"Unable to detect all states"

VARIATION	rs232PortInFlowType
SYNTAX		INTEGER { none(1), ctsRts(2) }
-- no		 { dsrDtr(3) }
DESCRIPTION	"Unable to detect all states"

VARIATION	rs232PortOutFlowType
SYNTAX		INTEGER { none(1), ctsRts(2) }
-- no		 { dsrDtr(3) }
DESCRIPTION	"Unable to detect all states"

VARIATION	rs232AsyncPortStopBits
SYNTAX		INTEGER { one(1), two(2), oneAndHalf(3) }
-- no		 { dynamic(4) }
DESCRIPTION	"Unable to detect all states"

VARIATION	rs232InSigChanges
ACCESS		not-implemented
DESCRIPTION	"Not supported"

VARIATION	rs232OutSigChanges
ACCESS		not-implemented
DESCRIPTION	"Not supported"
	::= { ciscoRS232Capability 1 }

ciscoRS232CapabilityV2R00 AGENT-CAPABILITIES

PRODUCT-RELEASE "MGX8850 Release 2.0,
                BPX SES Release 1.00"
STATUS          current
DESCRIPTION	"MGX8850 and BPX SES 
                RS-232-MIB capabilities."

SUPPORTS	RS-232-MIB
INCLUDES	{ rs232Group, rs232AsyncGroup }

VARIATION	rs232PortType
SYNTAX		INTEGER { rs232(2) }
DESCRIPTION	"Does not support other(1), rs422(3), rs423(4),
                v35(5), x21(6)."

VARIATION	rs232PortInSigNumber
ACCESS		not-implemented
DESCRIPTION	"Not supported"

VARIATION	rs232PortOutSigNumber
ACCESS		not-implemented
DESCRIPTION	"Not supported"

VARIATION	rs232PortInSpeed
DESCRIPTION	"Supports values 2400,9600 and 192000 only."

VARIATION	rs232PortOutSpeed
DESCRIPTION	"Supports values 2400,9600 and 192000 only."

VARIATION	rs232PortInFlowType
SYNTAX		INTEGER { ctsRts(2) }
DESCRIPTION	"Does not support none(1) and dsrDtr(3)."

VARIATION	rs232PortOutFlowType
SYNTAX		INTEGER { ctsRts(2) }
DESCRIPTION	"Does not support none(1) and dsrDtr(3)."

VARIATION	rs232AsyncPortStopBits
SYNTAX		INTEGER { one(1), two(2), oneAndHalf(3) }
DESCRIPTION	"Does not support dynamic(4)."

VARIATION	rs232InSigTable
-- ACCESS       not-implemented
DESCRIPTION	"This table is Not supported."

VARIATION	rs232OutSigTable
-- ACCESS       not-implemented
DESCRIPTION	"This table is Not supported."

VARIATION	rs232AsyncPortAutobaud
ACCESS	 	read-only
DESCRIPTION	"Write access is not supported."

VARIATION	rs232AsyncPortParityErrs
ACCESS	 	not-implemented
DESCRIPTION	"Not supported."

VARIATION	rs232AsyncPortFramingErrs
ACCESS	 	not-implemented
DESCRIPTION	"Not supported."

VARIATION	rs232AsyncPortOverrunErrs
ACCESS	 	not-implemented
DESCRIPTION	"Not supported."
    ::= { ciscoRS232Capability 2 }
END
