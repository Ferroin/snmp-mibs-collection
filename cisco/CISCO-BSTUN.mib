CISCO-BSTUN-MIB DEFINITIONS ::= BEGIN

IMPORTS
	MODULE-IDENTITY, OBJECT-TYPE, NOTIFICATION-TYPE,
	Counter32, Integer32, IpAddress
		FROM SNMPv2-SMI
	MODULE-COMPLIANCE, OBJECT-GROUP, NOTIFICATION-GROUP
		FROM SNMPv2-CONF
	ifIndex, InterfaceIndex
		FROM IF-MIB
	TruthValue
		FROM SNMPv2-TC 
	ciscoMgmt
		FROM CISCO-SMI;

ciscoBstunMIB MODULE-IDENTITY
	LAST-UPDATED 	"200302100000Z"
	ORGANIZATION 	"Cisco Systems, Inc."
	CONTACT-INFO
		"       Cisco Systems
			Customer Service

		Postal: 170 W. Tasman Drive
			San Jose, CA 95134
			USA

		   Tel: +1 800 553-NETS
		E-mail: cs-bisync@cisco.com"
	DESCRIPTION
		"The MIB module for Block Serial Tunneling.

   Overview of BSTUN MIB

   MIB description

   The BSTUN MIB provides the configuration and operational information 
   on Cisco's blocked serial tunnelling implementation.  The following 
   entities are managed:
    1) Global BSTUN information
    2) BSTUN groups
    3) BSTUN ports
    4) BSTUN routes

   The following example configuration shows how the BSTUN MIB returns
   BSTUN information, from either CISCO A or CISCO B.

    HOST == BSC  == Cisco A == IP Network == Cisco B == BSC   == BSC
            line                                        line     device

   1) The BSTUN global entry identifies the IP address by which the
      router is known to other BSTUN peers, a configurable SAP value
      on which to listen to LLC2 peers, and keepalive values to maintain
      a session between TCP/IP peers.
   2) The BSTUN group table identifies the BSTUN group number and protocol
      type that Cisco A and Cisco B use to route BSC traffic over the 
      IP network.  The table contains an entry for each BSTUN group
      defined on the router. (The group number must be the same in Cisco A 
      and Cisco B, for traffic to flow from one router to the other.)
   3) The BSTUN port table identifies the serial interface to the BSC 
      line for which the router is doing serial tunnelling.  The MIB also
      identifies the BSTUN group this interface is defined for, and
      identifies the default routing for unrecognized BSC addresses.
      There is a port entry for each BSTUN-enabled interface on the router.
   4) The BSTUN route table has an entry for each address defined for
      routing within the BSTUN group, and an entry for the default routing
      if the 'bstun route all' command is configured.  The route entry
      includes identification of the BSTUN peer, priority, state, and 
      packet and byte counters.
            "
        REVISION        "200302100000Z"
	DESCRIPTION
		"Added Asynchronous POS to IP conversion support"
        REVISION        "200106190000Z"
	DESCRIPTION
		"Added Bisync to IP conversion peer support"
	REVISION        "9701220000Z"
	DESCRIPTION
		"Added frame-relay and other support"
	REVISION        "9508210000Z"
	DESCRIPTION
		"Minor cleanups to pacify mib compiler."
::= { ciscoMgmt 35 }  

bstunObjects   OBJECT IDENTIFIER ::= { ciscoBstunMIB 1}
bstunGlobal    OBJECT IDENTIFIER ::= { bstunObjects 1}
bstunGroups    OBJECT IDENTIFIER ::= { bstunObjects 2}
bstunPorts     OBJECT IDENTIFIER ::= { bstunObjects 3}
bstunRoutes    OBJECT IDENTIFIER ::= { bstunObjects 4}

-- *********************************************************************
-- * global values for router
-- *********************************************************************

bstunIPAddr OBJECT-TYPE
    SYNTAX IpAddress
    MAX-ACCESS read-only
    STATUS current
    DESCRIPTION
        "The configured IP address used by the BSTUN component in
         this router."
    ::= { bstunGlobal 1 }

bstunLisnSap OBJECT-TYPE
    SYNTAX Integer32 (1..255)
    MAX-ACCESS read-only
    STATUS current
    DESCRIPTION
        "The configured Listening SAP address used by the BSTUN 
         component when routed via frame-relay local-ack in
         this router."
    ::= { bstunGlobal 2 }

bstunPeerKeepaliveInterval OBJECT-TYPE
    SYNTAX      Integer32 (1..300)
    UNITS       "deciseconds"
    MAX-ACCESS  read-only
    STATUS      current
    DESCRIPTION
        "The time interval between keepalives in this router."
    ::= { bstunGlobal 3 }

bstunPeerKeepaliveLimit OBJECT-TYPE
    SYNTAX      Integer32 (2..10)
    MAX-ACCESS  read-only
    STATUS      current
    DESCRIPTION
        "The number of keepalives which can be missed in a continuous
         interval before session declared down in this router."
    ::= { bstunGlobal 4 }

-- *********************************************************************
-- * bstun Group Table
-- *********************************************************************

bstunGroupTable OBJECT-TYPE
    SYNTAX SEQUENCE OF BstunGroupEntry
    MAX-ACCESS not-accessible
    STATUS current
    DESCRIPTION
        "A table of entries representing BSTUN groups configured on the
         router.  Each BSTUN-enabled interface is assigned to a BSTUN
         group, and packets can only travel between BSTUN-enabled
         interfaces in the same group."
    ::= { bstunGroups 1 }

bstunGroupEntry OBJECT-TYPE
    SYNTAX BstunGroupEntry
    MAX-ACCESS not-accessible
    STATUS current
    DESCRIPTION
        "Status and parameter values for a group."
    INDEX { bstunGroupIndex }
    ::= { bstunGroupTable 1 }

BstunGroupEntry ::=
    SEQUENCE {
        bstunGroupIndex
            INTEGER,
        bstunProtocolType
            INTEGER,
        bstunLocalAck
            TruthValue,
        bstunGroupUnroutableTransmit
            Counter32,
        bstunGroupUnroutableReceive
            Counter32
    }

bstunGroupIndex OBJECT-TYPE
    SYNTAX INTEGER (1..255)
    MAX-ACCESS not-accessible
    STATUS current
    DESCRIPTION
        "The configured BSTUN group number.  The significance of this 
        number is that it must match the BSTUN group number configured in 
        the router at the other end of the BSTUN tunnel."
    ::= { bstunGroupEntry 1 }

bstunProtocolType OBJECT-TYPE
    SYNTAX INTEGER {
                bsc(1),   -- Binary Synchronous Communications
                adtVariPoll(2),
                adtPollSelect(3),
                adplex(4),
                diebold(5),
                asyncGeneric(6),
                mdi(7),
                mosec(8),
                gddb(9),
                apos(10)
        }
    MAX-ACCESS read-only
    STATUS current
    DESCRIPTION
        "The protocol type for this BSTUN group."
    ::= { bstunGroupEntry 2 }

bstunLocalAck OBJECT-TYPE
    SYNTAX TruthValue
    MAX-ACCESS read-only
    STATUS current
    DESCRIPTION
       "Indicates if the BSTUN connection is locally acknowledged.       
        TRUE-> BSTUN connection is locally acknowledged
        FALSE-> BSTUN connection is not locally acknowledged
       " 
    ::= { bstunGroupEntry 3 }

bstunGroupUnroutableTransmit OBJECT-TYPE
    SYNTAX Counter32
    MAX-ACCESS read-only
    STATUS current
    DESCRIPTION
        "The number of unroutable frames received
         by this group from the remote partner.  They
         were unroutable because the address was not
         recognized; that is there is no bstun route command
         configured for this address.  This indicates that the
         configuration in this router is incompatible with the
         peer router."
    ::= { bstunGroupEntry 4 }

bstunGroupUnroutableReceive OBJECT-TYPE
    SYNTAX Counter32
    MAX-ACCESS read-only
    STATUS current
    DESCRIPTION
        "Count of frames received from a serial
         interface with an unsupported poll address.
         Note that there may be several ports configured
         within this bstun group; a non-zero value in this
         field indicates that a least one of these ports
         is receiving frames for which there are no 
         bstun route commands configured.  This indicates that
         the configuration in this router is incompatible with
         the configuration in at least one of the attached devices."
    ::= { bstunGroupEntry 5 }

-- *********************************************************************
-- * bstun Port Table
-- *********************************************************************

bstunPortTable OBJECT-TYPE
    SYNTAX SEQUENCE OF BstunPortEntry
    MAX-ACCESS not-accessible
    STATUS current
    DESCRIPTION
        "A list of BSTUN-enabled interfaces (ports)."
    ::= { bstunPorts 1 }

bstunPortEntry OBJECT-TYPE
    SYNTAX BstunPortEntry
    MAX-ACCESS not-accessible
    STATUS current
    DESCRIPTION
        "Status and parameter values for a BSTUN port."
    INDEX { ifIndex }
    ::= { bstunPortTable 1 }

BstunPortEntry ::=
    SEQUENCE {
        bstunPortGroupNumber
            INTEGER,
        bstunPortDefaultPeerType
            INTEGER,
        bstunPortDefaultPeerIP
            IpAddress,
        bstunPortDefaultPeerSerial
            InterfaceIndex
    }

bstunPortGroupNumber OBJECT-TYPE
    SYNTAX INTEGER (1..255)
    MAX-ACCESS read-only
    STATUS current
    DESCRIPTION
        "The group number to which the bstun port
         belongs.  Frames will only be routed to other 
         ports (on this or another router) in the same 
         bstun group.  This group should match a bstunGroupIndex
         in the bstunGroupTable."
    ::= { bstunPortEntry 1 }

bstunPortDefaultPeerType OBJECT-TYPE
    SYNTAX INTEGER { none(1), ip(2), serial(3), serialDirect(4), 
                     serialFrameRelay(5), serialLLC2(6) }
    MAX-ACCESS read-only
    STATUS current
    DESCRIPTION
        "The type of identification of the remote default partner. 
         (This is as configured with the 'route all' command.)
         If ip then the value is in bstunPortDefaultPeerIP; if serial or
         serialDirect then the value is in bstunPortDefaultPeerSerial."
    ::= { bstunPortEntry 2 }

bstunPortDefaultPeerIP OBJECT-TYPE
    SYNTAX IpAddress
    MAX-ACCESS read-only
    STATUS current
    DESCRIPTION
        "The ip address of the remote default BSTUN partner,
         for unrecognized addresses. 
         0.0.0.0 if partner address type is not ip."
    ::= { bstunPortEntry 3 }

bstunPortDefaultPeerSerial OBJECT-TYPE
    SYNTAX InterfaceIndex
    MAX-ACCESS read-only
    STATUS current
    DESCRIPTION
        "If bstunRouteType is serial then this is the 
         serial interface index of the point-to-point
         link to the remote partner; 
         if bstunRouteType is serialDirect then the 
         partner is in the local BSTUN.
         if bstunRouteType is ip then this field is
         0."
    ::= { bstunPortEntry 4 }

-- *********************************************************************
-- * Route Table
-- *********************************************************************

bstunRouteTable OBJECT-TYPE
    SYNTAX   SEQUENCE OF BstunRouteEntry
    MAX-ACCESS   not-accessible
    STATUS   current
    DESCRIPTION
       "A table containing information about specific poll
        addresses.  There is one table entry for each 
        address configured by the BSTUN ROUTE command."
    ::= { bstunRoutes 1 }

bstunRouteEntry OBJECT-TYPE
    SYNTAX   BstunRouteEntry
    MAX-ACCESS   not-accessible
    STATUS   current
    DESCRIPTION
       "The information regarding a single poll address."
    INDEX { bstunRouteGroupIndex, bstunRouteStationAddress }
    ::= { bstunRouteTable 1 }

BstunRouteEntry ::=
    SEQUENCE {
         bstunRouteGroupIndex
            INTEGER,
         bstunRouteStationAddress
            INTEGER,
         bstunRouteType
            INTEGER,
         bstunRouteIP
            IpAddress,
         bstunRouteSerial
            InterfaceIndex,
         bstunRoutePriority
            INTEGER,
         bstunRoutePeerState
            INTEGER,
         bstunRouteRxPackets
            Counter32,
         bstunRouteTxPackets
            Counter32,
         bstunRouteRxBytes
            Counter32,
         bstunRouteTxBytes
            Counter32,
         bstunRouteDLCI
            Integer32,
         bstunRouteRSAP
            Integer32,
         bstunLLC2Priority
            Integer32,
         bstunRouteBIPPassive
            TruthValue,
         bstunRouteBIPLocalPort
            Integer32,
         bstunRouteBIPForeignPort
            Integer32,
         bstunRouteBIPDeviceStatus
            BITS,
         bstunRouteAPIPHeaderVersion
            INTEGER
    }

bstunRouteGroupIndex OBJECT-TYPE
    SYNTAX INTEGER (1..255)
    MAX-ACCESS not-accessible
    STATUS current
    DESCRIPTION
        "The index of the BSTUN Group owning this 
         station."
    ::= { bstunRouteEntry 1 }

bstunRouteStationAddress OBJECT-TYPE
    SYNTAX INTEGER (1..256)
    MAX-ACCESS not-accessible
    STATUS current
    DESCRIPTION
        "The poll address of the station.  256 indicates the ALL parameter
         on the STUN ROUTE command, which is the route for all 
         unrecognized addresses." 
    ::= { bstunRouteEntry 2 }

bstunRouteType OBJECT-TYPE
    SYNTAX INTEGER { none(1), ip(2), serial(3), serialDirect(4), 
                     serialFrameRelay(5), serialLLC2(6), bip(7), 
                     apip(8) }
    MAX-ACCESS read-only
    STATUS current
    DESCRIPTION
        "The type of identification of the remote partner.
         If ip then the value is in bstunRouteIP; if serial or
         serialDirect then the value is in bstunRouteSerial; if 
         bip or apip then the value is in bstunRouteIP, 
         bstunRouteBIPLocalPort and bstunRouteBIPForeignPort."
    ::= { bstunRouteEntry 3 }

bstunRouteIP OBJECT-TYPE
    SYNTAX IpAddress
    MAX-ACCESS read-only
    STATUS current
    DESCRIPTION
        "The ip address of the remote BSTUN partner. 
         0.0.0.0 if partner address type is not ip."
    ::= { bstunRouteEntry 4 }

bstunRouteSerial OBJECT-TYPE
    SYNTAX InterfaceIndex
    MAX-ACCESS read-only
    STATUS current
    DESCRIPTION
        "If bstunRouteType is serial then this is the 
         serial interface index of the point-to-point
         link to the remote partner; 
         if bstunRouteType is serialDirect then the 
         partner is in the local BSTUN.
         if bstunRouteType is ip then this field is
         0."
    ::= { bstunRouteEntry 5 }

bstunRoutePriority OBJECT-TYPE
    SYNTAX INTEGER {low(1), normal(2), medium(3), high(4)}
    MAX-ACCESS read-only
    STATUS current
    DESCRIPTION
        "The priority with which this station's traffic will
         be routed across the network."
    ::= { bstunRouteEntry 6 }

bstunRoutePeerState OBJECT-TYPE
    SYNTAX INTEGER {dead(1), closed(2), opening(3), openWait(4),
                    connected(5), direct(6)}
    MAX-ACCESS read-only
    STATUS current
    DESCRIPTION
        "The state of the peer connection through the
         BSTUN tunnel."
    ::= { bstunRouteEntry 7 }

bstunRouteRxPackets OBJECT-TYPE
    SYNTAX Counter32
    MAX-ACCESS read-only
    STATUS current
    DESCRIPTION
        "Count of frames received from the serial
         interface with this station's address."
    ::= { bstunRouteEntry 8 }

bstunRouteTxPackets OBJECT-TYPE
    SYNTAX Counter32
    MAX-ACCESS read-only
    STATUS current
    DESCRIPTION
        "Count of frames transmitted at the serial
         interface with this station's address."
    ::= { bstunRouteEntry 9 }

bstunRouteRxBytes OBJECT-TYPE
    SYNTAX Counter32
    MAX-ACCESS read-only
    STATUS current
    DESCRIPTION
        "Count of bytes received from the serial
         interface with this station's address."
    ::= { bstunRouteEntry 10 }

bstunRouteTxBytes OBJECT-TYPE
    SYNTAX Counter32
    MAX-ACCESS read-only
    STATUS current
    DESCRIPTION
        "Count of bytes transmitted at the serial
         interface with this station's address."
    ::= { bstunRouteEntry 11 }

bstunRouteDLCI OBJECT-TYPE
    SYNTAX Integer32 (16..1007)
    MAX-ACCESS read-only
    STATUS current
    DESCRIPTION
        "If bstunRouteType is serialFrameRelay or serialLLC2
         then this is the frame relay dlci circuit used for 
         the point-to-point link to the remote partner; 
         if bstunRouteType is ip or serial then this field is
         0."
    ::= { bstunRouteEntry 12 }

bstunRouteRSAP OBJECT-TYPE
    SYNTAX Integer32    (1..255)
    MAX-ACCESS          read-only
    STATUS              current
    DESCRIPTION
        "If bstunRouteType is serialLLC2 then this 
         is the llc2 sap value used for the point-to-point
         link to the remote partner; 
         if bstunRouteType is ip or serial or serialFrameRelay
         then this field is 0."
    ::= { bstunRouteEntry 13 }

bstunLLC2Priority OBJECT-TYPE
    SYNTAX Integer32    (1..10)
    MAX-ACCESS          read-only
    STATUS              current
    DESCRIPTION
        "If bstunRouteType is serialLLC2 then this 
         is the llc2 priority used for the point-to-point
         link to the remote partner; 
         if bstunRouteType is ip or serial or serialFrameRelay
         then this field is 0."
    ::= { bstunRouteEntry 14 }

bstunRouteBIPPassive OBJECT-TYPE
    SYNTAX      	TruthValue
    MAX-ACCESS  	read-only
    STATUS      	current
    DESCRIPTION
	"Specifies whether the bip peer will wait for an inbound connection 
         or actively connect to the remote peer."
    DEFVAL                      { false }
   ::= { bstunRouteEntry 15 }

bstunRouteBIPLocalPort OBJECT-TYPE
    SYNTAX Integer32    (1025..32000)
    MAX-ACCESS          read-only
    STATUS              current
    DESCRIPTION
        "If bstunRouteType is bip then this is the local port used when 
         connecting to the remote peer."
    ::= { bstunRouteEntry 16 }

bstunRouteBIPForeignPort OBJECT-TYPE
    SYNTAX Integer32    (1025..32000)
    MAX-ACCESS          read-only
    STATUS              current
    DESCRIPTION
        "If bstunRouteType is bip then this is the for port used to 
         connect to the remote peer."
    ::= { bstunRouteEntry 17 }

bstunRouteBIPDeviceStatus OBJECT-TYPE
    SYNTAX BITS { operationcheck(0), reservedBit1(1), 
                  datacheck(2), equipmentcheck(3), 
                  interventionrequired(4), commandreject(5), 
                  deviceinactive(6), deviceactive(7), 
                  reservedBit8(8), deviceend(9),
                  unitspecify(10), devicebusy(11) }
    MAX-ACCESS read-only
    STATUS current
    DESCRIPTION
        "If bstunRouteType is bip then this indicates the OR bit mask
          status of the mapped bisync device:

                            if no bits are set, indicates that the 
                            bisync device is up and operational.        
	             Bit 0, if set, indicates that the bisync device is
                            reporting  an operation check error.
                     Bit 2, if set, indicates that the bisync device is
                            reporting  a data check error.
                     Bit 3, if set, indicates that the bisync device is
                            reporting  an equipment check error.
                     Bit 4, if set, indicates that the bisync device is
                            reporting  that intervention is required.
                     Bit 5, if set, indicates that the bisync device is
                            reporting  that a command has been rejected.
                     Bit 6, if set, indicates that the bisync device is
                            not responding to polls.
                     Bit 7, if set, indicates that the bisync device is
                            now responding to polls and is operational.
                     Bit 9, if set, indicates that the bisync device is
                            reporting  that is no longer busy.
                     Bit 10, if set, indicates that the bisync device is
                             reporting  a device unit specify.
                     Bit 11, if set, indicates that the bisync device is
                             reporting  a busy condition."
    ::= { bstunRouteEntry 18 }

bstunRouteAPIPHeaderVersion OBJECT-TYPE
    SYNTAX INTEGER {v0(1), v1(2), v2(3)}
    MAX-ACCESS read-only
    STATUS current
    DESCRIPTION
	"Specifies the tunneling header format to use for APIP:
		v0, if set, indicates a 2 byte encapsulation header. 
		    The length of the header is included in the size of 
		    the sent packet.
		v1, if set, indicates a 2 byte encapsulation header. 
		    The length of the header is excluded from the size of 
		    the sent packet.
		v2, if set, indicates a 4 byte encapsulation header. 
		    The length of the header is excluded from the size of 
		    the sent packet."
   ::= { bstunRouteEntry 19 }
-- *************************************************************************
-- * BSTUN notifications               
-- *************************************************************************

bstunNotificationPrefix OBJECT IDENTIFIER ::= { ciscoBstunMIB 2 }
bstunNotifications OBJECT IDENTIFIER ::= { bstunNotificationPrefix 0 }

bstunPeerStateChangeNotification NOTIFICATION-TYPE
     OBJECTS { bstunRoutePeerState }
     STATUS      deprecated
     DESCRIPTION
        "This notification indicates that the state of a BSTUN route
         has transitioned to active (connected) or inactive
         (dead or closed)."
     ::= { bstunNotifications 1 }

bstunPeerStateChangeNotification2 NOTIFICATION-TYPE
     OBJECTS { bstunRoutePeerState,
               bstunRouteType,
               bstunRouteRxPackets,
               bstunRouteTxPackets }
     STATUS      current
     DESCRIPTION
        "This notification indicates that the state of a BSTUN route
         has transitioned to active (connected) or inactive
         (dead or closed)."
     ::= { bstunNotifications 2 }

bstunCUStatusChangeNotification NOTIFICATION-TYPE
     OBJECTS { bstunRouteIP,
               bstunRouteBIPForeignPort,
               bstunRouteBIPLocalPort,
               bstunRouteBIPDeviceStatus }
     STATUS      current
     DESCRIPTION
        "This notification is generated when a mapped BIP bisync 
         device state has changed."
     ::= { bstunNotifications 3 }

-- *************************************************************************
-- * Conformance Information
-- *************************************************************************
--

bstunMibConformance   OBJECT IDENTIFIER ::= { ciscoBstunMIB 3 }
bstunMibCompliances   OBJECT IDENTIFIER ::= { bstunMibConformance 1 }
bstunMibGroups        OBJECT IDENTIFIER ::= { bstunMibConformance 2 }
--
-- *************************************************************************
-- * Compliance Statements
-- *************************************************************************
bstunMibCompliance    MODULE-COMPLIANCE
        STATUS obsolete -- superceded by bstunMibComplianceRev1
        DESCRIPTION
                 "The compliance statement for BSTUN."
        MODULE  -- this module
                MANDATORY-GROUPS {
                        bstunGlobalGroup,
			bstunGroupGroup,
                        bstunPortGroup,
                        bstunRouteGroup
		}
         ::= { bstunMibCompliances 1 }

bstunMibComplianceRev1    MODULE-COMPLIANCE
        STATUS obsolete
        DESCRIPTION
                "The compliance statement for all Cisco systems that 
                implement  BSTUN functions."
        MODULE  -- this module
                MANDATORY-GROUPS {
                        bstunGlobalGroupRev1,
			bstunGroupGroup,
                        bstunPortGroup,
                        bstunRouteGroupRev1
		}
         ::= { bstunMibCompliances 2 }

bstunMibComplianceRev2    MODULE-COMPLIANCE
        STATUS deprecated
        DESCRIPTION
                "The compliance statement for all Cisco systems that 
                implement  BSTUN functions."
        MODULE  -- this module
                MANDATORY-GROUPS {
                        bstunGlobalGroupRev1,
			bstunGroupGroup,
                        bstunPortGroup,
                        bstunRouteGroupRev2,
                        bstunNotificationGroupRev1
		}
         ::= { bstunMibCompliances 3 }

bstunMibComplianceRev3    MODULE-COMPLIANCE
        STATUS current
        DESCRIPTION
                "The compliance statement for all Cisco systems that 
                implement  BSTUN functions."
        MODULE  -- this module
                MANDATORY-GROUPS {
                        bstunGlobalGroupRev1,
			bstunGroupGroup,
                        bstunPortGroup,
                        bstunRouteGroupRev1,
                        bstunNotificationGroupRev1
		}
                GROUP bstunRouteBipGroup
                DESCRIPTION
                        "This group is mandatory when implementing
                        the bip route type."
                GROUP bstunRoutePortsGroup
                DESCRIPTION
                        "This group is mandatory when implementing
                        the bip or apip route types."
                GROUP bstunRouteApipGroup
                DESCRIPTION
                        "This group is mandatory when implementing
                        the apip route type."
         ::= { bstunMibCompliances 4 }

bstunGlobalGroup OBJECT-GROUP
        OBJECTS {
                bstunIPAddr
        }
        STATUS obsolete -- superceded by bstunGlobalGroupRev1
        DESCRIPTION
                "A collection of objects providing global BSTUN information."
        ::= { bstunMibGroups 1}

bstunGroupGroup OBJECT-GROUP
        OBJECTS {
                bstunProtocolType,
                bstunLocalAck,
                bstunGroupUnroutableTransmit,
                bstunGroupUnroutableReceive
        }
        STATUS current
        DESCRIPTION
                "A collection of objects providing information about 
                 BSTUN groups ."
        ::= { bstunMibGroups 2 }

bstunPortGroup OBJECT-GROUP
        OBJECTS {
                bstunPortGroupNumber,
                bstunPortDefaultPeerType,
                bstunPortDefaultPeerIP,
                bstunPortDefaultPeerSerial
        }
        STATUS current
        DESCRIPTION
                "A collection of objects providing information about
                 BSTUN enabled interfaces."
        ::= { bstunMibGroups 3}

bstunRouteGroup OBJECT-GROUP
        OBJECTS {
                bstunRouteType,
                bstunRouteIP,
                bstunRouteSerial,
                bstunRoutePriority,
                bstunRoutePeerState,
                bstunRouteRxPackets,
                bstunRouteTxPackets,
                bstunRouteRxBytes,
                bstunRouteTxBytes
        }
        STATUS obsolete -- superceded by bstunRouteGroupRev1
        DESCRIPTION
                "A collection of objects providing information about
                 BSTUN defined routes."
        ::= { bstunMibGroups 4}

bstunGlobalGroupRev1 OBJECT-GROUP
        OBJECTS {
                bstunIPAddr,
                bstunLisnSap,
                bstunPeerKeepaliveInterval,
                bstunPeerKeepaliveLimit
        }
        STATUS current
        DESCRIPTION
                "A collection of objects providing global BSTUN information."
        ::= { bstunMibGroups 5}

bstunRouteGroupRev1 OBJECT-GROUP
        OBJECTS {
                bstunRouteType,
                bstunRouteIP,
                bstunRouteSerial,
                bstunRoutePriority,
                bstunRoutePeerState,
                bstunRouteRxPackets,
                bstunRouteTxPackets,
                bstunRouteRxBytes,
                bstunRouteTxBytes,
                bstunRouteDLCI,
                bstunRouteRSAP,
                bstunLLC2Priority
        }
        STATUS current
        DESCRIPTION
                "A collection of objects providing information about
                 BSTUN defined routes."
        ::= { bstunMibGroups 6}

bstunRouteGroupRev2 OBJECT-GROUP
        OBJECTS {
                bstunRouteType,
                bstunRouteIP,
                bstunRouteSerial,
                bstunRoutePriority,
                bstunRoutePeerState,
                bstunRouteRxPackets,
                bstunRouteTxPackets,
                bstunRouteRxBytes,
                bstunRouteTxBytes,
                bstunRouteDLCI,
                bstunRouteRSAP,
                bstunLLC2Priority,
                bstunRouteBIPPassive,
                bstunRouteBIPLocalPort,
                bstunRouteBIPForeignPort,
                bstunRouteBIPDeviceStatus
        }
        STATUS deprecated
        DESCRIPTION
                "A collection of objects providing information about
                 BSTUN defined routes."
        ::= { bstunMibGroups 7}

bstunNotificationGroup NOTIFICATION-GROUP
	NOTIFICATIONS  {
                bstunPeerStateChangeNotification
	}
	STATUS deprecated
	DESCRIPTION
		"A collection of notifications. "
	::= { bstunMibGroups 8 } 

bstunNotificationGroupRev1 NOTIFICATION-GROUP
	NOTIFICATIONS  {
                bstunPeerStateChangeNotification2,
                bstunCUStatusChangeNotification
	}
	STATUS current
	DESCRIPTION
		"A collection of notifications. "
	::= { bstunMibGroups 9 }

bstunRouteBipGroup OBJECT-GROUP
        OBJECTS {
                bstunRouteBIPPassive,
                bstunRouteBIPDeviceStatus
        }
        STATUS current
        DESCRIPTION
                "A objects providing information about
                 BSTUN defined routes for BIP protocol."
        ::= { bstunMibGroups 10}

bstunRoutePortsGroup OBJECT-GROUP
        OBJECTS {
                bstunRouteBIPLocalPort,
                bstunRouteBIPForeignPort
        }
        STATUS current
        DESCRIPTION
                "A objects providing port number informaton information 
                 about BSTUN defined routes for BIP and APIP protocols."
        ::= { bstunMibGroups 11}

bstunRouteApipGroup OBJECT-GROUP
        OBJECTS {
                bstunRouteAPIPHeaderVersion
        }
        STATUS current
        DESCRIPTION
                "A objects providing information about
                 BSTUN defined routes for APIP protocol."
        ::= { bstunMibGroups 12}

END
