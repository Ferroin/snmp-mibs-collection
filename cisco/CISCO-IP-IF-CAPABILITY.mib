CISCO-IP-IF-CAPABILITY DEFINITIONS ::= BEGIN

IMPORTS
        MODULE-IDENTITY,
        Integer32
                FROM SNMPv2-SMI
        AGENT-CAPABILITIES
                FROM SNMPv2-CONF
        ciscoAgentCapability
                FROM CISCO-SMI;

ciscoIPIfCapability MODULE-IDENTITY
        LAST-UPDATED    "200404190000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of CISCO-IP-IF-MIB."

        REVISION        "200404190000Z"
        DESCRIPTION
                "Initial version of this MIB module."
        ::= { ciscoAgentCapability 324 }

ciscoIpIfCapCatOSV08R0101 AGENT-CAPABILITIES
    PRODUCT-RELEASE     "Cisco CatOS 8.1(1)."
    STATUS              current
    DESCRIPTION         "CISCO-IP-IF-MIB capabilities."

    SUPPORTS            CISCO-IP-IF-MIB
        INCLUDES        { ciscoIPIfAddressConfigurationGroup1,
                          ciscoIPIfAddressConfigurationGroup2,
                          ciscoIPIfAddressConfigurationGroup3,
                          ciscoIPIfAddressConfigurationGroup4 
                        }
        VARIATION       ciiIPAddressCategoryCap
        SYNTAX          BITS { single(0) }
        DESCRIPTION     "Only limited set of enumerated values
                         are supported."

        VARIATION       ciiIPAddressType
        SYNTAX          INTEGER {ipv4(1)}
        DESCRIPTION     "Only limited set of enumerated values
                         are supported."

        VARIATION       ciiIPAddressIfIndex
        SYNTAX          Integer32 (1 | 3)
        DESCRIPTION     "Only InterfaceIndex 1 and 3 which correspond
                         to kernel interfaces are supported."

        VARIATION       ciiIPAddressCategory
        SYNTAX          INTEGER {single(1)}
        DESCRIPTION     "Only limited set of enumerated values
                         are supported."

        VARIATION       ciiIPAddressStatus
        SYNTAX          INTEGER { active(1),
                                  creatAndGo(4),
                                  destroy(6)
                                }
        DESCRIPTION     "Only limited set of enumerated values 
                         are supported." 

        VARIATION       ciiIPIfAddressCategory
        SYNTAX          INTEGER {single(1)}
        DESCRIPTION     "Only limited set of enumerated values
                         are supported."

        VARIATION       ciiIPIfAddressStatus
        SYNTAX          INTEGER { active(1),
                                  creatAndGo(4),
                                  destroy(6)
                                }
        DESCRIPTION     "Only limited set of enumerated values 
                         are supported." 
    ::= { ciscoIPIfCapability 1 }

END
