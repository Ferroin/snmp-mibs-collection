CISCO-SRP-CAPABILITY DEFINITIONS ::= BEGIN

IMPORTS
         MODULE-IDENTITY
                 FROM SNMPv2-SMI
         AGENT-CAPABILITIES
                 FROM SNMPv2-CONF
         ciscoAgentCapability
                 FROM CISCO-SMI;

ciscoSrpCapability MODULE-IDENTITY
                 LAST-UPDATED    "200005260000Z"
                 ORGANIZATION    "Cisco Systems, Inc."
                 CONTACT-INFO
                         "       Cisco Systems
                                 Customer Service

                         Postal: 170 West Tasman Drive
                                 San Jose, CA  95134
                                 USA

                            Tel: +1 800 553-NETS

                         E-mail: cs-snmp@cisco.com"
                 DESCRIPTION
                         "Initial version of this MIB module."
                 ::= { ciscoAgentCapability 9999 }

ciscoSrpCapabilityV12R00 AGENT-CAPABILITIES

PRODUCT-RELEASE "Cisco IOS 12.0"
STATUS          current
DESCRIPTION     "CISCO-SRP-MIB agent capabilities"

SUPPORTS        CISCO-SRP-MIB
INCLUDES        { srpIfGroup,
                   srpMACSideGroup,
                   srpRingTopologyMapGroup }

VARIATION       srpIpsLockedOut
ACCESS          read-only
DESCRIPTION     "Lock out feature is not supported"

VARIATION       srpIfTimeElapsed
DESCRIPTION     "Always reads 1 since interval tables are not
                  supported"

VARIATION       srpIfValidIntervals
DESCRIPTION     "Always reads 0 since interval tables are not
                  supported"
         ::= { ciscoSrpCapability 1 }

END
