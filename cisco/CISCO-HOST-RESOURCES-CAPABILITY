CISCO-HOST-RESOURCES-CAPABILITY DEFINITIONS ::= BEGIN

IMPORTS
    MODULE-IDENTITY
        FROM SNMPv2-SMI
    AGENT-CAPABILITIES
        FROM SNMPv2-CONF
    ciscoAgentCapability
        FROM CISCO-SMI;

ciscoHostResourcesCapability MODULE-IDENTITY
    LAST-UPDATED    "200710040000Z"
    ORGANIZATION    "Cisco Systems, Inc."
    CONTACT-INFO
            "Cisco Systems
            Customer Service

            Postal: 170 W Tasman Drive
            San Jose, CA  95134
            USA

            Tel: +1 800 553-NETS

            E-mail: cs-snmp@cisco.com"
    DESCRIPTION
        "Agent capabilities for HOST-RESOURCES-MIB"
    REVISION        "200710040000Z"
    DESCRIPTION
        "Added Agent Capability for CTS 1000/3000 platform"
    REVISION        "200709170000Z"
    DESCRIPTION
        "Initial version of this MIB module."
    ::= { ciscoAgentCapability 547 }

ciscoHostResourcesCapabilityV12R04 AGENT-CAPABILITIES
    PRODUCT-RELEASE "Cisco IOS 12.4"
    STATUS          current
    DESCRIPTION
        "HOST RESOURCES MIB capabilities"

    SUPPORTS        HOST-RESOURCES-MIB
    INCLUDES        { hrDeviceGroup }
    VARIATION       hrDeviceType
    DESCRIPTION
        "The current implementation supports only Printer
        device type. Hence hard coded this object to
        hrDevicePrinter."

    VARIATION       hrDeviceID
    DESCRIPTION
        "Unable to display the product ID of the device
        as specified in the syntax of this object. For
        example, the USB Analyser output of the packet
        received from printer dispalys the ProductID for
        HP 5400 printer as 0x8604 etc. This is a bug in
        printer related code. Hence hrDeviceID can be
        displayed only as hrDevicePrinter."

    VARIATION       hrDeviceStatus
    SYNTAX          INTEGER  {
                        running(2),
                        down(5)
                    }
    DESCRIPTION
        "Supported operational states of the device
        are running(2) and down(5)."

    VARIATION       hrDeviceErrors
    ACCESS          not-implemented
    DESCRIPTION
        "Not Implemented."

    VARIATION       hrProcessorFrwID
    ACCESS          not-implemented
    DESCRIPTION
        "Not Implemented."

    VARIATION       hrProcessorLoad
    ACCESS          not-implemented
    DESCRIPTION
        "Not Implemented."

    VARIATION       hrNetworkIfIndex
    ACCESS          not-implemented
    DESCRIPTION
        "Not Implemented."

    VARIATION       hrPrinterStatus
    SYNTAX          INTEGER  {
                        other(1),
                        idle(3),
                        printing(4)
                    }
    DESCRIPTION
        "Unable to detect all current status of
        the printer device."

    VARIATION       hrPrinterDetectedErrorState
    DESCRIPTION
        "Unable to find all error conditions detected
        by the printer. 'noPaper' condition can be
        detected. Apart from that the software
        implementation can detect general printer error
        state for which the MIBs will return 'offline'
        condition."

    VARIATION       hrDiskStorageAccess
    ACCESS          not-implemented
    DESCRIPTION
        "Not Implemented."

    VARIATION       hrDiskStorageMedia
    ACCESS          not-implemented
    DESCRIPTION
        "Not Implemented."

    VARIATION       hrDiskStorageRemoveble
    ACCESS          not-implemented
    DESCRIPTION
        "Not Implemented."

    VARIATION       hrDiskStorageCapacity
    ACCESS          not-implemented
    DESCRIPTION
        "Not Implemented."

    VARIATION       hrPartitionIndex
    ACCESS          not-implemented
    DESCRIPTION
        "Not Implemented."

    VARIATION       hrPartitionLabel
    ACCESS          not-implemented
    DESCRIPTION
        "Not Implemented."

    VARIATION       hrPartitionID
    ACCESS          not-implemented
    DESCRIPTION
        "Not Implemented."

    VARIATION       hrPartitionSize
    ACCESS          not-implemented
    DESCRIPTION
        "Not Implemented."

    VARIATION       hrPartitionFSIndex
    ACCESS          not-implemented
    DESCRIPTION
        "Not Implemented."

    VARIATION       hrFSIndex
    ACCESS          not-implemented
    DESCRIPTION
        "Not Implemented."

    VARIATION       hrFSMountPoint
    ACCESS          not-implemented
    DESCRIPTION
        "Not Implemented."

    VARIATION       hrFSRemoteMountPoint
    ACCESS          not-implemented
    DESCRIPTION
        "Not Implemented."

    VARIATION       hrFSType
    ACCESS          not-implemented
    DESCRIPTION
        "Not Implemented."

    VARIATION       hrFSAccess
    ACCESS          not-implemented
    DESCRIPTION
        "Not Implemented."

    VARIATION       hrFSBootable
    ACCESS          not-implemented
    DESCRIPTION
        "Not Implemented."

    VARIATION       hrFSStorageIndex
    ACCESS          not-implemented
    DESCRIPTION
        "Not Implemented."

    VARIATION       hrFSLastFullBackupDate
    ACCESS          not-implemented
    DESCRIPTION
        "Not Implemented."

    VARIATION       hrFSLastPartialBackupDate
    ACCESS          not-implemented
    DESCRIPTION
        "Not Implemented."
    ::= { ciscoHostResourcesCapability 1 }

ciscoHostResourcesCapabilityCTSV120 AGENT-CAPABILITIES
    PRODUCT-RELEASE "Cisco TelePresence System (CTS) 1.2.0."
    STATUS          current
    DESCRIPTION
        "HOST RESOURCES MIB capabilities"

    SUPPORTS        HOST-RESOURCES-MIB
    INCLUDES        {
                        hrSystemGroup,
                        hrStorageGroup,
                        hrDeviceGroup,
                        hrSWRunGroup,
                        hrSWRunPerfGroup
                    }
    VARIATION       hrSystemInitialLoadDevice
    ACCESS          read-only
    DESCRIPTION
        "Write/create not supported."

    VARIATION       hrSystemInitialLoadParameters
    ACCESS          read-only
    DESCRIPTION
        "Write/create not supported."

    VARIATION       hrStorageSize
    ACCESS          read-only
    DESCRIPTION
        "Write/create not supported."

    VARIATION       hrStorageAllocationFailures
    ACCESS          not-implemented
    DESCRIPTION
        "Not supported."

    VARIATION       hrFSLastFullBackupDate
    ACCESS          read-only
    DESCRIPTION
        "Write/create not supported."

    VARIATION       hrFSLastPartialBackupDate
    ACCESS          read-only
    DESCRIPTION
        "Write/create not supported."

    VARIATION       hrSWInstalledIndex
    ACCESS          not-implemented
    DESCRIPTION
        "Not supported."

    VARIATION       hrSWInstalledName
    ACCESS          not-implemented
    DESCRIPTION
        "Not supported."

    VARIATION       hrSWInstalledID
    ACCESS          not-implemented
    DESCRIPTION
        "Not supported."

    VARIATION       hrSWInstalledType
    ACCESS          not-implemented
    DESCRIPTION
        "Not supported."

    VARIATION       hrSWInstalledDate
    ACCESS          not-implemented
    DESCRIPTION
        "Not supported."
    ::= { ciscoHostResourcesCapability 2 }

END
