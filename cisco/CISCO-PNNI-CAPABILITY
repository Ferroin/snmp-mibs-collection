CISCO-PNNI-CAPABILITY DEFINITIONS ::= BEGIN

IMPORTS
        MODULE-IDENTITY
                FROM SNMPv2-SMI
        AGENT-CAPABILITIES
                FROM SNMPv2-CONF
        ciscoAgentCapability
                FROM CISCO-SMI;   

ciscoPnniCapability MODULE-IDENTITY
        LAST-UPDATED    "200205020000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for PNNI-MIB."
        REVISION "200205020000Z"
        DESCRIPTION
            "Initial version of this MIB module."
        ::= { ciscoAgentCapability 9999 }

ciscoPnniCapabilityV2R00 AGENT-CAPABILITIES

PRODUCT-RELEASE "MGX8850 Release 2.00,
                BPX SES Release 1.00"
STATUS          current
DESCRIPTION     "PNNI MIB Capabilities."

SUPPORTS PNNI-MIB
INCLUDES {
    pnniGeneralMinGroup, pnniGeneralBorderGroup,
    pnniNodeMinGroup, pnniNodePglMinGroup, 
    pnniNodePglLgnGroup, pnniSummaryAddressLgnGroup,
    pnniLinkMinGroup, pnniNodeTimerMinGroup,
    pnniNodeSvccLgnGroup, pnniScopeMinGroup 
}
VARIATION    pnniNodeDomainName
ACCESS       not-implemented
DESCRIPTION "Not supported."

VARIATION pnniNodeRowStatus
SYNTAX    INTEGER { active(1), createAndGo(4), destroy(6) }
DESCRIPTION 
    "Does not support notInService(2), createAndWait(5)
    and notReady(3). The value active(1) is not supported 
    for write operation."

VARIATION pnniSummaryAddressRowStatus
SYNTAX    INTEGER { active(1),createAndGo(4),destroy(6) }
DESCRIPTION 
    "Does not support notInService(2), createAndWait(5)
    and notReady(3). The value active(1) is not supported for
    write operation."
    ::= { ciscoPnniCapability 1 }

END
