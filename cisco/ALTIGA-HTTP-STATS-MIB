ALTIGA-HTTP-STATS-MIB DEFINITIONS ::= BEGIN

   IMPORTS
      MODULE-IDENTITY, OBJECT-TYPE, Counter32, Gauge32, Unsigned32, 
          IpAddress, Integer32, TimeTicks
         FROM SNMPv2-SMI
      DisplayString
         FROM SNMPv2-TC
      EncryptionAlgorithm
              FROM ALTIGA-SESSION-STATS-MIB
      OBJECT-GROUP, MODULE-COMPLIANCE
         FROM SNMPv2-CONF
      alStatsHttp, alHttpGroup
         FROM ALTIGA-MIB
      alHttpMibModule
         FROM ALTIGA-GLOBAL-REG;

   altigaHttpStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"
      DESCRIPTION
         "The Altiga HTTP Statistics MIB models counters and objects that are
          of management interest for HTTP.

          Acronyms
          The following acronyms are used in this document:

            HTTP:       HyperText Transfer Protocol

            MIB:        Management Information Base

            TCP:        Transmission Control Protocol
         "

        REVISION "200209051300Z"
        DESCRIPTION
                "Added module compliance."

        REVISION "200207100000Z"
        DESCRIPTION
                "Updated with new header"
      ::= { alHttpMibModule 2 }

-- +++++++++++++++++++++++++++++++++++++++++++++++++++++++
-- MIB Objects
-- +++++++++++++++++++++++++++++++++++++++++++++++++++++++

alStatsHttpGlobal	OBJECT IDENTIFIER ::= { alStatsHttp 1 }

alHttpStatsOctetsSent		OBJECT-TYPE
	SYNTAX			Counter32
	MAX-ACCESS		read-only
	STATUS			current
	DESCRIPTION
	       "The number of octets sent."
	::= { alStatsHttpGlobal 1 }

alHttpStatsOctetsRcvd		OBJECT-TYPE
	SYNTAX			Counter32
	MAX-ACCESS		read-only
	STATUS			current
	DESCRIPTION
	       "The number of octets received."
	::= { alStatsHttpGlobal 2 }

alHttpStatsPacketsSent		OBJECT-TYPE
	SYNTAX			Counter32
	MAX-ACCESS		read-only
	STATUS			current
	DESCRIPTION
	       "The number of packets."
	::= { alStatsHttpGlobal 3 }

alHttpStatsPacketsRcvd		OBJECT-TYPE
	SYNTAX			Counter32
	MAX-ACCESS		read-only
	STATUS			current
	DESCRIPTION
	       "The number of packets received."
	::= { alStatsHttpGlobal 4 }

alHttpStatsActiveConnections	OBJECT-TYPE
	SYNTAX			Gauge32
	MAX-ACCESS		read-only
	STATUS			current
	DESCRIPTION
	       "The number of active TCP connections."
	::= { alStatsHttpGlobal 5 }

alHttpStatsMaxConnections	OBJECT-TYPE
	SYNTAX			Counter32
	MAX-ACCESS		read-only
	STATUS			current
	DESCRIPTION
	       "The maximum number of active TCP connections that existed at one any time."
	::= { alStatsHttpGlobal 6 }

alHttpStatsActiveSessions	OBJECT-TYPE
	SYNTAX			Gauge32
	MAX-ACCESS		read-only
	STATUS			current
	DESCRIPTION
	       "The number of active sessions."
	::= { alStatsHttpGlobal 7 }

alHttpStatsMaxSessions		OBJECT-TYPE
	SYNTAX			Counter32
	MAX-ACCESS		read-only
	STATUS			current
	DESCRIPTION
	       "The maximum number of active sessions that existed at one any time."
	::= { alStatsHttpGlobal 8 }

alHttpStatsTotalConnections	OBJECT-TYPE
	SYNTAX			Counter32
	MAX-ACCESS		read-only
	STATUS			current
	DESCRIPTION
	       "The total number of TCP connections established."
	::= { alStatsHttpGlobal 9 }

alHttpStatsTotalSessions	OBJECT-TYPE
	SYNTAX			Counter32
	MAX-ACCESS		read-only
	STATUS			current
	DESCRIPTION
	       "The total number of sessions established."
	::= { alStatsHttpGlobal 10 }

alHttpStatsSessionTable		OBJECT-TYPE
        SYNTAX			SEQUENCE OF AlHttpStatsSessionEntry
	MAX-ACCESS		not-accessible
	STATUS			current
	DESCRIPTION
	       "List of active HTTP sessions."
	::= { alStatsHttp 2 }

alHttpStatsSessionEntry	   	OBJECT-TYPE
        SYNTAX			AlHttpStatsSessionEntry
	MAX-ACCESS		not-accessible
	STATUS			current
	DESCRIPTION
	       "An entry in the alHttpStatsSessionTable."
	INDEX			{ alHttpStatsSessionIndex }
	::= { alHttpStatsSessionTable 1 }

AlHttpStatsSessionEntry ::= SEQUENCE {
        alHttpStatsSessionIndex         	Integer32,
	alHttpStatsSessionName          	DisplayString,
	alHttpStatsSessionIpAddr        	IpAddress,
	alHttpStatsSessionStartTime		TimeTicks,
	alHttpStatsSessionLoginTime		Unsigned32,
	alHttpStatsSessionEncr			EncryptionAlgorithm,
	alHttpStatsSessionOctetsSent    	Counter32,
	alHttpStatsSessionOctetsRcvd		Counter32,
	alHttpStatsSessionPacketsSent		Counter32,
	alHttpStatsSessionPacketsRcvd		Counter32,
	alHttpStatsSessionActiveConnections	Gauge32,
	alHttpStatsSessionMaxConnections	Counter32,
	alHttpStatsSessionTotalConnections	Counter32
}

alHttpStatsSessionIndex		OBJECT-TYPE
        SYNTAX			Integer32
	MAX-ACCESS		read-only
	STATUS			current
	DESCRIPTION
	       "Index of this session."
	::= { alHttpStatsSessionEntry 1 }

alHttpStatsSessionName		OBJECT-TYPE
        SYNTAX			DisplayString
	MAX-ACCESS		read-only
	STATUS			current
	DESCRIPTION
	       "Name of the administrator using this session."
	::= { alHttpStatsSessionEntry 2 }

alHttpStatsSessionIpAddr	OBJECT-TYPE
        SYNTAX			IpAddress
	MAX-ACCESS		read-only
	STATUS			current
	DESCRIPTION
	       "Remote IP address of this session.."
	::= { alHttpStatsSessionEntry 3 }

alHttpStatsSessionStartTime	OBJECT-TYPE
        SYNTAX			TimeTicks
	MAX-ACCESS		read-only
	STATUS			current
	DESCRIPTION
	       "Login time of this session."
	::= { alHttpStatsSessionEntry 4 }

alHttpStatsSessionLoginTime	OBJECT-TYPE
        SYNTAX			Unsigned32
	MAX-ACCESS		read-only
	STATUS			current
	DESCRIPTION
	       "time_t value of the concentrator at the start of this session."
	::= { alHttpStatsSessionEntry 5 }

alHttpStatsSessionEncr		OBJECT-TYPE
        SYNTAX			EncryptionAlgorithm
	MAX-ACCESS		read-only
	STATUS			current
	DESCRIPTION
	       "The type of encryption algorithm used for this session."
	::= { alHttpStatsSessionEntry 6 }

alHttpStatsSessionOctetsSent	OBJECT-TYPE
        SYNTAX			Counter32
	MAX-ACCESS		read-only
	STATUS			current
	DESCRIPTION
	       "Number of octets sent during this session."
	::= { alHttpStatsSessionEntry 7 }

alHttpStatsSessionOctetsRcvd	OBJECT-TYPE
        SYNTAX			Counter32
	MAX-ACCESS		read-only
	STATUS			current
	DESCRIPTION
	       "Number of octets received during this session."
	::= { alHttpStatsSessionEntry 8 }

alHttpStatsSessionPacketsSent	OBJECT-TYPE
        SYNTAX			Counter32
	MAX-ACCESS		read-only
	STATUS			current
	DESCRIPTION
	       "Number of packets sent during this session."
	::= { alHttpStatsSessionEntry 9 }

alHttpStatsSessionPacketsRcvd	OBJECT-TYPE
        SYNTAX			Counter32
	MAX-ACCESS		read-only
	STATUS			current
	DESCRIPTION
	       "Number of packets received during this session."
	::= { alHttpStatsSessionEntry 10 }

alHttpStatsSessionActiveConnections	OBJECT-TYPE
        SYNTAX			Gauge32
	MAX-ACCESS		read-only
	STATUS			current
	DESCRIPTION
	       "Number of active TCP connections for this session."
	::= { alHttpStatsSessionEntry 11 }

alHttpStatsSessionMaxConnections	OBJECT-TYPE
        SYNTAX			Counter32
	MAX-ACCESS		read-only
	STATUS			current
	DESCRIPTION
	       "Maximum number of active TCP connections for this 
                session at any one time."
	::= { alHttpStatsSessionEntry 12 }

alHttpStatsSessionTotalConnections	OBJECT-TYPE
        SYNTAX			Counter32
	MAX-ACCESS		read-only
	STATUS			current
	DESCRIPTION
	       "Total number of TCP connections for this session."
	::= { alHttpStatsSessionEntry 13 }

altigaHttpStatsMibConformance OBJECT IDENTIFIER ::= { altigaHttpStatsMibModule 1 }
altigaHttpStatsMibCompliances OBJECT IDENTIFIER ::= { altigaHttpStatsMibConformance 1 }

altigaHttpStatsMibCompliance MODULE-COMPLIANCE
   STATUS         current
   DESCRIPTION
      "The compliance statement for agents which 
       implement the Altiga HTTP Statistics MIB."
   MODULE
   MANDATORY-GROUPS { 
      altigaHttpStatsGroup
   }
   ::= { altigaHttpStatsMibCompliances 1 }

altigaHttpStatsGroup OBJECT-GROUP
	OBJECTS
	{
		alHttpStatsOctetsSent,
		alHttpStatsOctetsRcvd,
		alHttpStatsPacketsSent,
		alHttpStatsPacketsRcvd,
		alHttpStatsActiveConnections,
		alHttpStatsMaxConnections,
		alHttpStatsActiveSessions,
		alHttpStatsMaxSessions,
		alHttpStatsTotalConnections,
		alHttpStatsTotalSessions,
		alHttpStatsSessionIndex,
		alHttpStatsSessionName,
		alHttpStatsSessionIpAddr,
		alHttpStatsSessionStartTime,
		alHttpStatsSessionLoginTime,
		alHttpStatsSessionEncr,
		alHttpStatsSessionOctetsSent,
		alHttpStatsSessionOctetsRcvd,
		alHttpStatsSessionPacketsSent,
		alHttpStatsSessionPacketsRcvd,
		alHttpStatsSessionActiveConnections,
		alHttpStatsSessionMaxConnections,
		alHttpStatsSessionTotalConnections
	}
	STATUS 	current
	DESCRIPTION
	       "The objects for HTTP statistics."
	::= { alHttpGroup 2 }

END
