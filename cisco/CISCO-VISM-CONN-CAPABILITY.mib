CISCO-VISM-CONN-CAPABILITY DEFINITIONS ::= BEGIN

IMPORTS
        MODULE-IDENTITY
                FROM SNMPv2-SMI
        AGENT-CAPABILITIES
                FROM SNMPv2-CONF
        ciscoAgentCapability
                FROM CISCO-SMI;

ciscoVismConnCapability MODULE-IDENTITY
        LAST-UPDATED    "200403170000Z"
        ORGANIZATION    "Cisco Systems, Inc."
        CONTACT-INFO
                "       Cisco Systems
                        Customer Service

                Postal: 170 West Tasman Drive
                        San Jose, CA  95134
                        USA

                   Tel: +1 800 553-NETS

                E-mail: cs-wanatm@cisco.com"
        DESCRIPTION
                "The capabilities description of 
                 CISCO-VISM-CONN-MIB."

        REVISION        "200403170000Z"
        DESCRIPTION
                "Initial version of this capability file."
        ::= { ciscoAgentCapability 400 }

cVismConnCapabilityV321 AGENT-CAPABILITIES
    PRODUCT-RELEASE      "Cisco VISM Release 3.2.1"
    STATUS               current
    DESCRIPTION          "CISCO-VISM-CONN-MIB capabilities."

    SUPPORTS             CISCO-VISM-CONN-MIB
        INCLUDES         { ciscoVismConnGroupRev1 }

        VARIATION        vismChanUserMaxPCRBandwidth
            ACCESS       read-only
            DESCRIPTION  "Read only access. The value will be 
                          same as vismConnPCR which is configured
                          by the user."

        VARIATION        vismChanUserMaxScrIngress
            ACCESS       read-only
            DESCRIPTION  "Read only access. The value will be 
                          same as vismChanScrIngress which is 
                          configured by the user."

        VARIATION        vismChanUserMaxMbsIngress
            ACCESS       read-only
            DESCRIPTION  "Read only access. The value will be 
                          same as vismChanMbsIngress which is 
                          configured by the user."

        VARIATION        vismChanUserMinPCRBandwidth
            ACCESS       read-only
            DESCRIPTION  "Read only access. This is computed by 
                          the module and reported in this object."
    ::= { ciscoVismConnCapability 1 }

END
