CISCO-MAC-NOTIFICATION-CAPABILITY DEFINITIONS ::= BEGIN

IMPORTS
        MODULE-IDENTITY,
        Unsigned32
                FROM SNMPv2-SMI

        AGENT-CAPABILITIES
                FROM SNMPv2-CONF

        ciscoAgentCapability
                FROM CISCO-SMI;

ciscoMacNotificationCapability MODULE-IDENTITY
        LAST-UPDATED    "200707090000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of 
                 CISCO-MAC-NOTIFICATION-MIB."
        REVISION        "200707090000Z"
        DESCRIPTION
                "Add capability statement 
                 cmnCapabilityV12R0233SXHPCat6K."
        REVISION        "200402050000Z"
        DESCRIPTION
                "Add capability statement 
                 cmnCapabilityCatOSV08R0301Cat6K and add
                 VARIATION for cmnCapabilityV12R0217SXCat6K." 
        REVISION        "200311120000Z"
        DESCRIPTION
                "Initial version of this MIB module."
        ::= { ciscoAgentCapability 327 }

cmnCapabilityCatOSV08R0101Cat4K AGENT-CAPABILITIES
    PRODUCT-RELEASE     "Cisco CatOS 8.1(1) on Catalyst 4000 series
                        devices."
    STATUS              current
    DESCRIPTION         "CISCO-MAC-NOTIFICATION-MIB agent capabilities."

    SUPPORTS            CISCO-MAC-NOTIFICATION-MIB
        INCLUDES        { cmnGlobalGroup,
                          cmnInterfaceGroup,
                          cmnNotificationGroup
                        }
    ::= { ciscoMacNotificationCapability 1 }

cmnCapabilityCatOSV08R0101Cat6K AGENT-CAPABILITIES
    PRODUCT-RELEASE     "Cisco CatOS 8.1(1) on Catalyst 6000/6500
                        and Cisco 7600 series devices."
    STATUS              current
    DESCRIPTION         "CISCO-MAC-NOTIFICATION-MIB agent capabilities."

    SUPPORTS            CISCO-MAC-NOTIFICATION-MIB
        INCLUDES        { cmnGlobalGroup,
                          cmnInterfaceGroup,
                          cmnNotificationGroup
                        }
        VARIATION       cmnNotificationInterval
        SYNTAX          Unsigned32 (15..4294967295)
        DESCRIPTION     "Only supports value from 15 to 4294967295."
    ::= { ciscoMacNotificationCapability 2 }

cmnCapabilityV12R0217SXCat6K AGENT-CAPABILITIES
    PRODUCT-RELEASE     "Cisco IOS 12.2(17)SX on Catalyst 6000/6500
                         and Cisco 7600 series devices."
    STATUS              current
    DESCRIPTION         "CISCO-MAC-NOTIFICATION-MIB agent capabilities."

    SUPPORTS            CISCO-MAC-NOTIFICATION-MIB
    INCLUDES            { cmnMACMoveGroup,
                          cmnMACThresholdGroup,
                          cmnMACMoveNotifGroup,
                          cmnMACThresholdNotifGroup
                        }
    VARIATION       cmnMACThresholdInterval
    SYNTAX          Unsigned32 (120..1000000)
    DESCRIPTION     "Only supports value from 120 to 1000000."
    ::= { ciscoMacNotificationCapability 3 }

cmnCapabilityCatOSV08R0301Cat6K AGENT-CAPABILITIES
    PRODUCT-RELEASE     "Cisco CatOS 8.3(1) on Catalyst 6000/6500
                        and Cisco 7600 series devices."
    STATUS              current
    DESCRIPTION         "CISCO-MAC-NOTIFICATION-MIB agent capabilities."

    SUPPORTS            CISCO-MAC-NOTIFICATION-MIB
    INCLUDES            { cmnGlobalGroup,
                          cmnInterfaceGroup,
                          cmnNotificationGroup,
                          cmnMACMoveGroup,
                          cmnMACThresholdGroup,
                          cmnMACMoveNotifGroup,
                          cmnMACThresholdNotifGroup
                        }
    VARIATION       cmnNotificationInterval
    SYNTAX          Unsigned32 (15..4294967295)
    DESCRIPTION     "Only supports value from 15 to 4294967295."

    VARIATION       cmnMACThresholdInterval
    SYNTAX          Unsigned32 (120..4294967295)
    DESCRIPTION     "Only supports value from 120 to 4294967295."
    ::= { ciscoMacNotificationCapability 4 }

cmnCapabilityV12R0233SXHPCat6K AGENT-CAPABILITIES
    PRODUCT-RELEASE     "Cisco IOS 12.2(33)SXH on Catalyst 6000/6500."
    STATUS              current
    DESCRIPTION         "CISCO-MAC-NOTIFICATION-MIB agent capabilities."

    SUPPORTS            CISCO-MAC-NOTIFICATION-MIB
       INCLUDES            { cmnMACMoveGroup,
                             cmnMACThresholdGroup,
                             cmnMACMoveNotifGroup,
                             cmnMACThresholdNotifGroup,
                             cmnGlobalGroup,
                             cmnInterfaceGroup,
                             cmnNotificationGroup
                           }
       VARIATION       cmnMACThresholdInterval
          SYNTAX          Unsigned32 (120..1000000)
          DESCRIPTION     "Only limited set of values are supported."

       VARIATION       cmnNotificationInterval
          SYNTAX          Unsigned32 (0..2147483647)
          DESCRIPTION     "Only limited set of values are supported."
    ::= { ciscoMacNotificationCapability 5 }
END
