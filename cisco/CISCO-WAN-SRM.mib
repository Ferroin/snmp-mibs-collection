CISCO-WAN-SRM-MIB DEFINITIONS ::= BEGIN
IMPORTS
        MODULE-IDENTITY,
        OBJECT-TYPE, 
        Integer32       FROM    SNMPv2-SMI
        MODULE-COMPLIANCE,
        OBJECT-GROUP    FROM    SNMPv2-CONF
        cardSpecific    FROM    BASIS-MIB
        ciscoWan        FROM    CISCOWAN-SMI;

ciscoWanSrmMIB MODULE-IDENTITY
        LAST-UPDATED    "200208260000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "The MIB module for configuration of bulk distribution
         (de-multiplexing of traffic from higher-bandwidth to
         lower-bandwidth interfaces).
         This is used for configuring bulk distribution of
         T3 interfaces on T1 modules supported in MGX82xx series.
         Some of the T1 modules are AUSM, FRSM,CESM.
         This MIB module also contains info. on configuring
         bulk distribution of SONET interfaces(VT interfaces)
         on T1 Modules.

         SRM  - Service Resource Module
         SRME - Service Resource Module Enhanced."

    REVISION    "200208260000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been 
        modified."
    ::= { ciscoWan 30 }

srm3T3CnfGrp          OBJECT IDENTIFIER ::= {cardSpecific 10}
srmeCnfGrp            OBJECT IDENTIFIER ::= {cardSpecific 22}

-- *******************************************************************
-- 
-- srm3T3CnfGrpTable:
-- This table contains DS1 mapping configuration for SRM-3T3 card. 
-- This group is card specific for SRM-3T3 card.
-- 
-- *******************************************************************

srm3T3CnfGrpTable OBJECT-TYPE
	SYNTAX	SEQUENCE OF Srm3T3CnfGrpEntry
	MAX-ACCESS	not-accessible
	STATUS	current
	DESCRIPTION
		"The SRM 3T3 configuration table, it is the
		 distribution of a T3 line.
		"
	::= { srm3T3CnfGrp 1 }

srm3T3CnfGrpEntry OBJECT-TYPE
	SYNTAX	Srm3T3CnfGrpEntry
	MAX-ACCESS	not-accessible
	STATUS	current
	DESCRIPTION
		"an entry in the T3 configuration table
		"
	INDEX	{ srmT3LineNum, srmStartT1LineNum }
	::= { srm3T3CnfGrpTable 1 }

Srm3T3CnfGrpEntry ::=
	SEQUENCE {
		srmT3LineNum          Integer32,
		srmStartT1LineNum     Integer32,
		srmT1RowStatus        INTEGER,
		srmTargetSlotNum      Integer32,
		srmTargetSlotLineNum  Integer32
		}

srmT3LineNum   OBJECT-TYPE
    SYNTAX Integer32 (1..3)
    MAX-ACCESS read-only
    STATUS current
    DESCRIPTION
    "Select T3 line number.
     There is no default value for this object."
    ::= { srm3T3CnfGrpEntry 1 }

srmStartT1LineNum OBJECT-TYPE
    SYNTAX Integer32 (1..28) 
    MAX-ACCESS read-only
    STATUS current
    DESCRIPTION
    "The start T1 number to be affected.
     There is no default value for this object."
    ::= { srm3T3CnfGrpEntry 2 }

srmT1RowStatus OBJECT-TYPE
    SYNTAX INTEGER { 
        add    (1),
        delete (2),
        modify (3)
        }
    MAX-ACCESS read-write
    STATUS current
    DESCRIPTION
    "a command is used to add, delete, or modify
     one or more DS1 mapping. 
     Default value is delete."
    ::= { srm3T3CnfGrpEntry 3 }

srmTargetSlotNum OBJECT-TYPE
    SYNTAX Integer32 (1..32) 
    MAX-ACCESS read-write
    STATUS current
    DESCRIPTION
    " specify the target slot number to be linked.
     There is no default value for this object.
     For MGX8850:    SRM01 services slots 1 - 6 and 9 - 14,
                     SRM02 services slots 17 - 22 and 25 - 30
     For MGX8220: SYNTAX  Integer32 (5 ..14)
     "
    ::= { srm3T3CnfGrpEntry 4 }

srmTargetSlotLineNum OBJECT-TYPE
    SYNTAX Integer32 (0..8) 
    MAX-ACCESS read-write
    STATUS current
    DESCRIPTION
    "0 means not assigned.
     There is no default value for this object."
    ::= { srm3T3CnfGrpEntry 5 }

-- *******************************************************************
-- 
-- srmeCnfGrpTable:
-- This table contains DS1 and E1 mapping configuration for SRME card. 
-- This group is card specific for SRME card.
-- 
-- *******************************************************************

srmeCnfGrpTable OBJECT-TYPE
	SYNTAX	SEQUENCE OF SrmeCnfGrpEntry
	MAX-ACCESS	not-accessible
	STATUS	current
	DESCRIPTION
	    "The SRME configuration table for bulk distribution of
             SRME lines."
	::= { srmeCnfGrp 1 }

srmeCnfGrpEntry OBJECT-TYPE
	SYNTAX	SrmeCnfGrpEntry
	MAX-ACCESS	not-accessible
	STATUS	current
	DESCRIPTION
	    "an entry in the SRME Distribution configuration table"
	INDEX	{ srmeLineNum, srmeStartVtNum }
	::= { srmeCnfGrpTable 1 }

SrmeCnfGrpEntry ::=
	SEQUENCE {
		srmeLineNum            Integer32,
		srmeStartVtNum         Integer32,
		srmeRowStatus          INTEGER,
		srmeTargetSlotNum      Integer32,
		srmeTargetSlotLineNum  Integer32,
                srmeVtFramingType      INTEGER
		}

srmeLineNum   OBJECT-TYPE
    SYNTAX Integer32 (1..3)
    MAX-ACCESS read-only
    STATUS current
    DESCRIPTION
        "This object identifies the SRME line number.
        For OC3/STM1: SYNTAX Integer32 1
        There is no default value for this object."
    ::= { srmeCnfGrpEntry 1 }

srmeStartVtNum OBJECT-TYPE
    SYNTAX Integer32 (1..84) 
    MAX-ACCESS read-only
    STATUS current
    DESCRIPTION
        "The start T1 or E1 number (virtual tributary) to be affected.
        For OC3  with T1 tributaries: SYNTAX Integer32 (1 .. 84)
        For STM1 with E1 tributaries: SYNTAX Integer32 (1 .. 63) 
        There is no default value for this object."
    ::= { srmeCnfGrpEntry 2 }

srmeRowStatus OBJECT-TYPE
    SYNTAX INTEGER { 
        add    (1),
        delete (2),
        modify (3)
        }
    MAX-ACCESS read-write
    STATUS current
    DESCRIPTION
        "Command used to add, delete, or modify
        one or more T1 or E1 mappings. Only the 
        srmeVtFramingType object can be modified once the
        distribution link is added. To modify all other
        objects, user should first delete the link and 
        add it again.

        Default value is modify(3)."
    ::= { srmeCnfGrpEntry 3 }

srmeTargetSlotNum OBJECT-TYPE
    SYNTAX Integer32 (1..32) 
    MAX-ACCESS read-write
    STATUS current
    DESCRIPTION
        "This object specifies the target slot number to be linked.
        There is no default value for this object.
        For MGX8x50:    SRM01 services slots 1 - 6 and 9 - 14,
                        SRM02 services slots 17 - 22 and 25 - 30
        For MGX8x30:    service slots 3-6 and 10-13."
    ::= { srmeCnfGrpEntry 4 }

srmeTargetSlotLineNum OBJECT-TYPE
    SYNTAX Integer32 (0..8) 
    MAX-ACCESS read-write
    STATUS current
    DESCRIPTION
        "Specify the target slot's line to be linked.
        The value zero means, the target line number is 
        not assigned.
        There is no default value for this object."
    ::= { srmeCnfGrpEntry 5 }

srmeVtFramingType OBJECT-TYPE
    SYNTAX INTEGER {
        notApplicable (1),
        sf            (2),
        esf           (3)
        }
    MAX-ACCESS read-write
    STATUS current
    DESCRIPTION
        "Specifies the Framing Type of the target slot line.
        This is applicable only if the target module is a
        T1 Service Module and byte sync mapping is used on
        SRME. Not applicable to E1 Service Modules.

        sf: Superframe or D4
        esf: Extended Superframe. 

        Default is 'esf' if SRME lines are configured for 
        byte-synchronous mapping, Else, the default is notApplicable."
    ::= { srmeCnfGrpEntry 6 }

-- conformance information

ciscoWanSrmMIBConformance  OBJECT IDENTIFIER ::= { ciscoWanSrmMIB 2 }

ciscoWanSrmMIBGroups       OBJECT IDENTIFIER ::= { ciscoWanSrmMIBConformance 1 }

ciscoWanSrmMIBCompliances  OBJECT IDENTIFIER ::= { ciscoWanSrmMIBConformance 2 }

-- compliance statements

ciscoWanSrmCompliance MODULE-COMPLIANCE
    STATUS  current
    DESCRIPTION
        "The compliance statement for objects related
        to SRM MIB."
    MODULE  -- this module

    GROUP ciscoWanSrmConfGroup
    DESCRIPTION
        "This group is mandatory for those products
        where SRM is used for bulk distribution."

    GROUP ciscoWanSrmeConfGroup
    DESCRIPTION
        "This group is mandatory for those products
        where SRM-E is used for bulk distribution."
    ::= { ciscoWanSrmMIBCompliances 1 }

ciscoWanSrmConfGroup OBJECT-GROUP
    OBJECTS {
        srmT3LineNum,
	srmStartT1LineNum, 
	srmT1RowStatus,
	srmTargetSlotNum,
	srmTargetSlotLineNum 
      }
      STATUS current
      DESCRIPTION
          "The collection of objects which are used for
          configuring bulk distribution for SRM module."
      ::= { ciscoWanSrmMIBGroups 1 }

ciscoWanSrmeConfGroup OBJECT-GROUP
    OBJECTS {
        srmeLineNum,
	srmeStartVtNum, 
	srmeRowStatus, 
	srmeTargetSlotNum,
	srmeTargetSlotLineNum,
        srmeVtFramingType
      }
      STATUS current
      DESCRIPTION
          "The collection of objects which are used for
          configuring bulk distribution for SRM-E module."
      ::= { ciscoWanSrmMIBGroups 2 }

END
