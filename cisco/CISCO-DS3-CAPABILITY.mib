CISCO-DS3-CAPABILITY DEFINITIONS ::= BEGIN
IMPORTS
        MODULE-IDENTITY
                FROM SNMPv2-SMI
        AGENT-CAPABILITIES
                FROM SNMPv2-CONF
        ciscoAgentCapability
                FROM CISCO-SMI;

ciscoDs3Capability MODULE-IDENTITY
        LAST-UPDATED    "200405060000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for DS3-MIB(RFC 2496)."

        REVISION "200405060000Z"
        DESCRIPTION
            "Modified MPSM agent capability description."

        REVISION "200312220000Z"
        DESCRIPTION
            "Added ciscoDs3CapabilityV5R00."

        REVISION "200303120000Z"
        DESCRIPTION
            "Added ciscoDs3CapabilityV4R00 for modules:
             10 Gig. ATM Switch Service Module(AXSM-XG),
             AXSM Service Module Enhanced(AXSM-E) and 
             Processor Switch Module Enhanced(PXM1E)
             controller card."

        REVISION "200205010000Z"
        DESCRIPTION
            "Initial version of this MIB module."
        ::= { ciscoAgentCapability 265 }

ciscoDs3CapabilityV2R0100 AGENT-CAPABILITIES

PRODUCT-RELEASE "MGX8850 Release 2.1.00"
STATUS          current
DESCRIPTION     "DS3 MIB Capabilities for Following Modules:
                ATM Switch Service Module(AXSM).
                AXSM-E(AXSM Enhanced)."

SUPPORTS    DS3-MIB
INCLUDES { ds3NearEndConfigGroup,
           ds3NearEndStatisticsGroup,
           ds3NearEndOptionalConfigGroup
         }

VARIATION    dsx3LineType
ACCESS       read-only
DESCRIPTION  "Write access is not supported."

VARIATION    dsx3LoopbackConfig
SYNTAX       INTEGER { 
                dsx3NoLoop(1), 
                dsx3LineLoop(3),
                dsx3InwardLoop(5) 
             }
DESCRIPTION  "Does not support values dsx3PayloadLoop(2),
             dsx3OtherLoop(4) and dsx3DualLoop(6)."

VARIATION    dsx3TransmitClockSource
SYNTAX       INTEGER { 
                loopTiming(1), 
                localTiming(2) 
             }
DESCRIPTION  "Does not support value throughTiming(3). "

VARIATION    dsx3LineStatusLastChange
DESCRIPTION  "The value does not get updated.
             Always returns value 0."

VARIATION    dsx3LineStatusChangeTrapEnable
DESCRIPTION  "Read always returns disabled(2).
             Write operation is ignored."

VARIATION    dsx3Channelization
ACCESS       read-only
DESCRIPTION  "Write access is not supported."

VARIATION    dsx3Ds1ForRemoteLoop
ACCESS       not-implemented
DESCRIPTION  "Not supported."
    ::= { ciscoDs3Capability 1 }

ciscoDs3CapabilitySrmV3R00 AGENT-CAPABILITIES

PRODUCT-RELEASE "MGX8850 Release 3.0.00"
STATUS          current
DESCRIPTION     "DS3 MIB Capabilities for
                Service Resource Module(SRM)."

SUPPORTS DS3-MIB
INCLUDES { ds3NearEndConfigGroup,
           ds3NearEndStatisticsGroup,
           ds3NearEndOptionalConfigGroup
         }

VARIATION    dsx3TimeElapsed
ACCESS       not-implemented
DESCRIPTION  "Not supported."

VARIATION    dsx3ValidIntervals
ACCESS       not-implemented
DESCRIPTION  "Not supported."

VARIATION    dsx3LineType
SYNTAX       INTEGER { 
                dsx3M23(2), 
                dsx3CbitParity(4) 
             }
DESCRIPTION  "Does not support values dsx3other(1),
             dsx3SYNTRAN(3), dsx3ClearChannel(5),
             e3other(6), e3Framed(7) and e3Plcp(8)."

VARIATION    dsx3LineCoding
SYNTAX       INTEGER { 
                dsx3B3ZS(2), 
                e3HDB3(3) 
             }
DESCRIPTION  "Does not support value dsx3Other(1)."       

VARIATION    dsx3CircuitIdentifier
ACCESS       not-implemented
DESCRIPTION  "Not supported."

VARIATION    dsx3LoopbackConfig
SYNTAX       INTEGER { 
                dsx3NoLoop(1), 
                dsx3PayloadLoop(2),
                dsx3LineLoop(3), 
                dsx3InwardLoop(5) 
             }
DESCRIPTION  "Does not support values dsx3OtherLoop(4)
             and dsx3DualLoop(6)."

VARIATION    dsx3TransmitClockSource
SYNTAX       INTEGER { 
                loopTiming(1), 
                localTiming(2) 
             }
DESCRIPTION  "Does not support value throughTiming(3)."

VARIATION    dsx3InvalidIntervals
ACCESS       not-implemented
DESCRIPTION  "Not supported."

VARIATION    dsx3LineStatusLastChange
DESCRIPTION  "The value does not get updated.
             Always returns value 0."

VARIATION    dsx3LineStatusChangeTrapEnable
DESCRIPTION  "Read always returns disabled(2).
             Write operation is ignored."

VARIATION    dsx3LoopbackStatus
ACCESS       not-implemented
DESCRIPTION  "Not supported."

VARIATION    dsx3Channelization
ACCESS       read-only
DESCRIPTION  "Write access is not supported."
    ::= { ciscoDs3Capability 2 }

ciscoDs3CapabilityPxm1eV3R00 AGENT-CAPABILITIES

PRODUCT-RELEASE "MGX8850 Release 3.0.00"
STATUS          current
DESCRIPTION     "DS3 MIB Capabilities for
                 Processor Switch Module Enhanced (PXM1E)
                 controller card."

SUPPORTS DS3-MIB
INCLUDES { ds3NearEndConfigGroup,
           ds3NearEndStatisticsGroup,
           ds3NearEndOptionalConfigGroup
         }

VARIATION    dsx3LineType
ACCESS       read-only
DESCRIPTION  "Write access is not supported."

VARIATION    dsx3CircuitIdentifier
ACCESS       read-only
DESCRIPTION  "Agent always returns 0 length string."

VARIATION    dsx3LoopbackConfig
SYNTAX       INTEGER { 
                dsx3NoLoop(1), 
                dsx3LineLoop(3),
                dsx3InwardLoop(5)
             }
DESCRIPTION  "Does not support values dsx3PayloadLoop(2),
             dsx3OtherLoop(4) and dsx3DualLoop(6)."

VARIATION    dsx3TransmitClockSource
SYNTAX       INTEGER { 
                loopTiming(1), 
                localTiming(2) 
             }
DESCRIPTION  "Does not support value throughTiming(3). "

VARIATION    dsx3LineStatusLastChange
DESCRIPTION  "The value does not get updated.
             Always returns value 0."

VARIATION    dsx3LineStatusChangeTrapEnable
DESCRIPTION  "Read always returns disabled(2).
             Write operation is ignored."

VARIATION    dsx3Channelization
ACCESS       read-only
DESCRIPTION  "Write access is not supported."

VARIATION    dsx3Ds1ForRemoteLoop
ACCESS       read-only
DESCRIPTION  "Agent always returns value 0."
    ::= { ciscoDs3Capability 3 }

ciscoDs3CapabilityV4R00 AGENT-CAPABILITIES

PRODUCT-RELEASE "MGX8950 and MGX8850 Release 4.0.00"
STATUS          current
DESCRIPTION     "DS3 MIB Capabilities for Modules:
                10 Gig. ATM Switch Service Module(AXSM-XG),
                AXSM Service Module Enhanced(AXSM-E) and 
                Processor Switch Module Enhanced(PXM1E)
                controller card."

SUPPORTS    DS3-MIB
INCLUDES { ds3NearEndConfigGroup,
           ds3NearEndStatisticsGroup,
           ds3NearEndOptionalConfigGroup,
           ds3FarEndGroup
         }

--
-- Variations applicable for AXSM-E, AXSM-XG, PXM1E.
--

VARIATION    dsx3LineType
ACCESS       read-only
DESCRIPTION  "Write access is not supported."

VARIATION    dsx3LineCoding
ACCESS       read-only
DESCRIPTION  "Write access is not supported."

VARIATION    dsx3LoopbackConfig
SYNTAX       INTEGER { 
                dsx3NoLoop(1), 
                dsx3LineLoop(3),
                dsx3InwardLoop(5) 
             }
DESCRIPTION  "Does not support values dsx3PayloadLoop(2),
             dsx3OtherLoop(4) and dsx3DualLoop(6)."

VARIATION    dsx3TransmitClockSource
SYNTAX       INTEGER { 
                loopTiming(1), 
                localTiming(2)
             }
DESCRIPTION  "Does not support value throughTiming(3). "

VARIATION    dsx3Channelization
ACCESS       read-only
DESCRIPTION  "Write access is not supported."

VARIATION    dsx3Ds1ForRemoteLoop
ACCESS       not-implemented
DESCRIPTION  "Not supported."

VARIATION    dsx3LineStatusLastChange
DESCRIPTION  "The value does not get updated.
             Always returns value 0."

VARIATION    dsx3LineStatusChangeTrapEnable
DESCRIPTION  "Read always returns disabled(2).
             Write operation is ignored."

VARIATION    dsx3FarEndConfigTable
-- ACCESS    not-implemented
DESCRIPTION  "This table is not supported."

--
--  Variations applicable for AXSM-XG
--

VARIATION    dsx3LineLength
ACCESS       read-only
DESCRIPTION  "Write access not supported."

VARIATION    dsx3CurrentPESs
ACCESS       not-implemented
DESCRIPTION  "Not supported."

VARIATION    dsx3CurrentPSESs
ACCESS       not-implemented
DESCRIPTION  "Not supported."

VARIATION    dsx3CurrentSEFSs
ACCESS       not-implemented
DESCRIPTION  "Not supported."

VARIATION    dsx3CurrentLCVs
ACCESS       not-implemented
DESCRIPTION  "Not supported."

VARIATION    dsx3CurrentPCVs
ACCESS       not-implemented
DESCRIPTION  "Not supported."

VARIATION    dsx3CurrentLESs
ACCESS       not-implemented
DESCRIPTION  "Not supported."

VARIATION    dsx3IntervalPESs
ACCESS       not-implemented
DESCRIPTION  "Not supported."

VARIATION    dsx3IntervalPSESs
ACCESS       not-implemented
DESCRIPTION  "Not supported."

VARIATION    dsx3IntervalSEFSs
ACCESS       not-implemented
DESCRIPTION  "Not supported."

VARIATION    dsx3IntervalLCVs
ACCESS       not-implemented
DESCRIPTION  "Not supported."

VARIATION    dsx3IntervalPCVs
ACCESS       not-implemented
DESCRIPTION  "Not supported."

VARIATION    dsx3IntervalLESs
ACCESS       not-implemented
DESCRIPTION  "Not supported."

VARIATION    dsx3TotalPESs
ACCESS       not-implemented
DESCRIPTION  "Not supported."

VARIATION    dsx3TotalPSESs
ACCESS       not-implemented
DESCRIPTION  "Not supported."

VARIATION    dsx3TotalSEFSs
ACCESS       not-implemented
DESCRIPTION  "Not supported."

VARIATION    dsx3TotalLCVs
ACCESS       not-implemented
DESCRIPTION  "Not supported."

VARIATION    dsx3TotalPCVs
ACCESS       not-implemented
DESCRIPTION  "Not supported."

VARIATION    dsx3TotalLESs
ACCESS       not-implemented
DESCRIPTION  "Not supported."
    ::= { ciscoDs3Capability 4 }

ciscoDs3CapabilityV5R00 AGENT-CAPABILITIES

PRODUCT-RELEASE "MGX8850 Release 5.0.0"
STATUS          current
DESCRIPTION     "DS3 MIB capabilities for Voice Switch 
                 Service Module(VXSM) and MPSM in release
                 5.0.0"

--
-- VXSM VARIATION
--
SUPPORTS DS3-MIB
INCLUDES { ds3NearEndConfigGroup,
           ds3NearEndStatisticsGroup,
           ds3NearEndOptionalConfigGroup
         }
--
-- MPSM VARIATION
--
SUPPORTS DS3-MIB
INCLUDES { ds3NearEndConfigGroup,
           ds3NearEndStatisticsGroup,
           ds3NearEndOptionalConfigGroup,
           ds3FarEndGroup
         }

--
-- VXSM VARIATION
--
VARIATION    dsx3LineCoding
ACCESS       not-implemented
DESCRIPTION  "Not supported."

--
-- MPSM VARIATION
--
VARIATION    dsx3LineCoding
ACCESS       read-only
DESCRIPTION  "Set is not supported."

--
-- VXSM VARIATION
--
VARIATION    dsx3LineLength
ACCESS       not-implemented
DESCRIPTION  "Not supported."

--
-- MPSM VARIATION
--
VARIATION    dsx3LineLength
DESCRIPTION  "MPSM does not support write access on
              DS3 paths."

--
-- VXSM VARIATION
--
VARIATION    dsx3CircuitIdentifier
ACCESS       not-implemented
DESCRIPTION  "Not supported."

VARIATION    dsx3LineStatusLastChange
ACCESS       not-implemented
DESCRIPTION  "Not supported."

VARIATION    dsx3LineStatusChangeTrapEnable
ACCESS       not-implemented
DESCRIPTION  "Not supported."

VARIATION    dsx3Ds1ForRemoteLoop
ACCESS       not-implemented
DESCRIPTION  "Not supported."

--
-- VXSM VARIATION
--
VARIATION    dsx3LineType
SYNTAX       INTEGER { dsx3M23(2), 
                       dsx3CbitParity(4)
                     }
DEFVAL       { dsx3M23 }
DESCRIPTION  "dsx3other(1),
              dsx3SYNTRAN(3),
              dsx3ClearChannel(5),
              e3other(6),
              e3Framed(7),
              e3Plcp(8),
              dsx3M13(9) are not supported."

--
-- MPSM VARIATION
--
VARIATION    dsx3LineType
ACCESS       read-only
DESCRIPTION  "Set is not supported."

--
-- VXSM VARIATION
--
VARIATION    dsx3SendCode
SYNTAX       INTEGER { dsx3SendNoCode   (1), 
                       dsx3SendLineCode (2),
                       dsx3SendResetCode(4) }
DEFVAL       { dsx3SendNoCode }
DESCRIPTION  "dsx3SendPayloadCode(3),
              dsx3SendDS1LoopCode(5),
              dsx3SendTestPattern(6) are not supported."

--
-- MPSM VARIATION
--
VARIATION    dsx3SendCode
ACCESS       read-only
DESCRIPTION  "Set is not supported."

VARIATION    dsx3LoopbackConfig
SYNTAX       INTEGER { dsx3NoLoop    (1),
                       dsx3LineLoop  (3),
                       dsx3InwardLoop(5) }
DEFVAL       { dsx3NoLoop }
DESCRIPTION  "dsx3PayloadLoop(2),
              dsx3OtherLoop(4),
              dsx3DualLoop(6) are not supported."

--
-- VXSM Variation
--
VARIATION    dsx3TransmitClockSource
ACCESS       read-only
DESCRIPTION  "Set is not allowed"

--
-- MPSM Variation
--
VARIATION    dsx3TransmitClockSource
SYNTAX       INTEGER { loopTiming(1), localTiming(2) }   
DESCRIPTION  "Does not support value throughTiming(3)." 

--
-- VXSM Variation
--
VARIATION    dsx3Channelization
SYNTAX       INTEGER { enabledDs1 (2) }
ACCESS       read-only
DESCRIPTION  "disabled(1) and enabledDs2(3) are not supported.
              Set is not allowed"

--
-- MPSM Variation
--
VARIATION    dsx3Channelization
SYNTAX       INTEGER { disabled(1), enabledDs1(2) }  
DESCRIPTION  "Does not support value enabledDs2(3)."

VARIATION    dsx3LineStatus
DESCRIPTION  "Use bit 512 (dsx3OtherFailure) for BERT"
    ::= { ciscoDs3Capability 5 }

END
