CISCO-DS1-CAPABILITY DEFINITIONS ::= BEGIN

IMPORTS
    MODULE-IDENTITY
        FROM SNMPv2-SMI
    AGENT-CAPABILITIES
        FROM SNMPv2-CONF
    ciscoAgentCapability
        FROM CISCO-SMI
    DisplayString 
        FROM SNMPv2-TC;

ciscoDs1Capability MODULE-IDENTITY
    LAST-UPDATED    "200710310000Z"
    ORGANIZATION    "Cisco Systems, Inc."
    CONTACT-INFO
            "Cisco Systems
            Customer Service

            Postal: 170 W Tasman Drive
            San Jose, CA  95134
            USA

            Tel: +1 800 553-NETS

            E-mail: cs-wanatm@cisco.com"
    DESCRIPTION
        "The agent capabilities for DS1-MIB for Cisco Products Series.
        - ciscoDs1AxsmeCapabilityV3R00 is for
          Enhanced ATM Switch Service Module(AXSM-E), and
          Enhanced Processor Switch Module 1(PXM1E) uplink.

        - ciscoDs1CapabilityV5R00 is for Voice Switch
          Service Module(VXSM) and MPSM Module Release 5.0.0."

    REVISION        "200710310000Z"
    DESCRIPTION
        "Added VARIATION for dsx1LineStatusChangeTrapEnable to
        agent capability statement ciscoDs1CapabilityMARsV12R5T
        and ciscoDs1CapabilityAS5xxxV12R5T"
    REVISION        "200709100000Z"
    DESCRIPTION
        "Added ciscoDs1CapabilityV5R500 for defining capability for
         VXSM support in MGX8880 release 5.5.0."
    REVISION        "200705110000Z"
    DESCRIPTION
        "Added ciscoDs1CapabilityMARsV12R5T for 2800, 3800, 3700 series
        routers and IAD2430 platforms. 
        Added ciscoDs1CapabilityAS5xxxV12R5T for AS5xxx platforms."
    REVISION        "200606160000Z"
    DESCRIPTION
        "Added ciscoDs1CapabilityV5R310 for VXSM support in
        MGX8880 release 5.3.1."
    REVISION        "200507110000Z"
    DESCRIPTION
        "Added ciscoDs1CapabilityV5R100 for MPSM and VXSM support in
        MGX8880 release 5.1.0."
    REVISION        "200312220000Z"
    DESCRIPTION
        "ciscoDs1CapabilityV5R00 added for MPSM and VXSM support."
    REVISION        "200204280000Z"
    DESCRIPTION
        "Initial version of this MIB module."
          ::= { ciscoAgentCapability 273 }

ciscoDs1AxsmeCapabilityV3R00 AGENT-CAPABILITIES
    PRODUCT-RELEASE "MGX8850 Release 3.0"
    STATUS          current
    DESCRIPTION     "DS1-MIB Capabilities."

    SUPPORTS        DS1-MIB
    INCLUDES        {
                        ds1NearEndConfigGroup,
                        ds1NearEndStatisticsGroup,
                        ds1FarEndGroup
                    }
    VARIATION       dsx1LineType
    SYNTAX          INTEGER  {
                        dsx1ESF(2),
                        dsx1E1CRCMF(7)
                    }
    ACCESS          read-only
    DESCRIPTION
        "Supported with limitation.
        dsx1ESF(2)     used only for T1 mode,
        dsx1E1CRCMF(7) used only for E1 mode."

    VARIATION       dsx1LineCoding
    SYNTAX          INTEGER  {
                        dsx1B8ZS(2),
                        dsx1HDB3(3)
                    }
    ACCESS          read-only
    DESCRIPTION
        "Supported with limitation.
        dsx1B8ZS(2)    used only for T1 mode,
        dsx1HDB3(3)    used only for E1 mode."

    VARIATION       dsx1SendCode
    ACCESS          not-implemented
    DESCRIPTION     "Not Supported."

    VARIATION       dsx1CircuitIdentifier
    ACCESS          not-implemented
    DESCRIPTION     "Not Supported."

    VARIATION       dsx1LoopbackConfig
    SYNTAX          INTEGER  {
                        dsx1NoLoop(1),
                        dsx1LineLoop(3),
                        dsx1InwardLoop(5)
                    }
    DESCRIPTION     "Supported with limitation."

    VARIATION       dsx1SignalMode
    ACCESS          not-implemented
    DESCRIPTION     "Not Supported."

    VARIATION       dsx1Fdl
    ACCESS          not-implemented
    DESCRIPTION     "Not Supported."

    VARIATION       dsx1LineStatusLastChange
    ACCESS          not-implemented
    DESCRIPTION     "Not Supported."

    VARIATION       dsx1LineStatusChangeTrapEnable
    ACCESS          not-implemented
    DESCRIPTION     "Not Supported."

    VARIATION       dsx1LoopbackStatus
    DESCRIPTION
        "The agent only sets following bits:
        1  dsx1NoLoopback
        16  dsx1NearEndInwardLoopback
        64  dsx1FarEndLineLoopback."

    VARIATION       dsx1Ds1ChannelNumber
    ACCESS          not-implemented
    DESCRIPTION     "Not Supported."

    VARIATION       dsx1Channelization
    ACCESS          not-implemented
    DESCRIPTION     "Not Supported."

    VARIATION       dsx1CurrentCSSs
    ACCESS          not-implemented
    DESCRIPTION     "Not Supported."

    VARIATION       dsx1CurrentBESs
    ACCESS          not-implemented
    DESCRIPTION     "Not Supported."

    VARIATION       dsx1CurrentDMs
    ACCESS          not-implemented
    DESCRIPTION     "Not Supported."

    VARIATION       dsx1IntervalCSSs
    ACCESS          not-implemented
    DESCRIPTION     "Not Supported."

    VARIATION       dsx1IntervalBESs
    ACCESS          not-implemented
    DESCRIPTION     "Not Supported."

    VARIATION       dsx1IntervalDMs
    ACCESS          not-implemented
    DESCRIPTION     "Not Supported."

    VARIATION       dsx1TotalCSSs
    ACCESS          not-implemented
    DESCRIPTION     "Not Supported."

    VARIATION       dsx1TotalBESs
    ACCESS          not-implemented
    DESCRIPTION     "Not Supported."

    VARIATION       dsx1TotalDMs
    ACCESS          not-implemented
    DESCRIPTION     "Not Supported."

    VARIATION       dsx1FarEndCurrentCSSs
    ACCESS          not-implemented
    DESCRIPTION     "Not Supported."

    VARIATION       dsx1FarEndCurrentBESs
    ACCESS          not-implemented
    DESCRIPTION     "Not Supported."

    VARIATION       dsx1FarEndCurrentDMs
    ACCESS          not-implemented
    DESCRIPTION     "Not Supported."

    VARIATION       dsx1FarEndIntervalCSSs
    ACCESS          not-implemented
    DESCRIPTION     "Not Supported."

    VARIATION       dsx1FarEndIntervalBESs
    ACCESS          not-implemented
    DESCRIPTION     "Not Supported."

    VARIATION       dsx1FarEndIntervalDMs
    ACCESS          not-implemented
    DESCRIPTION     "Not Supported."

    VARIATION       dsx1FarEndTotalCSSs
    ACCESS          not-implemented
    DESCRIPTION     "Not Supported."

    VARIATION       dsx1FarEndTotalBESs
    ACCESS          not-implemented
    DESCRIPTION     "Not Supported."

    VARIATION       dsx1FarEndTotalDMs
    ACCESS          not-implemented
    DESCRIPTION     "Not Supported."
    ::= { ciscoDs1Capability 1 }

ciscoDs1CapabilityV5R00 AGENT-CAPABILITIES
    PRODUCT-RELEASE "MGX8850 Release 5.0.0"
    STATUS          current
    DESCRIPTION
        "DS1 MIB capabilities for VXSM and
        MPSM in release 5.0.0"

    SUPPORTS        DS1-MIB
    INCLUDES        {
                        ds1NearEndConfigGroup,
                        ds1NearEndStatisticsGroup,
                        ds1FarEndGroup,
                        ds1NearEndOptionalConfigGroup
                    }
    VARIATION       dsx1LineCoding
    DESCRIPTION
        "Only supported by T1/E1 card
        (entPhysicalVendorType is cevVxsm48t1e1)."

    VARIATION       dsx1LineLength
    SYNTAX          INTEGER (0..200)
    DESCRIPTION
        "Supported with limited length only by T1/E1 card 
        (entPhysicalVendorType is cevVxsm48t1e1), 
        for T1 only." 

    VARIATION       dsx1CircuitIdentifier
    ACCESS          not-implemented
    DESCRIPTION     "Not supported."

    VARIATION       dsx1LineStatusLastChange
    ACCESS          not-implemented
    DESCRIPTION     "Not supported."

    VARIATION       dsx1Ds1ChannelNumber
    ACCESS          not-implemented
    DESCRIPTION     "Not supported."

    VARIATION       dsx1LineMode
    DESCRIPTION
        "Only supported by T1/E1 card
        (entPhysicalVendorType is cevVxsm48t1e1),
        for T1 only."

    VARIATION       dsx1LineBuildOut
    DESCRIPTION
        "Only supported by T1/E1 card
        (entPhysicalVendorType is cevVxsm48t1e1),
        for T1 only."

    VARIATION       dsx1CurrentDMs
    ACCESS          not-implemented
    DESCRIPTION     "Not supported."

    VARIATION       dsx1IntervalDMs
    ACCESS          not-implemented
    DESCRIPTION     "Not supported."

    VARIATION       dsx1TotalDMs
    ACCESS          not-implemented
    DESCRIPTION     "Not supported."

    VARIATION       dsx1FarEndCurrentDMs
    ACCESS          not-implemented
    DESCRIPTION     "Not supported."

    VARIATION       dsx1FarEndIntervalDMs
    ACCESS          not-implemented
    DESCRIPTION     "Not supported."

    VARIATION       dsx1FarEndTotalDMs
    ACCESS          not-implemented
    DESCRIPTION     "Not supported."

    VARIATION       dsx1LineType
    SYNTAX          INTEGER  {
                        dsx1ESF(2),
                        dsx1D4(3),
                        dsx1E1(4),
                        dsx1E1CRC(5),
                        dsx1E1MF(6),
                        dsx1E1CRCMF(7),
                        dsx1E1Q50(12),
                        dsx1E1Q50CRC(13)
                    }
    DESCRIPTION
        "Limited data values are supported.
        For T1, valid values are 2 and 3.
        For E1, valud values are 4..7, 12 and 13."

    VARIATION       dsx1SendCode
    SYNTAX          INTEGER  {
                        dsx1SendNoCode(1),
                        dsx1SendLineCode(2),
                        dsx1SendResetCode(4)
                    }
    DESCRIPTION
        "dsx1SendPayloadCode(3),
        dsx1SendQRS(5),
        dsx1Send511Pattern(6),
        dsx1Send3in24Pattern(7),
        dsx1SendOtherTestPattern(8)
        are not supported on T1.
        This object is not supported on E1."

    VARIATION       dsx1LoopbackConfig
    SYNTAX          INTEGER  {
                        dsx1NoLoop(1),
                        dsx1LineLoop(3),
                        dsx1InwardLoop(5)
                    }
    DESCRIPTION
        "dsx1PayloadLoop(2), dsx1OtherLoop(4),
        and dsx1DualLoop(6) are not supported."

    VARIATION       dsx1LineStatus
    DESCRIPTION
        "dsx1OtherFailure (bit 4096) is used to indicate
        the line is in BERT testing."

    VARIATION       dsx1SignalMode
    SYNTAX          INTEGER  {
                        none(1),
                        robbedBit(2),
                        bitOriented(3),
                        messageOriented(4)
                    }
    DESCRIPTION
        "other(5) is not supported.
        For T1, valid values are 1, 2 and 4.
        For E1, valid values are 1, 3 and 4."

    VARIATION       dsx1Fdl
    SYNTAX          INTEGER (2)
    ACCESS          read-only
    DESCRIPTION
        "Only  dsx1AnsiT1403(2) is supported.
        Set is not allowed."

    VARIATION       dsx1LineStatusChangeTrapEnable
    DEFVAL          { enabled }
    DESCRIPTION     "The initial value is enabled(1)."

    VARIATION       dsx1Channelization
    SYNTAX          INTEGER  {
                        enabledDs0(2)
                    }
    ACCESS          read-only
    DESCRIPTION
        "disabled(1) and enabledDs1(3) are not supported.
        Set is not allowed."

    VARIATION       dsx1FarEndCurrentTable
    DESCRIPTION     "It is not supported on E1."

    VARIATION       dsx1FarEndIntervalTable
    DESCRIPTION     "It is not supported on E1."

    VARIATION       dsx1FarEndTotalTable
    DESCRIPTION     "It is not supported on E1."
    ::= { ciscoDs1Capability 2 }

ciscoDs1CapabilityV5R100 AGENT-CAPABILITIES
    PRODUCT-RELEASE "MGX8880 Release 5.1.0"
    STATUS          current
    DESCRIPTION
        "DS1 MIB capabilities for VXSM and
        MPSM in release 5.1.0"

    SUPPORTS        DS1-MIB
    INCLUDES        {
                        ds1NearEndConfigGroup,
                        ds1NearEndStatisticsGroup,
                        ds1FarEndGroup,
                        ds1NearEndOptionalConfigGroup
                    }
    VARIATION       dsx1LineCoding
    DESCRIPTION
        "Only supported by T1/E1 card
        (entPhysicalVendorType is cevVxsm48t1e1)."

    VARIATION       dsx1LineLength
    SYNTAX          INTEGER (0..200)
    DESCRIPTION
        "Only supported by T1/E1 card
        (entPhysicalVendorType is cevVxsm48t1e1),
        for T1 only."

    VARIATION       dsx1CircuitIdentifier
    ACCESS          not-implemented
    DESCRIPTION     "Not supported."

    VARIATION       dsx1LineStatusLastChange
    ACCESS          not-implemented
    DESCRIPTION     "Not supported."

    VARIATION       dsx1Ds1ChannelNumber
    ACCESS          not-implemented
    DESCRIPTION     "Not supported."

    VARIATION       dsx1LineMode
    DESCRIPTION
        "Only supported by T1/E1 card
        (entPhysicalVendorType is cevVxsm48t1e1),
        for T1 only."

    VARIATION       dsx1LineBuildOut
    DESCRIPTION
        "Only supported by T1/E1 card
        (entPhysicalVendorType is cevVxsm48t1e1),
        for T1 only."

    VARIATION       dsx1CurrentDMs
    ACCESS          not-implemented
    DESCRIPTION     "Not supported."

    VARIATION       dsx1IntervalDMs
    ACCESS          not-implemented
    DESCRIPTION     "Not supported."

    VARIATION       dsx1TotalDMs
    ACCESS          not-implemented
    DESCRIPTION     "Not supported."

    VARIATION       dsx1FarEndCurrentDMs
    ACCESS          not-implemented
    DESCRIPTION     "Not supported."

    VARIATION       dsx1FarEndIntervalDMs
    ACCESS          not-implemented
    DESCRIPTION     "Not supported."

    VARIATION       dsx1FarEndTotalDMs
    ACCESS          not-implemented
    DESCRIPTION     "Not supported."

    VARIATION       dsx1LineType
    SYNTAX          INTEGER  {
                        dsx1ESF(2),
                        dsx1D4(3),
                        dsx1E1(4),
                        dsx1E1CRC(5),
                        dsx1E1MF(6),
                        dsx1E1CRCMF(7),
                        dsx1E1Q50(12),
                        dsx1E1Q50CRC(13)
                    }
    DESCRIPTION
        "Limited data values are supported.
        For T1, valid values are 2 and 3.
        For E1, valud values are 4..7, 12 and 13."

    VARIATION       dsx1SendCode
    SYNTAX          INTEGER  {
                        dsx1SendNoCode(1),
                        dsx1SendLineCode(2),
                        dsx1SendResetCode(4)
                    }
    DESCRIPTION
        "dsx1SendPayloadCode(3),
        dsx1SendQRS(5),
        dsx1Send511Pattern(6),
        dsx1Send3in24Pattern(7),
        dsx1SendOtherTestPattern(8)
        are not supported on T1.
        This object is not supported on E1."

    VARIATION       dsx1LoopbackConfig
    SYNTAX          INTEGER  {
                        dsx1NoLoop(1),
                        dsx1LineLoop(3),
                        dsx1InwardLoop(5)
                    }
    DESCRIPTION
        "dsx1PayloadLoop(2), dsx1OtherLoop(4),
        and dsx1DualLoop(6) are not supported."

    VARIATION       dsx1LineStatus
    DESCRIPTION
        "dsx1OtherFailure (bit 4096) is used to indicate
        the line is in BERT testing."

    VARIATION       dsx1SignalMode
    SYNTAX          INTEGER  {
                        none(1),
                        robbedBit(2),
                        bitOriented(3)
                    }
    DESCRIPTION
        "other(5) is not supported.
        For T1, valid values are 1, and 2
        For E1, valid values are 1, and 3."

    VARIATION       dsx1Fdl
    SYNTAX          INTEGER (2)
    ACCESS          read-only
    DESCRIPTION
        "Only  dsx1AnsiT1403(2) is supported.
        Set is not allowed."

    VARIATION       dsx1LineStatusChangeTrapEnable
    DEFVAL          { enabled }
    DESCRIPTION     "The initial value is enabled(1)."

    VARIATION       dsx1Channelization
    SYNTAX          INTEGER  {
                        enabledDs0(2)
                    }
    ACCESS          read-only
    DESCRIPTION
        "disabled(1) and enabledDs1(3) are not supported.
        Set is not allowed."

    VARIATION       dsx1FarEndCurrentTable
    DESCRIPTION     "It is not supported on E1."

    VARIATION       dsx1FarEndIntervalTable
    DESCRIPTION     "It is not supported on E1."

    VARIATION       dsx1FarEndTotalTable
    DESCRIPTION     "It is not supported on E1."
    ::= { ciscoDs1Capability 3 }

ciscoDs1CapabilityV5R310 AGENT-CAPABILITIES
    PRODUCT-RELEASE "MGX8880 Release 5.3.1"
    STATUS          current
    DESCRIPTION
        "DS1 MIB capabilities for VXSM
        in release 5.3.1"

    SUPPORTS        DS1-MIB
    INCLUDES        {
                        ds1NearEndConfigGroup,
                        ds1NearEndStatisticsGroup,
                        ds1FarEndGroup,
                        ds1NearEndOptionalConfigGroup
                    }
    VARIATION       dsx1LineCoding
    DESCRIPTION
        "Only supported by T1/E1 card
        (entPhysicalVendorType is cevVxsm48t1e1)."

    VARIATION       dsx1LineLength
    SYNTAX          INTEGER (0..200)
    DESCRIPTION
        "Only supported by T1/E1 card
        (entPhysicalVendorType is cevVxsm48t1e1),
        for T1 only."

    VARIATION       dsx1CircuitIdentifier
    ACCESS          not-implemented
    DESCRIPTION     "Not supported."

    VARIATION       dsx1LineStatusLastChange
    ACCESS          not-implemented
    DESCRIPTION     "Not supported."

    VARIATION       dsx1Ds1ChannelNumber
    ACCESS          not-implemented
    DESCRIPTION     "Not supported."

    VARIATION       dsx1LineMode
    DESCRIPTION
        "Only supported by T1/E1 card
        (entPhysicalVendorType is cevVxsm48t1e1),
        for T1 only."

    VARIATION       dsx1LineBuildOut
    DESCRIPTION
        "Only supported by T1/E1 card
        (entPhysicalVendorType is cevVxsm48t1e1),
        for T1 only."

    VARIATION       dsx1CurrentDMs
    ACCESS          not-implemented
    DESCRIPTION     "Not supported."

    VARIATION       dsx1IntervalDMs
    ACCESS          not-implemented
    DESCRIPTION     "Not supported."

    VARIATION       dsx1TotalDMs
    ACCESS          not-implemented
    DESCRIPTION     "Not supported."

    VARIATION       dsx1FarEndCurrentDMs
    ACCESS          not-implemented
    DESCRIPTION     "Not supported."

    VARIATION       dsx1FarEndIntervalDMs
    ACCESS          not-implemented
    DESCRIPTION     "Not supported."

    VARIATION       dsx1FarEndTotalDMs
    ACCESS          not-implemented
    DESCRIPTION     "Not supported."

    VARIATION       dsx1LineType
    SYNTAX          INTEGER  {
                        dsx1ESF(2),
                        dsx1D4(3),
                        dsx1E1(4),
                        dsx1E1CRC(5),
                        dsx1E1MF(6),
                        dsx1E1CRCMF(7),
                        dsx1E1Q50(12),
                        dsx1E1Q50CRC(13)
                    }
    DESCRIPTION
        "Limited data values are supported.
        For T1, valid values are 2 and 3.
        For E1, valud values are 4..7, 12 and 13."

    VARIATION       dsx1SendCode
    SYNTAX          INTEGER  {
                        dsx1SendNoCode(1),
                        dsx1SendLineCode(2),
                        dsx1SendResetCode(4)
                    }
    DESCRIPTION
        "dsx1SendPayloadCode(3),
        dsx1SendQRS(5),
        dsx1Send511Pattern(6),
        dsx1Send3in24Pattern(7),
        dsx1SendOtherTestPattern(8)
        are not supported on T1.
        This object is not supported on E1."

    VARIATION       dsx1LoopbackConfig
    SYNTAX          INTEGER  {
                        dsx1NoLoop(1),
                        dsx1LineLoop(3),
                        dsx1InwardLoop(5)
                    }
    DESCRIPTION
        "dsx1PayloadLoop(2), dsx1OtherLoop(4),
        and dsx1DualLoop(6) are not supported."

    VARIATION       dsx1LineStatus
    DESCRIPTION
        "dsx1OtherFailure (bit 4096) is used to indicate
        the line is in BERT testing."

    VARIATION       dsx1SignalMode
    SYNTAX          INTEGER  {
                        none(1),
                        robbedBit(2),
                        bitOriented(3),
                        other(5)
                    }
    DESCRIPTION
        "other(5) is only supported at
        VXSM xGCP and T1.
        For T1, valid values are 1, 2 and
        5 (xGCP only).
        For E1, valid values are 1 and 3."

    VARIATION       dsx1Fdl
    SYNTAX          INTEGER (2)
    ACCESS          read-only
    DESCRIPTION
        "Only  dsx1AnsiT1403(2) is supported.
        Set is not allowed."

    VARIATION       dsx1LineStatusChangeTrapEnable
    DEFVAL          { enabled }
    DESCRIPTION     "The initial value is enabled(1)."

    VARIATION       dsx1Channelization
    SYNTAX          INTEGER  {
                        enabledDs0(2)
                    }
    ACCESS          read-only
    DESCRIPTION
        "disabled(1) and enabledDs1(3) are not supported.
        Set is not allowed."

    VARIATION       dsx1FarEndCurrentTable
    DESCRIPTION     "It is not supported on E1."

    VARIATION       dsx1FarEndIntervalTable
    DESCRIPTION     "It is not supported on E1."

    VARIATION       dsx1FarEndTotalTable
    DESCRIPTION     "It is not supported on E1."
    ::= { ciscoDs1Capability 4 }

ciscoDs1CapabilityMARsV12R5T AGENT-CAPABILITIES
    PRODUCT-RELEASE "IOS 12.5T for Cisco Access Routers and ISRs"
    STATUS          current
    DESCRIPTION
        "Agent capabilities for Cisco 3700 series routers, IAD2430
        and 2800, 3800 Series Integrated Services Routers."

    SUPPORTS        DS1-MIB
    INCLUDES        {
                        ds1NearEndConfigGroup,
                        ds1NearEndStatisticsGroup
                    }
    VARIATION       dsx1LineType
    ACCESS          read-only
    DESCRIPTION
        "Read only support is provided."

    VARIATION       dsx1LineCoding
    ACCESS          read-only
    DESCRIPTION
        "Read only support is provided."

    VARIATION       dsx1SendCode
    ACCESS          read-only
    DESCRIPTION
        "Read only support is provided."

    VARIATION       dsx1CircuitIdentifier
    ACCESS          read-only
    DESCRIPTION
        "Read only support is provided."

    VARIATION       dsx1LoopbackConfig
    ACCESS          read-only
    DESCRIPTION
        "Read only support is provided."

    VARIATION       dsx1SignalMode
    ACCESS          read-only
    DESCRIPTION
        "Read only support is provided."

    VARIATION       dsx1TransmitClockSource
    ACCESS          read-only
    DESCRIPTION
        "Read only support is provided."

    VARIATION       dsx1Fdl
    ACCESS          read-only
    DESCRIPTION
        "Read only support is provided."

    VARIATION       dsx1LineLength
    ACCESS          read-only
    DESCRIPTION
        "Configured length is shown if it is available.
        If length is not available then the value is 0. For example, length
        is not available for 'cablelength long' config"

    VARIATION       dsx1LineStatusChangeTrapEnable
    ACCESS          read-only
    DESCRIPTION
        "Read only support is provided."

    VARIATION       dsx1Channelization
    ACCESS          not-implemented
    DESCRIPTION
        "Not Supported."

    VARIATION       dsx1LineMode
    ACCESS          not-implemented
    DESCRIPTION
        "Not Supported."

    VARIATION       dsx1LineBuildOut
    ACCESS          not-implemented
    DESCRIPTION
        "Not Supported."
    ::= { ciscoDs1Capability 6 }

ciscoDs1CapabilityAS5xxxV12R5T AGENT-CAPABILITIES
    PRODUCT-RELEASE "IOS 12.5T for Cisco Access Servers"
    STATUS          current
    DESCRIPTION
        "Agent capabilities for Cisco AS5xxx routers."

    SUPPORTS        DS1-MIB
    INCLUDES        {
                        ds1NearEndConfigGroup,
                        ds1NearEndStatisticsGroup
                    }
    VARIATION       dsx1LineType
    ACCESS          read-only
    DESCRIPTION
        "Read only support is provided."

    VARIATION       dsx1LineCoding
    ACCESS          read-only
    DESCRIPTION
        "Read only support is provided."

    VARIATION       dsx1SendCode
    ACCESS          read-only
    DESCRIPTION
        "Read only support is provided."

    VARIATION       dsx1CircuitIdentifier
    ACCESS          read-only
    DESCRIPTION
        "Read only support is provided."

    VARIATION       dsx1LoopbackConfig
    ACCESS          read-only
    DESCRIPTION
        "Read only support is provided."

    VARIATION       dsx1SignalMode
    ACCESS          read-only
    DESCRIPTION
        "Read only support is provided."

    VARIATION       dsx1TransmitClockSource
    ACCESS          read-only
    DESCRIPTION
        "Read only support is provided."

    VARIATION       dsx1Fdl
    ACCESS          read-only
    DESCRIPTION
        "Read only support is provided."

    VARIATION       dsx1InvalidIntervals
    ACCESS          not-implemented
    DESCRIPTION
        "Not Supported."

    VARIATION       dsx1LineLength
    ACCESS          not-implemented
    DESCRIPTION
        "Not Supported."

    VARIATION       dsx1LineStatusChangeTrapEnable
    ACCESS          not-implemented
    DESCRIPTION
        "Not Supported."

    VARIATION       dsx1LoopbackStatus
    ACCESS          not-implemented
    DESCRIPTION
        "Not Supported."

    VARIATION       dsx1Ds1ChannelNumber
    ACCESS          not-implemented
    DESCRIPTION
        "Not Supported."

    VARIATION       dsx1Channelization
    ACCESS          not-implemented
    DESCRIPTION
        "Not Supported."

    VARIATION       dsx1LineMode
    ACCESS          not-implemented
    DESCRIPTION
        "Not Supported."

    VARIATION       dsx1LineBuildOut
    ACCESS          not-implemented
    DESCRIPTION
        "Not Supported."

    VARIATION       dsx1IntervalValidData
    ACCESS          not-implemented
    DESCRIPTION
        "Not Supported."
    ::= { ciscoDs1Capability 7 }

ciscoDs1CapabilityV5R500 AGENT-CAPABILITIES
    PRODUCT-RELEASE "MGX8880 Release 5.5.0"
    STATUS          current
    DESCRIPTION
        "DS1 MIB capabilities for VXSM
        in release 5.5.0."

    SUPPORTS        DS1-MIB
    INCLUDES        {
                        ds1NearEndConfigGroup,
                        ds1NearEndStatisticsGroup,
                        ds1FarEndGroup,
                        ds1NearEndOptionalConfigGroup
                    }
    VARIATION       dsx1LineCoding
    DESCRIPTION
        "Only supported by T1/E1 card
        (entPhysicalVendorType is cevVxsm48t1e1)."

    VARIATION       dsx1LineLength
    SYNTAX          INTEGER (0..200)
    DESCRIPTION
        "Supported with limited length only by T1/E1 card 
        (entPhysicalVendorType is cevVxsm48t1e1), 
        for T1 only." 

    VARIATION       dsx1CircuitIdentifier
    SYNTAX          DisplayString (SIZE (1..64))
    DESCRIPTION     "Restricted length supported."

    VARIATION       dsx1LineStatusLastChange
    ACCESS          not-implemented
    DESCRIPTION     "Not supported."

    VARIATION       dsx1Ds1ChannelNumber
    ACCESS          not-implemented
    DESCRIPTION     "Not supported."

    VARIATION       dsx1LineMode
    DESCRIPTION
        "Only supported by T1/E1 card
        (entPhysicalVendorType is cevVxsm48t1e1),
        for T1 only."

    VARIATION       dsx1LineBuildOut
    DESCRIPTION
        "Only supported by T1/E1 card
        (entPhysicalVendorType is cevVxsm48t1e1),
        for T1 only."

    VARIATION       dsx1CurrentDMs
    ACCESS          not-implemented
    DESCRIPTION     "Not supported."

    VARIATION       dsx1IntervalDMs
    ACCESS          not-implemented
    DESCRIPTION     "Not supported."

    VARIATION       dsx1TotalDMs
    ACCESS          not-implemented
    DESCRIPTION     "Not supported."

    VARIATION       dsx1FarEndCurrentDMs
    ACCESS          not-implemented
    DESCRIPTION     "Not supported."

    VARIATION       dsx1FarEndIntervalDMs
    ACCESS          not-implemented
    DESCRIPTION     "Not supported."

    VARIATION       dsx1FarEndTotalDMs
    ACCESS          not-implemented
    DESCRIPTION     "Not supported."

    VARIATION       dsx1LineType
    SYNTAX          INTEGER  {
                        dsx1ESF(2),
                        dsx1D4(3),
                        dsx1E1(4),
                        dsx1E1CRC(5),
                        dsx1E1MF(6),
                        dsx1E1CRCMF(7),
                        dsx1E1Q50(12),
                        dsx1E1Q50CRC(13)
                    }
    DESCRIPTION
        "Limited data values are supported.
        For T1, valid values are 2 and 3.
        For E1, valid values are 4..7, 12 and 13."

    VARIATION       dsx1SendCode
    SYNTAX          INTEGER  {
                        dsx1SendNoCode(1),
                        dsx1SendLineCode(2),
                        dsx1SendResetCode(4)
                    }
    DESCRIPTION
        "Limited values are supported on T1: 
        dsx1SendNoCode(1), 
        dsx1SendLineCode(2), 
        dsx1SendResetCode(4) 

        This object is supported on DS1 interface 
        and not supported on E1." 

    VARIATION       dsx1LoopbackConfig
    SYNTAX          INTEGER  {
                        dsx1NoLoop(1),
                        dsx1LineLoop(3),
                        dsx1InwardLoop(5)
                    }
    DESCRIPTION
        "Limited values are supported: 
         dsx1NoLoop(1),
         dsx1LineLoop(3),
         dsx1InwardLoop(5)"

    VARIATION       dsx1LineStatus
    DESCRIPTION
        "dsx1OtherFailure (value 4096) is used to indicate 
        the line is in BERT testing." 

    VARIATION       dsx1SignalMode
    SYNTAX          INTEGER  {
                        none(1),
                        robbedBit(2),
                        bitOriented(3),
                        other(5)
                    }
    DESCRIPTION
        "other(5) is only supported at
        VXSM xGCP and T1.
        For T1, valid values are 1, 2 and
        5 (xGCP only).
        For E1, valid values are 1 and 3."

    VARIATION       dsx1Fdl
    SYNTAX          INTEGER (2)
    ACCESS          read-only
    DESCRIPTION
        "Only  dsx1AnsiT1403(2) is supported.
        Set is not allowed."

    VARIATION       dsx1LineStatusChangeTrapEnable
    DEFVAL          { enabled }
    DESCRIPTION     "The default value is enabled(1)."

    VARIATION       dsx1Channelization
    SYNTAX          INTEGER  {
                        enabledDs0(2)
                    }
    ACCESS          read-only
    DESCRIPTION
       "Limited values are supported: 
        enabledDs0(2) 
        Set is not allowed." 

    VARIATION       dsx1FarEndCurrentTable
    DESCRIPTION     "It is not supported on E1."

    VARIATION       dsx1FarEndIntervalTable
    DESCRIPTION     "It is not supported on E1."

    VARIATION       dsx1FarEndTotalTable
    DESCRIPTION     "It is not supported on E1."
    ::= { ciscoDs1Capability 8 }

END
