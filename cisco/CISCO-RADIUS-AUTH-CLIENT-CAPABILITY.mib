CISCO-RADIUS-AUTH-CLIENT-CAPABILITY DEFINITIONS ::= BEGIN

IMPORTS
        MODULE-IDENTITY
                FROM SNMPv2-SMI
        AGENT-CAPABILITIES
                FROM SNMPv2-CONF
        ciscoAgentCapability
                FROM CISCO-SMI;   

ciscoRadiusAuthClientCapability MODULE-IDENTITY
    LAST-UPDATED    "200603060000Z"
    ORGANIZATION    "Cisco Systems, Inc."
    CONTACT-INFO  
        "       Cisco Systems
                Customer Service

               Postal: 170 West Tasman Drive
               San Jose, CA  95134
               USA

               Tel: +1 800 553-NETS

               E-mail: cs-radius@cisco.com" 
    DESCRIPTION
       "The capabilities description of RADIUS-AUTH-CLIENT-MIB"

    REVISION        "200603060000Z"
    DESCRIPTION
       "Initial version of this MIB module."
    ::= {  ciscoAgentCapability 494 } 

ciscoRadiusAuthClientCapV330CRS1 AGENT-CAPABILITIES
    PRODUCT-RELEASE "Cisco IOS XR release 3.3.0 for CRS-1"
    STATUS          current
    DESCRIPTION     "RADIUS-AUTH-CLIENT-MIB capabilities." 

    SUPPORTS        RADIUS-AUTH-CLIENT-MIB 
     INCLUDES       {        
                     radiusAuthClientMIBGroup
                    } 
    ::= { ciscoRadiusAuthClientCapability 1 }

END
