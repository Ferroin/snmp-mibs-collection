CISCO-WAN-ATM-CONN-STAT-CAPABILITY DEFINITIONS ::= BEGIN

IMPORTS
        MODULE-IDENTITY
                FROM SNMPv2-SMI
        AGENT-CAPABILITIES
                FROM SNMPv2-CONF
        ciscoAgentCapability
                FROM CISCO-SMI;

ciscoWanAtmConnStatCapability MODULE-IDENTITY
        LAST-UPDATED    "200304080000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
                "The Agent Capabilities for CISCO-WAN-ATM-CONN-STAT-MIB
                 for different Service Modules in in MGX8850 Series.

                - The cwaConnStatCapabilityAxsmV21R60 is for
                  ATM Switch Service Module(AXSM).
                - The cwAtmConnStatCapabilityAxsmeV2R0170 is for
                  Enhanced AXSM(AXSM-E) module.
                - The cwAtmConnStatCapabilityPxm1eV2R300 is for
                  PXM1-E module"

        REVISION    "200304080000Z"
        DESCRIPTION
            "Added cwacsCapabilityAxsmxgV4R00 for 10 Gig. AXSM 
             Module (AXSM-XG)."

        REVISION    "200103210000Z"
        DESCRIPTION
            "Initial version of this MIB module."
        ::= { ciscoAgentCapability 9999}

cwaConnStatCapabilityAxsmV21R60 AGENT-CAPABILITIES
    PRODUCT-RELEASE      "MGX8850 Release 2.1.60"
    STATUS               current
    DESCRIPTION          "CISCO-WAN-ATM-CONN-STAT-MIB capabilities
                         for ATM Switch Service Module(AXSM)."

    SUPPORTS CISCO-WAN-ATM-CONN-STAT-MIB
        INCLUDES { cwacsGroup }

        VARIATION   cwacsIngXmtCLP0
        ACCESS      not-implemented      
        DESCRIPTION "Not supported."

        VARIATION   cwacsIngXmtCLP1
        ACCESS      not-implemented      
        DESCRIPTION "Not supported."

        VARIATION   cwacsIngCLP0CoSDiscard
        ACCESS      not-implemented      
        DESCRIPTION "Not supported."

        VARIATION   cwacsIngCLP1CoSDiscard
        ACCESS      not-implemented      
        DESCRIPTION "Not supported."

        VARIATION   cwacsIngRcvEFCI0   
        ACCESS      not-implemented      
        DESCRIPTION "Not supported."

        VARIATION   cwacsIngEFCI0Discard   
        ACCESS      not-implemented      
        DESCRIPTION "Not supported."

        VARIATION   cwacsIngEFCI1Discard   
        ACCESS      not-implemented      
        DESCRIPTION "Not supported."

        VARIATION   cwacsIngRcvOAM
        ACCESS      not-implemented      
        DESCRIPTION "Not supported."

        VARIATION   cwacsIngOAMDiscard
        ACCESS      not-implemented      
        DESCRIPTION "Not supported."

        VARIATION   cwacsIngRcvRM
        ACCESS      not-implemented      
        DESCRIPTION "Not supported."

        VARIATION   cwacsIngRMDiscard
        ACCESS      not-implemented      
        DESCRIPTION "Not supported."

        VARIATION   cwacsIngXmtFRm   
        ACCESS      not-implemented      
        DESCRIPTION "Not supported."

        VARIATION   cwacsIngXmtBRmFsRm   
        ACCESS      not-implemented      
        DESCRIPTION "Not supported."

        VARIATION   cwacsIngEOF1Discard   
        ACCESS      not-implemented      
        DESCRIPTION "Not supported."

        VARIATION   cwacsIngACR
        ACCESS      not-implemented      
        DESCRIPTION "Not supported."

        VARIATION   cwacsEgrXmtCLP0
        ACCESS      not-implemented      
        DESCRIPTION "Not supported."

        VARIATION   cwacsEgrXmtCLP1
        ACCESS      not-implemented      
        DESCRIPTION "Not supported."

        VARIATION   cwacsEgrCLP0CoSDiscard
        ACCESS      not-implemented      
        DESCRIPTION "Not supported."

        VARIATION   cwacsEgrCLP1CoSDiscard
        ACCESS      not-implemented      
        DESCRIPTION "Not supported."

        VARIATION   cwacsEgrRcvEFCI0   
        ACCESS      not-implemented      
        DESCRIPTION "Not supported."

        VARIATION   cwacsEgrEFCI0Discard   
        ACCESS      not-implemented      
        DESCRIPTION "Not supported."

        VARIATION   cwacsEgrEFCI1Discard   
        ACCESS      not-implemented      
        DESCRIPTION "Not supported."

        VARIATION   cwacsEgrRcvOAM
        ACCESS      not-implemented      
        DESCRIPTION "Not supported."

        VARIATION   cwacsEgrOAMDiscard
        ACCESS      not-implemented      
        DESCRIPTION "Not supported."

        VARIATION   cwacsEgrRcvRM
        ACCESS      not-implemented      
        DESCRIPTION "Not supported."

        VARIATION   cwacsEgrRMDiscard
        ACCESS      not-implemented      
        DESCRIPTION "Not supported."

        VARIATION   cwacsEgrXmtFRm   
        ACCESS      not-implemented      
        DESCRIPTION "Not supported."

        VARIATION   cwacsEgrXmtBRmFsRm   
        ACCESS      not-implemented      
        DESCRIPTION "Not supported."

        VARIATION   cwacsEgrEOF1Discard   
        ACCESS      not-implemented      
        DESCRIPTION "Not supported."

        VARIATION   cwacsEgrACR
        ACCESS      not-implemented      
        DESCRIPTION "Not supported."
    ::= { ciscoWanAtmConnStatCapability 1 }

cwAtmConnStatCapabilityAxsmeV2R0170 AGENT-CAPABILITIES
    PRODUCT-RELEASE      "MGX8850 Release 2.1.70"
    STATUS               current
    DESCRIPTION          "CISCO-WAN-ATM-CONN-STAT-MIB capabilities
                         for Enhanced AXSM(AXSM-E) Module."

    SUPPORTS CISCO-WAN-ATM-CONN-STAT-MIB
        INCLUDES { cwacsGroup }

        VARIATION   cwacsIngRcvEFCI0   
        ACCESS      not-implemented      
        DESCRIPTION "Not supported."

        VARIATION   cwacsIngEFCI0Discard   
        ACCESS      not-implemented      
        DESCRIPTION "Not supported."

        VARIATION   cwacsIngXmtFRm   
        ACCESS      not-implemented      
        DESCRIPTION "Not supported."

        VARIATION   cwacsIngXmtBRmFsRm   
        ACCESS      not-implemented      
        DESCRIPTION "Not supported."

        VARIATION   cwacsEgrRcvEFCI0   
        ACCESS      not-implemented      
        DESCRIPTION "Not supported."

        VARIATION   cwacsEgrEFCI0Discard   
        ACCESS      not-implemented      
        DESCRIPTION "Not supported."

        VARIATION   cwacsEgrXmtFRm   
        ACCESS      not-implemented      
        DESCRIPTION "Not supported."

        VARIATION   cwacsEgrXmtBRmFsRm   
        ACCESS      not-implemented      
        DESCRIPTION "Not supported."

        VARIATION   cwacsEgrRcvEOF1   
        ACCESS      not-implemented      
        DESCRIPTION "Not supported."

        VARIATION   cwacsEgrEOF1Discard
        ACCESS      not-implemented      
        DESCRIPTION "Not supported."
    ::= { ciscoWanAtmConnStatCapability 2 }

cwAtmConnStatCapabilityPxm1eV2R300 AGENT-CAPABILITIES
    PRODUCT-RELEASE      "MGX8850 Release 3.0.00"
    STATUS               current
    DESCRIPTION          "CISCO-WAN-ATM-CONN-STAT-MIB capabilities
                         for PXM1-E Module."

    SUPPORTS CISCO-WAN-ATM-CONN-STAT-MIB
        INCLUDES { cwacsGroup }

        VARIATION   cwacsIngXmtCLP0   
        ACCESS      not-implemented      
        DESCRIPTION "Not supported."

        VARIATION   cwacsIngXmtCLP1
        ACCESS      not-implemented      
        DESCRIPTION "Not supported."

        VARIATION   cwacsIngCLP0CoSDiscard
        ACCESS      not-implemented      
        DESCRIPTION "Not supported."

        VARIATION   cwacsIngCLP1CoSDiscard
        ACCESS      not-implemented      
        DESCRIPTION "Not supported."

        VARIATION   cwacsIngRcvEFCI0   
        ACCESS      not-implemented      
        DESCRIPTION "Not supported."

        VARIATION   cwacsIngRcvEFCI1   
        ACCESS      not-implemented      
        DESCRIPTION "Not supported."

        VARIATION   cwacsIngEFCI0Discard   
        ACCESS      not-implemented      
        DESCRIPTION "Not supported."

        VARIATION   cwacsIngRcvOAM   
        ACCESS      not-implemented      
        DESCRIPTION "Not supported."

        VARIATION   cwacsIngOAMDiscard   
        ACCESS      not-implemented      
        DESCRIPTION "Not supported."

        VARIATION   cwacsIngRcvRM   
        ACCESS      not-implemented      
        DESCRIPTION "Not supported."

        VARIATION   cwacsIngRMDiscard   
        ACCESS      not-implemented      
        DESCRIPTION "Not supported."

        VARIATION   cwacsIngXmtFRm   
        ACCESS      not-implemented      
        DESCRIPTION "Not supported."

        VARIATION   cwacsIngXmtBRmFsRm   
        ACCESS      not-implemented      
        DESCRIPTION "Not supported."

        VARIATION   cwacsIngRcvEOF1   
        ACCESS      not-implemented      
        DESCRIPTION "Not supported."

        VARIATION   cwacsIngEOF1Discard   
        ACCESS      not-implemented      
        DESCRIPTION "Not supported."

        VARIATION   cwacsIngACR   
        ACCESS      not-implemented      
        DESCRIPTION "Not supported."

        VARIATION   cwacsEgrRcvCLP0   
        ACCESS      not-implemented      
        DESCRIPTION "Not supported."

        VARIATION   cwacsEgrRcvCLP1   
        ACCESS      not-implemented      
        DESCRIPTION "Not supported."

        VARIATION   cwacsEgrCLP0CoSDiscard   
        ACCESS      not-implemented      
        DESCRIPTION "Not supported."

        VARIATION   cwacsEgrCLP1CoSDiscard   
        ACCESS      not-implemented      
        DESCRIPTION "Not supported."

        VARIATION   cwacsEgrRcvEFCI0   
        ACCESS      not-implemented      
        DESCRIPTION "Not supported."

        VARIATION   cwacsEgrRcvEFCI1   
        ACCESS      not-implemented      
        DESCRIPTION "Not supported."

        VARIATION   cwacsEgrEFCI0Discard   
        ACCESS      not-implemented      
        DESCRIPTION "Not supported."

        VARIATION   cwacsEgrXmtFRm   
        ACCESS      not-implemented      
        DESCRIPTION "Not supported."

        VARIATION   cwacsEgrXmtBRmFsRm   
        ACCESS      not-implemented      
        DESCRIPTION "Not supported."

        VARIATION   cwacsEgrRcvEOF1   
        ACCESS      not-implemented      
        DESCRIPTION "Not supported."

        VARIATION   cwacsEgrEOF1Discard
        ACCESS      not-implemented      
        DESCRIPTION "Not supported."

        VARIATION   cwacsEgrACR
        ACCESS      not-implemented      
        DESCRIPTION "Not supported."
    ::= { ciscoWanAtmConnStatCapability 3 }

cwacsCapabilityAxsmxgV4R00 AGENT-CAPABILITIES
    PRODUCT-RELEASE      "MGX8950 Release 4.0.00"
    STATUS               current
    DESCRIPTION          "CISCO-WAN-ATM-CONN-STAT-MIB capabilities
                         for 10 Gig. AXSM Module (AXSM-XG)."

    SUPPORTS CISCO-WAN-ATM-CONN-STAT-MIB
        INCLUDES { cwacsGroup1 }

        VARIATION   cwacsIngRcvEFCI0   
        ACCESS      not-implemented      
        DESCRIPTION "Not supported."

        VARIATION   cwacsIngEFCI0Discard   
        ACCESS      not-implemented      
        DESCRIPTION "Not supported."

        VARIATION   cwacsIngXmtFRm   
        ACCESS      not-implemented      
        DESCRIPTION "Not supported."

        VARIATION   cwacsIngXmtBRmFsRm   
        ACCESS      not-implemented      
        DESCRIPTION "Not supported."

        VARIATION   cwacsEgrRcvEFCI0   
        ACCESS      not-implemented      
        DESCRIPTION "Not supported."

        VARIATION   cwacsEgrEFCI0Discard   
        ACCESS      not-implemented      
        DESCRIPTION "Not supported."

        VARIATION   cwacsEgrXmtFRm   
        ACCESS      not-implemented      
        DESCRIPTION "Not supported."

        VARIATION   cwacsEgrXmtBRmFsRm   
        ACCESS      not-implemented      
        DESCRIPTION "Not supported."

        VARIATION   cwacsEgrRcvEOF1   
        ACCESS      not-implemented      
        DESCRIPTION "Not supported."

        VARIATION   cwacsEgrEOF1Discard
        ACCESS      not-implemented      
        DESCRIPTION "Not supported."

        VARIATION   cwacsHighIngRcvEFCI0
        ACCESS      not-implemented      
        DESCRIPTION "Not supported."

        VARIATION   cwacsHighIngEFCI0Discard
        ACCESS      not-implemented      
        DESCRIPTION "Not supported."

        VARIATION   cwacsHighEgrRcvEFCI0
        ACCESS      not-implemented      
        DESCRIPTION "Not supported."

        VARIATION   cwacsHighEgrEFCI0Discard
        ACCESS      not-implemented      
        DESCRIPTION "Not supported."
    ::= { ciscoWanAtmConnStatCapability 4}

END
