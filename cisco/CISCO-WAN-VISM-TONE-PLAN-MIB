CISCO-WAN-VISM-TONE-PLAN-MIB DEFINITIONS ::= BEGIN

IMPORTS
    MODULE-IDENTITY,
    OBJECT-TYPE,
    Integer32 
                        FROM SNMPv2-SMI
    MODULE-COMPLIANCE,
    OBJECT-GROUP
                        FROM SNMPv2-CONF
    DisplayString,
    RowStatus          
                        FROM SNMPv2-TC 
    ciscoWan            FROM CISCOWAN-SMI;

vismTonePlanGrpMIB MODULE-IDENTITY
    LAST-UPDATED "200312170000Z"
    ORGANIZATION "Cisco Systems, Inc."
    CONTACT-INFO
            "       Cisco Systems
                    Customer Service

                Postal: 170 W Tasman Drive
                        San Jose, CA 95134
                        USA

                        Tel: +1 800 553-NETS

                E-mail: cs-voice@cisco.com"
    DESCRIPTION
        "The MIB module is defined to configure the programmable
         Tone Plan feature on VISM.
        " 

    REVISION "200312170000Z"
    DESCRIPTION
        "1. Remove default value from vismEventCode object.
         2. Change default value of vismFreqMaxDelay object 
            from 3 to 10.
         3. Change default value of vismMinOnCadence object 
            from 3 to 20.
         4. Change default value of vismMaxOffCadence object 
            from 5 to 450.
         5. Remove default value from vismFrequency1 object.
         6. Remove default value from vismFrequency2 object.
         7. Remove default value from vismFreqOnCadence object.
         8. Change default value of seqToneMaximumGapDuration
            object from 10 to 15. 
         9. Change SYNTAX INTEGER to Integer32 except for 
         enumerated integers in vismConfigToneDetectEntry.
         10. Clarify description of object.
        "

    REVISION "200304230000Z"
    DESCRIPTION "
                Added Object vismConfigToneDetect (Programmable Tone)
                under vismTonePlan
                "
    REVISION "200207190000Z"
    DESCRIPTION 
        "Give tonePlanIndex a range (1..1000) to be
         compiled in new SMICNG compiler (ver2.2.11-beta).
        "

    REVISION "200112260000Z"
    DESCRIPTION 
        "Description changes for tonePlanEntryStatus, 
         tonePlanProvisionFlag, vismTonePlanEntry.
        "

    REVISION "200108050000Z"
    DESCRIPTION 
        "Results from MIB external interfaces review.
        "

    REVISION "200104030000Z"
    DESCRIPTION 
        "Initial draft. Created new VISM Tone Plan Group.
        "
    ::= { ciscoWan 24 }

vismTonePlanGrpMIBObjects  OBJECT IDENTIFIER ::= 
                                    { vismTonePlanGrpMIB 1}
vismTonePlan               OBJECT IDENTIFIER ::= 
                                    { vismTonePlanGrpMIBObjects 1 }
vismTonePlanControlGrp     OBJECT IDENTIFIER ::= { vismTonePlan 1 }
vismTonePlanTableGrp       OBJECT IDENTIFIER ::= { vismTonePlan 2 }

vismConfigToneDetectGrp    OBJECT IDENTIFIER ::= { vismTonePlan 3 }
vismSequentialToneDetectGrp OBJECT IDENTIFIER ::= { vismTonePlan 4 } 

-- ------------------------------------------------------------------
--
-- vismTonePlan Control group
--
--
-- The MIB variables in this group have been defined to report
-- the size of the programmable Tone Plan table on VISM and 
-- any other high level controls of the Tone Plan Feature.  
--
-- ------------------------------------------------------------------

tonePlanCurrentSize    OBJECT-TYPE
    SYNTAX       Integer32
    MAX-ACCESS   read-only
    STATUS       current
    DESCRIPTION
        "This object specifies the number of entries 
         in vismTonePlanTable.
        "
    ::= { vismTonePlanControlGrp 1 }

-- ------------------------------------------------------------------
--
-- vismTonePlan group
--
--
-- The MIB variables in this group have been defined to configure
-- the programmable Tone Plan feature on VISM. VISM card can be 
-- configured with different Tone Plans by downloading the different
-- files which contains the various Tone Plans from the PXM.
--
-- ------------------------------------------------------------------

vismTonePlanTable OBJECT-TYPE
    SYNTAX        SEQUENCE OF VismTonePlanEntry
    MAX-ACCESS    not-accessible
    STATUS        current
    DESCRIPTION
        "This table contains configuration information about different 
         Tone Plans. 

         The first 32 entries of the table are 'provisionable' 
         followed by an implementation specific number 
         of 'builtIn' entries.
        "
    ::= { vismTonePlanTableGrp 1 }

vismTonePlanEntry OBJECT-TYPE
    SYNTAX        VismTonePlanEntry
    MAX-ACCESS    not-accessible
    STATUS        current
    DESCRIPTION
        "An entry in the vismTonePlanTable. Each entry consists of 
         configuration information for a specific Tone Plan.

         The vismTonePlanTable is of fixed size with a predefined
         number of entries, where each entry contains usable
         information or not depending upon the value of the
         tonePlanEntryStatus MIB object.

         The configuration is retained after VISM card reboots.

         tonePlanRegionName, tonePlanVersionNumber, and 
         tonePlanFileName can be modified only if the 
         tonePlanProvisionFlag is 'provisionable' and 
         tonePlanEntryStatus is 'configured' when loading a new 
         tone plan (see MIB object tonePlanEntryStatus below). After 
         the new tone plan is loaded, these three MIB objects may
         not be modified. To change these objects, the entry in
         this table must be deleted, and all objects re-added 
         with new corrected values.

         The rest of the entries of this table, (the 'builtIn' ones)
         cannot be modified after the table is build at reload time.
        "
    INDEX { tonePlanIndex }
    ::= { vismTonePlanTable 1 }

VismTonePlanEntry ::=
    SEQUENCE {
        tonePlanIndex           Integer32,
        tonePlanEntryStatus     INTEGER,
        tonePlanProvisionFlag   INTEGER,
        tonePlanRegionName      DisplayString,
        tonePlanVersionNumber   Integer32,
        tonePlanFileName        DisplayString
        }

tonePlanIndex    OBJECT-TYPE
    SYNTAX       Integer32 (1..1000)
    MAX-ACCESS   not-accessible
    STATUS       current
    DESCRIPTION
        " Serves as index to this table. However, the maximum 
          entry allowed is specify in tonePlanCurrentSize.
        "
    ::= { vismTonePlanEntry 1 }

tonePlanEntryStatus    OBJECT-TYPE
    SYNTAX             INTEGER
                         {
                         unused     (1),
                         configured (2),
                         reloading  (3),
                         lostFile   (4)
                         }
    MAX-ACCESS         read-write
    STATUS             current
    DESCRIPTION
        " This attribute specifies the status of this entry as to
          whether this entry (row) contains usable Tone Plan 
          configuration information (object is set to 'configured'), 
          or if it is empty (object is set to 'unused'), or if is 
          temporarily (object is set to 'reloading') or 
          permanently (object is set to 'lostFile') unusable.

          This tone plan information for this row can be used
          by a DS-1 line only if this object has a value of
          'configured (2)'.

          To add a configured entry in the vismTonePlanTable
          table, there must be an existing empty row with its 
          entry status set to 'unused(1)'.

          Then before this empty row in the vismTonePlanTable
          table can be changed to 'configured', it must, in
          one single operation, be given all the usable
          values necessary to be stored in the
          tonePlanRegionName, tonePlanVersionNumber and 
          tonePlanFileName MIB objects for this row. In addition, 
          those values for the tonePlanRegionName and 
          tonePlanVersionNumber MIB objects pair must be
          unique with respect to every other row of the
          vismTonePlanTable. Then, as this existing empty row
          is set with all three valid entries for the
          tonePlanRegionName, tonePlanVersionNumber, 
          and tonePlanFileName MIB objects, the Entry Status
          MIB object for this row will be finally, internally,
          set to 'configured(2)'. This final 'configured' status
          is the direct result of correctly setting these three
          MIB objects with valid data.

          In no case will an external manager be able to directly
          set this MIB object to 'configured(2)' by a SNMP set
          command, for such a single stand alone command will
          be rejected.

          Once a table entry is set to 'configured(2)' with
          valid tonePlanRegionName, tonePlanVersionNumber, and
          tonePlanFileName MIB objects for this row, then these
          MIB objects may not be modified by any subsequent 
          SNMP set command.  In the case where a row needs to
          have these objects changed, this entry must be cleared
          from the table (paragraph below) and a new entry added
          by the add process above.

          Once an entry exists in the vismTonePlanTable table it
          may be cleared and set to unused by setting this MIB
          object to 'unused(1)'.  But before the entry status of
          any entry in this table can be set to 'unused(1)',
          there is a check to make sure there is no
          vismDsx1TonePlanRegion MIB object and
          vismDsx1TonePlanVersion MIB object pair in the
          dsx1VismCnfGrpTable MIB table that may point to or
          refer to this table entry (row) with its unique
          tonePlanRegionName and tonePlanVersionNumber.

          Once the entry status of an entry in this table is set
          to 'unused(1)', all the other MIB objects for this
          table row are set to defaults or to NULL.

          Once an entry is 'configured', if a subsequent card
          reset occurs the VISM card will attempt to restore
          all of the configuration information by doing the
          normal download of the latest MIB database, set all
          'configured (2)' MIB objects to 'reloading (3)', and
          then do an automatic background process to retrieve
          all of the tone plan files from the server since they
          were not downloaded by the PXM. If this retrieval of
          the tone plan files succeeds then this MIB object
          will be set back to 'configured (2)'. If this file
          retrieval does not succeed, then this MIB object will
          be set to 'lostFile (4)'. In no way will an external
          manager be able to directly set this MIB object
          to 'reloading (3)' or 'lostFile (4)' by a SNMP set
          command.
        "
    DEFVAL { unused }
    ::= { vismTonePlanEntry 2 }

tonePlanProvisionFlag    OBJECT-TYPE
    SYNTAX               INTEGER
                            {
                            builtIn       (1),
                            provisionable (2)
                            }
    MAX-ACCESS           read-only
    STATUS               current
    DESCRIPTION
        " This attribute specifies whether this entry contains
          predefined Tone Plan configuration information from
          internal firmware code (object is set to 'builtIn') or
          if it has been configured with tone plan configuration
          information that has been downloaded from the PXM
          (object is set to unused).

          Only entries that are provisionable may have their
          tonePlanEntryStatus MIB object marked as unused in
          this table.  BuiltIn entries may not be marked as unused.
        "
    ::= { vismTonePlanEntry 3 }

tonePlanRegionName    OBJECT-TYPE
    SYNTAX            DisplayString (SIZE(1..64))
    MAX-ACCESS        read-write
    STATUS            current
    DESCRIPTION
        " The region (or country) for which this tone plan is
          defined. Any other entry in this table may have an
          identical name, but the combination of tonePlanRegionName
          and tonePlanVersionNumber must be unique.

          This field may be from 1 to 64 alphabetic, numeric, or
          underscore characters long, with no embedded spaces.
          A NULL entry will consist of a single space character
          of length one.
        "
    ::= { vismTonePlanEntry 4 }

tonePlanVersionNumber    OBJECT-TYPE
    SYNTAX               Integer32 (0..65535)
    MAX-ACCESS           read-write
    STATUS               current
    DESCRIPTION
        " This attribute specifies this entry's version number
          for a tone plan for a region.  Multiple tone plans may
          be defined for each region, but each of these tone
          plans must have a unique tonePlanRegionName and
          tonePlanVersionNumber.  When a new tone plan is added
          for a region, it should be added with a newer(larger)
          version number.

          Allowed values are in range (1..65535) but a value of
          zero being set in this object means that this object
          is a NULL entry.
        "
    ::= { vismTonePlanEntry 5 }

tonePlanFileName    OBJECT-TYPE
    SYNTAX          DisplayString (SIZE(1..32))
    MAX-ACCESS      read-write
    STATUS          current
    DESCRIPTION
        " This is the name of a valid file stored on the TFTP
          server which contains the tone definitions.  A missing
          or invalid file name will cause a failure in the
          configuration of this entry.

          If this entry points to a build-in tone plan predefined
          in firmware, then this name will be: 'BUILTIN'. 
          Provisionable file names are not allowed to have the
          string 'BUILTIN' as their names.

          This field may be from 1 to 32 alphabetic, numeric, or 
          underscore characters (no embedded spaces) long for a
          valid entry.  A NULL entry will consist of a single
          space character of length one.
        "
    ::= { vismTonePlanEntry 6 }

-- ------------------------------------------------------------------
--
-- vismConfigToneDetectGrp group
--
--
-- The MIB variables in this group have been defined to configure
-- the programmable CallProgress Tone Plan feature on VISM.
-- VISM card can be configured with different tones by 
-- configuring the different rows of this table, and assigning
-- an eventID against it. Then this eventID can be requested
-- from the CallAgent as a telephone-event.
--
-- ------------------------------------------------------------------

vismConfigToneDetectTable OBJECT-TYPE
    SYNTAX        SEQUENCE OF VismConfigToneDetectEntry
    MAX-ACCESS    not-accessible
    STATUS        current
    DESCRIPTION
            "This table contains the list of user configurable dual
             frequency tones that can be detected on VISM. The call
             agent can request the VISM to detect any of the tones 
             defined in this table.

             Entries to this table can only be added or deleted,
             not modified. Individual parameters within a row 
             cannot be changed without deleting and re-adding
             the entry.
            "
    ::= { vismConfigToneDetectGrp 1 }

vismConfigToneDetectEntry OBJECT-TYPE
    SYNTAX        VismConfigToneDetectEntry
    MAX-ACCESS    not-accessible
    STATUS        current
    DESCRIPTION
        "This is the primary entry in the vismConfigToneDetectTable. 
         Each entry references a User configurable dual 
         frequency tones that can be detected on VISM. 
        "
    INDEX  { vismConfigToneDetectNum }
    ::= { vismConfigToneDetectTable 1 }

VismConfigToneDetectEntry ::=
         SEQUENCE {
                vismConfigToneDetectNum             Integer32,
                vismEventCode                       Integer32,
                vismConfigToneDetectRowStatus       RowStatus,
                vismFreqMaxDeviation                Integer32,
                vismFreqMaxPower                    Integer32,
                vismFreqMinPower                    Integer32,
                vismFreqPowerTwist                  Integer32,
                vismFreqMaxDelay                    Integer32,
                vismMinOnCadence                    Integer32,
                vismMaxOffCadence                   Integer32,
                vismFreqNumOfCadenceMatch           Integer32,
                vismFrequency1                      Integer32,
                vismFrequency2                      Integer32,
                vismFreqOnCadence                   Integer32,
                vismFreqOffCadence                  Integer32
              }

vismConfigToneDetectNum    OBJECT-TYPE
    SYNTAX      Integer32 (1..10)
    MAX-ACCESS  read-only
    STATUS      current
    DESCRIPTION
        "This is the index of this table. Currently only 
         tones 1 to 10 are used and call agent can request up to
         ten tones to be detected on different endpoints at 
         any point in time.
        "
    ::= { vismConfigToneDetectEntry 1 }

vismEventCode   OBJECT-TYPE
    SYNTAX      Integer32 (0..255)
    MAX-ACCESS  read-create
    STATUS      current
    DESCRIPTION
        "This is the secondary index of this table. Call agent can
         request supervision tone detection indexed by this field.
         The values of event code are mapped from the subscriber 
         line event codes defined in RFC2833. Currently VISM supports 
         detection of only a handful of supervision tones like 
         Ringing, Busy, Dial-Tone and SIT tones.
        "
    ::= { vismConfigToneDetectEntry 2 }

vismConfigToneDetectRowStatus  OBJECT-TYPE
    SYNTAX          RowStatus 
    MAX-ACCESS      read-create
    STATUS          current
    DESCRIPTION
            "Controls the creation and deletion of a Config Tone.

             An entry may be created using the 'createAndGo' option.
             When the row is successfully created, the 
             vismConfigToneDetectRowStatus would be set to 'active' 
             by the agent. An entry may be deleted by setting the 
             vismConfigToneDetectRowStatus to 'destroy'. 
            "
    ::= { vismConfigToneDetectEntry 3 }

vismFreqMaxDeviation  OBJECT-TYPE
    SYNTAX            Integer32 (10..125)
    UNITS             "Hz"
    MAX-ACCESS        read-create 
    STATUS            current
    DESCRIPTION
            "Specifies the maximum frequency deviation to be
             used by VISM when detecting a specific dual
             frequency tone. 

             Please refer the VISM configuration guide for standard
             values to be used for this field.
            "
    DEFVAL { 30 }
    ::= { vismConfigToneDetectEntry 4 }

vismFreqMaxPower    OBJECT-TYPE
    SYNTAX          Integer32 (0..30)
    UNITS           "dB"
    MAX-ACCESS      read-create 
    STATUS          current
    DESCRIPTION
            "Specifies the maximum frequency power to be
             used by VISM when detecting a specific dual
             frequency tone.

             Please refer the VISM configuration guide for standard
             values to be used for this field.
            "
    DEFVAL { 0 }
    ::= { vismConfigToneDetectEntry 5 }

vismFreqMinPower    OBJECT-TYPE
    SYNTAX          Integer32 (10..35)
    UNITS           "dB"
    MAX-ACCESS      read-create 
    STATUS          current
    DESCRIPTION
            "Specifies the minimum frequency power to be
             used by VISM when detecting a specific dual 
             frequency tone.

             Please refer the VISM configuration guide for standard
             values to be used for this field.
            "
    DEFVAL { 35 }
    ::= { vismConfigToneDetectEntry 6 }

vismFreqPowerTwist OBJECT-TYPE
    SYNTAX          Integer32 (0..15)
    UNITS           "dB"
    MAX-ACCESS      read-create 
    STATUS          current
    DESCRIPTION
            "Specifies the maximum frequency power twist permitted 
             between the two frequencies used by VISM when 
             detecting a dual frequency tone.

             Please refer the VISM configuration guide for standard
             values to be used for this field.
            "
    DEFVAL { 10 }
    ::= { vismConfigToneDetectEntry 7 }

vismFreqMaxDelay    OBJECT-TYPE
    SYNTAX          Integer32 (0..100)
    UNITS           "milliseconds"
    MAX-ACCESS      read-create 
    STATUS          current
    DESCRIPTION
            "Specifies the maximum frequency delay to be
             used by VISM when detecting a dual frequency tone.

             Please refer the VISM configuration guide for standard
             values to be used for this field. 

             It is measured in units of 10ms.
            "
    DEFVAL { 10 }
    ::= { vismConfigToneDetectEntry 8 }

vismMinOnCadence    OBJECT-TYPE
    SYNTAX          Integer32 (3..100)
    UNITS           "milliseconds"
    MAX-ACCESS      read-create 
    STATUS          current
    DESCRIPTION
            "Specifies the minimum tone cycle ON time that is 
             necessary for the VISM to detect the dual frequency
             tone. The vismMinOnCadence has to be less than
             vismFreqOnCadence value.

             Please refer the VISM configuration guide for standard
             values to be used for this field.
            "
    DEFVAL { 20 }
    ::= { vismConfigToneDetectEntry 9 }

vismMaxOffCadence   OBJECT-TYPE
    SYNTAX          Integer32 (5..5000)
    MAX-ACCESS      read-create 
    STATUS          current
    DESCRIPTION
            "Specifies the maximum tone cycle OFF time that 
             is necessary for the VISM to detect the dual 
             frequency tone. The vismMaxOffCadence should be 
             greater than vismFreqOffCadence value.

             Please refer the VISM configuration guide for standard
             values to be used for this field.
            "
    DEFVAL { 450 }
    ::= { vismConfigToneDetectEntry 10 }

vismFreqNumOfCadenceMatch    OBJECT-TYPE
    SYNTAX          Integer32 (0..6)
    MAX-ACCESS      read-create 
    STATUS          current
    DESCRIPTION
            "Specifies the number of pairs of the dual frequency that
             needs to be detected. Currently ten pairs of frequency can
             be detected by the DSP.
            "
    DEFVAL { 1 }
    ::= { vismConfigToneDetectEntry 11 }

vismFrequency1      OBJECT-TYPE
    SYNTAX          Integer32 (280..3800)
    UNITS           "Hz"
    MAX-ACCESS      read-create 
    STATUS          current
    DESCRIPTION
            "Specifies the 1st frequency component of the dual
             frequency to be detected by the VISM.
            "
    ::= { vismConfigToneDetectEntry 12 }

vismFrequency2      OBJECT-TYPE
    SYNTAX          Integer32 (0..3800)
    UNITS           "Hz"
    MAX-ACCESS      read-create 
    STATUS          current
    DESCRIPTION
            "Specifies the 2nd frequency component of the dual 
             frequency to be detected by the DSP. A value of 0 
             means this is a single frequency. The range of 
             1 to 279 is not a valid range in the DSP. 
            "
    ::= { vismConfigToneDetectEntry 13 }

vismFreqOnCadence   OBJECT-TYPE
    SYNTAX          Integer32 (3..5000)
    UNITS           "milliseconds"
    MAX-ACCESS      read-create 
    STATUS          current
    DESCRIPTION
            "The On time in each cycle of the dual frequency 
             to be detected by the DSP. The vismFreqOnCadence
             has to be less than vismMinOnCadence value.

             It is measured in units of 10ms. 
            "
    ::= { vismConfigToneDetectEntry 14 }

vismFreqOffCadence  OBJECT-TYPE
    SYNTAX          Integer32 (5..5000)
    UNITS           "milliseconds"
    MAX-ACCESS      read-create 
    STATUS          current
    DESCRIPTION
            "The Off time in each cycle of the dual frequency
             to be detected by the DSP. The vismFreqOffCadence
             should be lesser than the vismMaxOffCadence value.

             It is measured in units of 10ms.
            "
    ::= { vismConfigToneDetectEntry 15 }

-- ------------------------------------------------------------------
--
-- vismSequentialToneDetectGrp group
--
-- This group holds the values needed to use the Sequential tone
-- detector on the VISM DSP. It is used to be able to specify
-- the frequencies, cadence, etc  parameters to the DSP. This
-- event can be requested by call agent. 
--
-- the MIB variable values within this group  will be saved over
-- a card reset the objects in this group are only valid in
-- VoIP switching mode.
--
-- ------------------------------------------------------------------
seqToneNumOfFrequencies OBJECT-TYPE
    SYNTAX     Integer32 (1..10)
    MAX-ACCESS read-write
    STATUS     current
    DESCRIPTION
        " The number of single frequencies which have to be detected
          by the sequential tone detector command on VISM. The 
          frequencies should specified below (seqToneFrequency1 to 
          seqToneFrequency10). This number should correspond to the
          non-zero frequency values seqToneFrequency1 to 
          seqToneFrequency10.
        "
    DEFVAL { 3 }
    ::= { vismSequentialToneDetectGrp 1 }

seqToneEventID OBJECT-TYPE
    SYNTAX     Integer32 (0..255)
    MAX-ACCESS read-write
    STATUS     current
    DESCRIPTION
        " The eventID corresponding to the sequential frequency.
          Currently only supports Event 74 (SIT tone)
        "
    DEFVAL { 74 }
    ::= { vismSequentialToneDetectGrp 2 }

seqToneDurationOfEachTone OBJECT-TYPE
    SYNTAX     Integer32 (1..65534)
    MAX-ACCESS read-write
    STATUS     current
    DESCRIPTION
        " Nominal tone duration of each single tone in counts of 10ms
          used with sequential tone detector on VISM DSP.
        "
    DEFVAL { 33 }
    ::= { vismSequentialToneDetectGrp 3 }

seqToneGapBetweenEachTone OBJECT-TYPE
    SYNTAX     Integer32 (1..65534)
    MAX-ACCESS read-write
    STATUS     current
    DESCRIPTION
        " Nominal silence gap duration between each tone in 10ms
          used with sequential tone detector on VISM DSP.
        "
    DEFVAL { 1 }
    ::= { vismSequentialToneDetectGrp 4 }

seqToneDurationDeviation OBJECT-TYPE
    SYNTAX     Integer32 (1..4095)
    MAX-ACCESS read-write
    STATUS     current
    DESCRIPTION
        " Tone duration deviation allowed in 10ms
          used with sequential tone detector on VISM DSP.
        "
    DEFVAL { 2 }
    ::= { vismSequentialToneDetectGrp 5 }

seqToneMaximumGapDuration OBJECT-TYPE
    SYNTAX     Integer32 (1..4095)
    MAX-ACCESS read-write
    STATUS     current
    DESCRIPTION
        " Maximum tone duration allowed in 10ms
          used with sequential tone detector on VISM DSP.
        "
    DEFVAL { 15 }
    ::= { vismSequentialToneDetectGrp 6 }

seqToneGapDurationDeviation OBJECT-TYPE
    SYNTAX     Integer32 (1..4095)
    MAX-ACCESS read-write
    STATUS     current
    DESCRIPTION
        " Tone duration deviation allowed in 10ms
          used with sequential tone detector on VISM DSP.
        "
    DEFVAL { 20 }
    ::= { vismSequentialToneDetectGrp 7 }

seqToneFreqDeviation OBJECT-TYPE
    SYNTAX     Integer32 (1..1000)
    MAX-ACCESS read-write
    STATUS     current
    DESCRIPTION
        " Frequency deviation allowed (1 - 1000 Hz)
          used with sequential tone detector on VISM DSP.
        "
    DEFVAL { 40 }
    ::= { vismSequentialToneDetectGrp 8 }

seqTonePowerLevelCeiling OBJECT-TYPE
    SYNTAX     Integer32 (0..40)
    MAX-ACCESS read-write
    STATUS     current
    DESCRIPTION
        " Maximum ceiling power level of the sequential 
          frequency tone (absolute value in dBm)
          used with sequential tone detector on VISM DSP.
          Range from 0 to 40 (0 to -40dB)
        "
    DEFVAL { 3 }
    ::= { vismSequentialToneDetectGrp 9 }

seqTonePowerLevelFloor OBJECT-TYPE
    SYNTAX     Integer32 (0..40)
    MAX-ACCESS read-write
    STATUS     current
    DESCRIPTION
        " Lowest (floor) power level of the sequential 
          frequency tone (absolute value in dBm)
          used with sequential tone detector on VISM DSP.
          Range from 0 to 40 (0 to -40dB)
        "
    DEFVAL { 40 }
    ::= { vismSequentialToneDetectGrp 10 }

seqToneFrequency1 OBJECT-TYPE
    SYNTAX     Integer32 (280..3800)
    MAX-ACCESS read-write
    STATUS     current
    DESCRIPTION
        " 1st frequency in the SequentialTone to detect (280 - 3800), 
          used with sequential tone detector on VISM DSP.
        "
    DEFVAL { 950 }
    ::= { vismSequentialToneDetectGrp 11 }

seqToneFrequency2 OBJECT-TYPE
    SYNTAX     Integer32 (280..3800)
    MAX-ACCESS read-write
    STATUS     current
    DESCRIPTION
        " 2nd frequency in the SequentialTone to detect (280 - 3800), 
          used with sequential tone detector on VISM DSP.
        "
    DEFVAL { 1400 }
    ::= { vismSequentialToneDetectGrp 12 }

seqToneFrequency3 OBJECT-TYPE
    SYNTAX     Integer32 (280..3800)
    MAX-ACCESS read-write
    STATUS     current
    DESCRIPTION
        " 3rd frequency in the SequentialTone to detect (280 - 3800), 
          used with sequential tone detector on VISM DSP.
        "
    DEFVAL { 1800 }
    ::= { vismSequentialToneDetectGrp 13 }

seqToneFrequency4 OBJECT-TYPE
    SYNTAX     Integer32 (280..3800)
    MAX-ACCESS read-write
    STATUS     current
    DESCRIPTION
        " 4th frequency in the SequentialTone to detect (280 - 3800), 
          used with sequential tone detector on VISM DSP.
        "
    DEFVAL { 280 }
    ::= { vismSequentialToneDetectGrp 14 }

seqToneFrequency5 OBJECT-TYPE
    SYNTAX     Integer32 (280..3800)
    MAX-ACCESS read-write
    STATUS     current
    DESCRIPTION
        " 5th frequency in the SequentialTone to detect (280 - 3800),
          used with sequential tone detector on VISM DSP.
        "
    DEFVAL { 280 }
    ::= { vismSequentialToneDetectGrp 15 }

seqToneFrequency6 OBJECT-TYPE
    SYNTAX     Integer32 (280..3800)
    MAX-ACCESS read-write
    STATUS     current
    DESCRIPTION
        " 6th frequency in the SequentialTone to detect (280 - 3800), 
          used with sequential tone detector on VISM DSP.
        "
    DEFVAL { 280 }
    ::= { vismSequentialToneDetectGrp 16 }

seqToneFrequency7 OBJECT-TYPE
    SYNTAX     Integer32 (280..3800)
    MAX-ACCESS read-write
    STATUS     current
    DESCRIPTION
        " 7th frequency in the SequentialTone to detect (280 - 3800), 
          used with sequential tone detector on VISM DSP.
        "
    DEFVAL { 280 }
    ::= { vismSequentialToneDetectGrp 17 }

seqToneFrequency8 OBJECT-TYPE
    SYNTAX     Integer32 (280..3800)
    MAX-ACCESS read-write
    STATUS     current
    DESCRIPTION
        " 8th frequency in the SequentialTone to detect (280 - 3800), 
          used with sequential tone detector on VISM DSP.
        "
    DEFVAL { 280 }
    ::= { vismSequentialToneDetectGrp 18 }

seqToneFrequency9 OBJECT-TYPE
    SYNTAX     Integer32 (280..3800)
    MAX-ACCESS read-write
    STATUS     current
    DESCRIPTION
        " 9th frequency in the SequentialTone to detect (280 - 3800), 
          used with sequential tone detector on VISM DSP.
        "
    DEFVAL { 280 }
    ::= { vismSequentialToneDetectGrp 19 }

seqToneFrequency10 OBJECT-TYPE
    SYNTAX     Integer32 (280..3800)
    MAX-ACCESS read-write
    STATUS     current
    DESCRIPTION
        " 10th frequency in the SequentialTone to detect (280 - 3800), 
          used with sequential tone detector on VISM DSP.
        "
    DEFVAL { 280 }
    ::= { vismSequentialToneDetectGrp 20 }

-- *****************************************************************
-- vism Tone Plan group notification
-- *****************************************************************
-- *****************************************************************

vismToneNotificationPrefix OBJECT IDENTIFIER ::= 
                             { vismTonePlanGrpMIB 2 }

vismToneNotifications OBJECT IDENTIFIER      ::= 
                             { vismToneNotificationPrefix 0 }

-- **********************************************************************
-- Conformance
-- **********************************************************************

--
-- conformance information
--

vismTonePlanMIBConformance  OBJECT IDENTIFIER  ::= 
                              { vismTonePlanGrpMIB 3 }

vismTonePlanMIBCompliances  OBJECT IDENTIFIER  ::= 
                              { vismTonePlanMIBConformance 1 }
vismTonePlanMIBGroups       OBJECT IDENTIFIER  ::= 
                              { vismTonePlanMIBConformance 2 }

--
-- Conformance and compliance statements statements
--

vismTonePlanMIBCompliance MODULE-COMPLIANCE
    STATUS     current
    DESCRIPTION
            " The complaince statement for VISM Tone Plan group
              which implements vismTonePlanGrp MIB."
    MODULE  -- this module
        MANDATORY-GROUPS { vismTonePlanControlGroup,
                           vismTonePlanTableGroup,
                           vismConfigToneDetectTableGroup,
                           vismSequentialToneDetectGroup
                         }

    OBJECT     vismConfigToneDetectRowStatus 
    SYNTAX     INTEGER {
                  active(1),
                  createAndGo(4),
                  destroy(6)
                }
    DESCRIPTION
        "Only three values 'createAndGo', 'destroy' and
         'active' out of the six enumerated values need to
         be supported.
        "
    ::= { vismTonePlanMIBCompliances 1 }

--
-- units of conformance
--
-- MIB Groups
--

vismTonePlanControlGroup OBJECT-GROUP
   OBJECTS     {
                 tonePlanCurrentSize
               }
    STATUS    current
    DESCRIPTION
            "This group contains objects related to control of
             VISM Tone Plan Table.
             "
    ::= { vismTonePlanMIBGroups 1 }

vismTonePlanTableGroup OBJECT-GROUP
  OBJECTS      {
                 tonePlanEntryStatus,
                 tonePlanProvisionFlag,
                 tonePlanRegionName,
                 tonePlanVersionNumber,
                 tonePlanFileName
                }
    STATUS    current
    DESCRIPTION
            "This group contains objects related to configuration 
             of VISM Tone Plan.
             "
    ::= { vismTonePlanMIBGroups 2 }

vismConfigToneDetectTableGroup OBJECT-GROUP
   OBJECTS    {
                vismConfigToneDetectNum,
                vismEventCode          ,
                vismConfigToneDetectRowStatus,
                vismFreqMaxDeviation,
                vismFreqMaxPower,
                vismFreqMinPower,
                vismFreqPowerTwist,
                vismFreqMaxDelay,
                vismMinOnCadence,
                vismMaxOffCadence,
                vismFreqNumOfCadenceMatch,
                vismFrequency1,
                vismFrequency2,
                vismFreqOnCadence,
                vismFreqOffCadence 
              }
    STATUS    current
    DESCRIPTION
            "This group contains objects related to configuration
             of VISM dual frequency detect tones.
             "
    ::= { vismTonePlanMIBGroups 3 }

vismSequentialToneDetectGroup OBJECT-GROUP
         OBJECTS {
                 seqToneNumOfFrequencies,
                 seqToneEventID,
                 seqToneDurationOfEachTone,
                 seqToneGapBetweenEachTone,
                 seqToneDurationDeviation,
                 seqToneMaximumGapDuration,
                 seqToneGapDurationDeviation,
                 seqToneFreqDeviation,
                 seqTonePowerLevelCeiling,
                 seqTonePowerLevelFloor,
                 seqToneFrequency1,
                 seqToneFrequency2,
                 seqToneFrequency3,
                 seqToneFrequency4,
                 seqToneFrequency5,
                 seqToneFrequency6,
                 seqToneFrequency7,
                 seqToneFrequency8,
                 seqToneFrequency9,
                 seqToneFrequency10
                 }
    STATUS    current
    DESCRIPTION
            "This group contains objects related to configuration
             of VISM sequential single frequency tone detection.
             "
    ::= { vismTonePlanMIBGroups 4 }

END
