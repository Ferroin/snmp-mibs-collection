CISCO-WAN-BBIF-ATM-CONN-MIB DEFINITIONS ::= BEGIN
IMPORTS
        MODULE-IDENTITY,
        OBJECT-TYPE, 
        Integer32       FROM    SNMPv2-SMI
        MODULE-COMPLIANCE,
        OBJECT-GROUP    FROM    SNMPv2-CONF
        TEXTUAL-CONVENTION,
        DisplayString   FROM    SNMPv2-TC
        bbChanCnfGrp,
        bbChanStateGrp  FROM    BASIS-MIB
        ciscoWan        FROM    CISCOWAN-SMI;

ciscoWanBbifAtmConnMIB MODULE-IDENTITY
        LAST-UPDATED    "200209090000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
    DESCRIPTION
        "The MIB module to configure the ATM Connections
        on a broad band interface in PXM1 Service module."

    REVISION    "200209090000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been 
        modified."
    ::= { ciscoWan 35 }

IfNsapAddress ::= TEXTUAL-CONVENTION
	STATUS	current
	DESCRIPTION
		"ATM address used by the networking entity. The only 
		address type presently supported is NSAP (20 octets)"
	SYNTAX	OCTET STRING (SIZE(20))

-- ********************************************************************
--
--
--      BROADBAND CHANNEL  CONFIG Group
--
--
-- ********************************************************************

bbChanCnfGrpTable OBJECT-TYPE
    SYNTAX     SEQUENCE OF BbChanCnfGrpEntry
    MAX-ACCESS not-accessible
    STATUS     current
    DESCRIPTION "
        The Broadband Channel config table is for a channel on logical 
        interface.  There will an entry for each of the channel added on the
        logical partition of the physical line.

        Following parameters are needed if the connection is from a 
        PXM user port and policing is enabled. These apply to 
        connection on PXM lines confiured as user port only.

           PCR/CDVT is used for GCRA1 and
           SCR/MBS is used for GCRA2
           UpcEnable
              UpcPCR
              UpcCDVT
           UpcSCRPolicing
             for CBR conns.
                 UpcPCR0
                 UpcCDVT0
             for non CBR conns.
                 UpcSCR
                 UpcMBS"
    ::= { bbChanCnfGrp 1 }

bbChanCnfGrpEntry OBJECT-TYPE
    SYNTAX     BbChanCnfGrpEntry
    MAX-ACCESS not-accessible
    STATUS     current
    DESCRIPTION 
        "The config table is for logical channel."
    INDEX   { bbChanCnfNum }
    ::= { bbChanCnfGrpTable  1 }

BbChanCnfGrpEntry ::=
    SEQUENCE {
    bbChanCnfNum                   Integer32,
    bbChanRowStatus                INTEGER,
    bbChanConnType                 INTEGER,
    bbChanServiceType              INTEGER,
    bbChanConnDesc                 DisplayString,
    bbChanSvcFlag                  INTEGER,
    bbChanSvcConnId                Integer32,
-- 
-- connection endpoint parameters, 'e'
--
    bbChanIfNum                    Integer32,
    bbChanVpi                      Integer32,
    bbChanVci                      Integer32,
--
-- Note that all these parameters are clp = 0+1 stream
--
    bbChanUpcEnable                INTEGER,
    bbChanUpcPCR                   Integer32,
    bbChanUpcCDVT                  Integer32,
    bbChanUpcSCR                   Integer32,
    bbChanUpcMBS                   Integer32,
    bbChanGcra1Action              INTEGER,
    bbChanGcra2Action              INTEGER,
    bbChanUpcSCRPolicing           INTEGER,
-- 
-- below defines the per-connection based threshold
-- 
    bbChanEfciThreshold            Integer32,
    bbChanDiscardOption            INTEGER,
    bbChanFrmDiscardThreshold      Integer32,
    bbChanClpHiThreshold           Integer32,
    bbChanClpLoThreshold           Integer32,
    bbChanCongstUpdateCode         INTEGER,
    bbChanMaxCellMemThreshold      Integer32,
-- CAC parameters
    bbChanIngrPercentUtil          Integer32,
    bbChanEgrPercentUtil           Integer32,
    bbChanEgrSrvRate               Integer32,
    bbChanOvrSubOvrRide            INTEGER,
--
-- connection parameters, 'x'
-- 
    bbChanLocalVpi                 Integer32,
    bbChanLocalVci                 Integer32,
    bbChanLocalNsapAddr            IfNsapAddress,
--
-- connection parameters, 'y'
-- 
    bbChanRemoteVpi                Integer32,
    bbChanRemoteVci                Integer32,
    bbChanRemoteNsapAddr           IfNsapAddress,
--
-- connection parameters, 'p'
-- 
    bbChanMaster                   INTEGER,
    bbChanRtePriority              Integer32,
    bbChanMaxCost                  Integer32,
    bbChanRestrictTrkType          INTEGER,
--
-- for testcon/testdelay 
--
    bbChanTestType                 INTEGER,
    bbChanTestState                INTEGER,
    bbChanTestResult               Integer32,
-- Variable to support OAM Segment Loopback towards CPE
    bbChanTestTypeCPESide          INTEGER,
    bbChanTestStateCPESide         INTEGER,
-- Connection parameters, used by PXM

    bbConnVpcFlag                  INTEGER,
    bbConnServiceType              INTEGER,
    bbConnPCR                      Integer32,
    bbConnSCR                      Integer32,
    bbConnPercentUtil              Integer32,
    bbRemoteConnPCR                Integer32,
    bbRemoteConnSCR                Integer32,
    bbRemoteConnPercentUtil        Integer32,
    bbChanUpcMCR                   Integer32
    }

bbChanCnfNum OBJECT-TYPE
    SYNTAX     Integer32 (16..4111)
    MAX-ACCESS read-only
    STATUS     current
    DESCRIPTION "
        This identifies a channel on the PXM logical interface, used as 
        PXM port.
    "
    ::= { bbChanCnfGrpEntry 1 }

bbChanRowStatus OBJECT-TYPE
    SYNTAX  INTEGER  {
        add    (1),
        delete (2),
        modify (3)
    }
    MAX-ACCESS read-write
    STATUS     current
    DESCRIPTION
        "This object is used for adding/deleting/modifying
        entries in the table.

        add(1)    :  Adds the entry.
        delete(2) :  Deletes the entry
        modify(3) :  Set this before modifying any entries in the table.

        Following parameters need to be available before creating
        the entry:
            bbChanConnType,
            bbChanServiceType."
    ::= { bbChanCnfGrpEntry 2 }

bbChanConnType OBJECT-TYPE
    SYNTAX  INTEGER  {
           vpc(1),
           vcc(2)
    }
    MAX-ACCESS read-write
    STATUS     current
    DESCRIPTION
        "This specifies the connection type
        vpc(1) : Virtual Path Connection
        vcc(2) : Virtual Channel Connection

        This object can not be modified once the connection is created."
    ::= { bbChanCnfGrpEntry 3 }

bbChanServiceType OBJECT-TYPE
    SYNTAX  INTEGER  {
        cbr    (1),
        vbr    (2),
        abr    (3),
        ubr    (4),
        vbr-rt (5)
    }
    MAX-ACCESS read-write
    STATUS     current
    DESCRIPTION "
        This specifies the service type
        cbr(1)   : Constant Bit Rate
        vbr(2)   : Variable Bit Rate
        abr(3)   : Available Bit Rate
        ubr(4)   : Unspecified Bit Rate
        vbr-rt(5): Variable Bit Rate - Real Time

        This object can not be modified once the connection is created."
    ::= { bbChanCnfGrpEntry 4 }

bbChanConnDesc    OBJECT-TYPE
    SYNTAX     DisplayString (SIZE (0..20))
    MAX-ACCESS read-write
    STATUS     current
    DESCRIPTION
       "A string that has been defined to give a
        descriptive name to the connection."
    ::= { bbChanCnfGrpEntry 5 }

bbChanSvcFlag     OBJECT-TYPE
    SYNTAX  INTEGER {
        svc  (1),
        pvc  (2),
        spvc (3)
    }
    MAX-ACCESS read-write
    STATUS     current
    DESCRIPTION
        "This specifies the connection type
        svc(1)  : SVC connection
        pvc(2)  : PVC connection, used by PAR(Portable Auto Route)
        spvc(3) : Soft PVC connection, used by PNNI"
    ::= { bbChanCnfGrpEntry 6 }

bbChanSvcConnId   OBJECT-TYPE
    SYNTAX     Integer32
    MAX-ACCESS read-write
    STATUS     current
    DESCRIPTION
        "This connection ID is for future use Currently not supported."
    ::= { bbChanCnfGrpEntry 7 }

--
-- connection endpoint parameters, 'e'
--

bbChanIfNum OBJECT-TYPE
    SYNTAX     Integer32 (1..32)
    MAX-ACCESS read-write
    STATUS     current
    DESCRIPTION 
        "Channel's logical Interface from which traffic of the connection
        will be received."
    ::= { bbChanCnfGrpEntry 8}

bbChanVpi OBJECT-TYPE
    SYNTAX     Integer32 (0..4095)
    MAX-ACCESS read-write
    STATUS     current
    DESCRIPTION
        "VPI for the connection."
    ::= { bbChanCnfGrpEntry 9}

bbChanVci OBJECT-TYPE
    SYNTAX     Integer32 (0..'ffff'h)
    MAX-ACCESS read-write
    STATUS     current
    DESCRIPTION
        "VCI for the connection."
    ::= { bbChanCnfGrpEntry 10}

--
-- UPC parameters
-- 

bbChanUpcEnable OBJECT-TYPE
    SYNTAX  INTEGER {
        disable (1),
        enable (2)
    }
    MAX-ACCESS read-write
    STATUS     current
    DESCRIPTION
        "enables/disables UPC for Ingress cells."
    DEFVAL { enable }
    ::= { bbChanCnfGrpEntry 11}

bbChanUpcPCR OBJECT-TYPE
    SYNTAX     Integer32 (50..1412832)
    MAX-ACCESS read-write
    STATUS     current
    DESCRIPTION
         "PCR(0+1), Peak Cell Rate, specifies an upper bound on
         rate at which traffic can be submitted on an ATM
         connection. This object applies to the First Leaky
         Bucket for leaving cells with Cell Loss Priority of 0 or 1.
         . Units: cells per second.
         . Applicable connection types:
           UBR, CBR, VBR, ABR
         . Default: 50
         . Ranges:
           T3  : 50-96000
           E3  : 50-80000
           OC3 : 50-353208
           OC12: 50-1412832

         PCR is used for GCRA1."
    ::= { bbChanCnfGrpEntry 12}

bbChanUpcCDVT OBJECT-TYPE
    SYNTAX     Integer32 (1..5000000)     
    MAX-ACCESS read-write
    STATUS     current
    DESCRIPTION 
        "Compliant Cell Delay Variation. Also known as
        CDVT(0+1), Cell Delay Variation Tolerance, which
        specifies the maximum time period for accumulated
        violations of cell-arrival time parameters. This object
        applies to the First Leaky bucket for cells with Cell
        Loss Priority of 0 or 1.
            . Units: microseconds.
            . Applicable connection types:
               UBR, CBR, VBR, ABR
            . Default:
               CBR:    10000
               Others: 250000
    "
    ::= { bbChanCnfGrpEntry 13}

bbChanUpcSCR OBJECT-TYPE
    SYNTAX     Integer32 (1..1412832)
    MAX-ACCESS read-write
    STATUS     current
    DESCRIPTION "
         SCR, Sustainable Cell Rate, is an upper bound on the
         conforming average rate of an ATM connection, over
         time scales which are long relative to those for which
         the PCR is defined. Enforcement of this bound by the UPC
         could allow the network to allocate sufficient resources,
         but less than thos based on the PCR, and still ensure
         that the performance objectives (e.g., Cell Loss Ratio)
         can be achieved.
         . Units: cell per second.
         . Applicable connection types:
           . VBR, ABR
         . Ranges:
             T3  :  50-96000
             E3  :  50-80000
             OC3 :  50-353208
             OC12:  50-1412832
         . Default: 50
    "
    ::= { bbChanCnfGrpEntry 14}

bbChanUpcMBS OBJECT-TYPE
    SYNTAX     Integer32 (1..5000000)
    MAX-ACCESS read-write
    STATUS     current
    DESCRIPTION
        "Maximum Burst Size (MBS). Also known as Compliant Burst Size (CBS).
            . Units: cells
            . Applicable connection types:
                . VBR, ABR
            . Default: 1000
            . Range  : 1-5000000
      "
    ::= { bbChanCnfGrpEntry 15}

bbChanGcra1Action OBJECT-TYPE
    SYNTAX  INTEGER {
        noAction(1),
        tagCells(2),
        tagAndDiscard(3),
        discardAllNonComformCells(4)
    }
    MAX-ACCESS read-write
    STATUS     current
    DESCRIPTION
        "GCRA1 Action.
        1 = No Action
        2 = Tag Untagged cells
        3 = Tag untagged cells and discard tagged cells
        4 = Discard all (0+1) non-comforming cells."
    DEFVAL { discardAllNonComformCells }
    ::= { bbChanCnfGrpEntry 16 }

bbChanGcra2Action OBJECT-TYPE
    SYNTAX  INTEGER {
        noAction(1),
        tagCells(2),
        tagAndDiscard(3),
        discardAllNonComformCells(4)
    }
    MAX-ACCESS  read-write
    STATUS  current
    DESCRIPTION
        "GCRA2 Action.
         1 = No Action
         2 = Tag Untagged cells
         3 = Tag untagged cells and discard tagged cells
         4 = Discard all (0+1) non-comforming cells."
    DEFVAL { discardAllNonComformCells }
    ::= { bbChanCnfGrpEntry 17 }

bbChanUpcSCRPolicing OBJECT-TYPE
    SYNTAX  INTEGER {
        clp0 (1),
        clp0and1 (2),
        off (3)
    }
    MAX-ACCESS read-write
    STATUS     current
    DESCRIPTION
        "Selects SCR policing for CLP = 0 or all cells."
    ::= { bbChanCnfGrpEntry 18}

bbChanEfciThreshold OBJECT-TYPE
    SYNTAX     Integer32 (0..491520)
    MAX-ACCESS read-write
    STATUS     current
    DESCRIPTION
        "Threshold above which EFCI bit is to be set.
        Default Value  is 3/4 of max cell count."
	DEFVAL { 196608 }
    ::= { bbChanCnfGrpEntry 19 }

bbChanDiscardOption OBJECT-TYPE
    SYNTAX  INTEGER {
        clpHysteresis(1),
        frameDiscard(2)
    }
    MAX-ACCESS read-write
    STATUS     current
    DESCRIPTION
        "Enable Frame Discard or CLP Hysteresis."
    DEFVAL { clpHysteresis }
    ::= { bbChanCnfGrpEntry 20 }

bbChanFrmDiscardThreshold OBJECT-TYPE
    SYNTAX     Integer32 (0..491520)
    MAX-ACCESS read-write
    STATUS     current
    DESCRIPTION
        "Ingress Frame Discard Threshold.
        Valid only when Ingress Frame Discard option is selected."
    ::= { bbChanCnfGrpEntry 21 }

bbChanClpHiThreshold OBJECT-TYPE
    SYNTAX     Integer32 (0..491520)
    MAX-ACCESS read-write
    STATUS     current
    DESCRIPTION
        "Ingress CLP High Threshold.
	Default is 3/4 of max cell count."
	DEFVAL { 196608 }
    ::= { bbChanCnfGrpEntry 22 }

bbChanClpLoThreshold OBJECT-TYPE
    SYNTAX     Integer32 (0..491520)
    MAX-ACCESS read-write
    STATUS     current
    DESCRIPTION
        "Ingress CLP Low Threshold. Valid only when
        Ingress CLP Hysteresis option is selected.

        Default Value is 1/2 of max cell count."
	DEFVAL { 131072 }
    ::= { bbChanCnfGrpEntry 23 }

bbChanCongstUpdateCode OBJECT-TYPE
    SYNTAX  INTEGER  {
        dontUpdate(1),
        setCiBit(2),
        setEfciBit(3),
        clearEfciBit(4)
    }
    MAX-ACCESS read-write
    STATUS     current
    DESCRIPTION
        "Ingress Channel Congestion Update Code."
    ::= { bbChanCnfGrpEntry 24 }

bbChanMaxCellMemThreshold OBJECT-TYPE
    SYNTAX     Integer32 (0..512000)
    MAX-ACCESS read-write
    STATUS     current
    DESCRIPTION
        "Maximum number of cells of that connection in
        the memory.
	Assuming Total Cell Memory is 512K cells, this is defaulted to
	half of total size."
	DEFVAL { 262144 }
    ::= { bbChanCnfGrpEntry 25 }

-- CAC parameters

bbChanIngrPercentUtil OBJECT-TYPE
    SYNTAX     Integer32 (0..100)
    MAX-ACCESS read-write
    STATUS     current
    DESCRIPTION
        "Percentage Utilization of the IngrService Rate. This is used
        for connection admission control."
    ::= { bbChanCnfGrpEntry 26}

bbChanEgrPercentUtil OBJECT-TYPE
    SYNTAX  Integer32 (0..100)
    MAX-ACCESS  read-write
    STATUS  current
    DESCRIPTION
        "Percentage Utilization of the EgrService Rate.
        This is used for egress bandwidth calculation and 
        connection admission control."
    ::= { bbChanCnfGrpEntry 27 }

bbChanEgrSrvRate OBJECT-TYPE
    SYNTAX     Integer32 (1..1412832)
    MAX-ACCESS read-write
    STATUS     current
    DESCRIPTION
        "Egress service rate - This is used for egress bandwidth calculation
        and for connection admission control. The actual value
        depends on the speed of the logical interface."
    ::= { bbChanCnfGrpEntry 28 }

bbChanOvrSubOvrRide OBJECT-TYPE
    SYNTAX  INTEGER {
            disable (1),
            enable (2)
    }
    MAX-ACCESS read-write
    STATUS     current
    DESCRIPTION
        "Channel Over Subscrive Override
        This MIB variable allows one to add a new connection on a port
        even if it is over subscribed.
    "
    DEFVAL { disable }
    ::= { bbChanCnfGrpEntry 29 }

--
-- connection parameters, 'x'
--

bbChanLocalVpi OBJECT-TYPE
    SYNTAX     Integer32 (0..4095)
    MAX-ACCESS read-only
    STATUS     current
    DESCRIPTION
        "The VPI value for this channel."
    ::= { bbChanCnfGrpEntry 30 }

bbChanLocalVci OBJECT-TYPE
    SYNTAX  Integer32 (0..'ffff'h)
    MAX-ACCESS  read-only
    STATUS  current
    DESCRIPTION
        "The VCI value for this channel."
    ::= { bbChanCnfGrpEntry 31 }

bbChanLocalNsapAddr OBJECT-TYPE
    SYNTAX  IfNsapAddress
    MAX-ACCESS  read-write
    STATUS  current
    DESCRIPTION
        "The Near End NSAP Address  value for this channel."
    ::= { bbChanCnfGrpEntry 32 }

--
-- connection parameters, 'y'
--
bbChanRemoteVpi OBJECT-TYPE
    SYNTAX     Integer32 (0..4095)
    MAX-ACCESS read-write
    STATUS     current
    DESCRIPTION
        "The VPI value for this channel."
    ::= { bbChanCnfGrpEntry 33 }

bbChanRemoteVci OBJECT-TYPE
    SYNTAX     Integer32 (0..'ffff'h)
    MAX-ACCESS read-write
    STATUS     current
    DESCRIPTION
        "The VCI value for this channel."
    ::= { bbChanCnfGrpEntry 34 }

bbChanRemoteNsapAddr OBJECT-TYPE
    SYNTAX     IfNsapAddress
    MAX-ACCESS read-write
    STATUS     current
    DESCRIPTION
        "The Far End NSAP Address  value for this channel."
    ::= { bbChanCnfGrpEntry 35 }

--
-- connection parameters, 'p'
--

bbChanMaster OBJECT-TYPE
    SYNTAX  INTEGER {
        master  (1),
        slave   (2),
        unknown (3)

    }
    MAX-ACCESS  read-write
    STATUS  current
    DESCRIPTION
        "This is used by the PXM switch platform module, 
        to determine if this endpoint ia master or slave."
    ::= { bbChanCnfGrpEntry 36 }

bbChanRtePriority OBJECT-TYPE
    SYNTAX     Integer32 (1..15)
    MAX-ACCESS read-write
    STATUS     current
    DESCRIPTION
        "This is also known as class of service, it is used by 
        PXM to determine how important this connection is when
        selecting connections to route."
    DEFVAL { 1 }
    ::= { bbChanCnfGrpEntry 37 }

bbChanMaxCost OBJECT-TYPE
    SYNTAX     Integer32 (1..65535)
    MAX-ACCESS read-write
    STATUS     current
    DESCRIPTION
        "Maximum allowed cost. It is related to Cost Based Routing.
        This is used by PXM so that it won't choose a path with a
        cost greater than this configured level."
    DEFVAL { 255 }
    ::= { bbChanCnfGrpEntry 38 }

bbChanRestrictTrkType OBJECT-TYPE
    SYNTAX  INTEGER {
        noRestriction    (1),
        terrestrialTrunk (2),
        satelliteTrunk   (3)
    }
    MAX-ACCESS  read-write
    STATUS  current
    DESCRIPTION
        "Restricted trunk type for routind, used by PXM. 
        It specifies that the connection either cannot be 
        routed over satellite trunks or terrestrial trunks,
        or it can be on any type of trunk."
    DEFVAL { noRestriction }
    ::= { bbChanCnfGrpEntry 39 }

--
-- for testcon/testdelay
--
bbChanTestType OBJECT-TYPE
    SYNTAX  INTEGER {
        testcon(1),
        testdelay(2),
        notest(3)
    }
    MAX-ACCESS read-write
    STATUS  current
    DESCRIPTION
        "The chanTestType starts testing the continuity or delay 
        of a connection. It sends specific cell patterns toward 
        the network and the terminating end of this connection 
        has to be an AXIS or ASI of a BPX in order for this test 
        to be working. The receiving node would loop back when 
        it receives these cells. The test should be done in 
        about couple of seconds. 
        testcon(1) : The testcon tests the continuity of
                     the connection and testdelay uses the same
                     test except that it measures for delay through 
                     the network.

        To test the delay follow this procedure:
          a- set chanTestType to testdelay
          b- read chanTestState till it is Pass or Fail
          c- Read chanTestResult for the delay if it is Pass

        * Note that the chanTestType would go back to notest when the
          test is completed
         To test the continuity follow this procedure:
          a- set chanTestType to testcon
          b- read chanTestState till it is Pass or Fail
        * Note that the chanTestType would go back to notest when the
         test is completed

        You CAN NOT select 2 tests back to back, you have to select one
        and wait for the result and then start the other one."
    DEFVAL { notest }
    ::= { bbChanCnfGrpEntry 40 }

bbChanTestState OBJECT-TYPE
    SYNTAX  INTEGER {
        passed        (1),
        failed        (2),
        inprogress    (3),
        notinprogress (4)
    }
    MAX-ACCESS read-only
    STATUS  current
    DESCRIPTION
        "This object provides the state of the test performed 
        on a connection.
        When you add a connection then the chanTestState becomes notinprogress
        and when you select any test, it would go to inprogress state and after
        it completes the test, it will go to failed or passed state.
        1 = Passed
        2 = Failed
        3 = In Progress
        4 = Not In Progress
    "
    ::= { bbChanCnfGrpEntry 41 }

bbChanTestResult OBJECT-TYPE
    SYNTAX     Integer32 (1..65535)
    UNITS      "milliseconds"
    MAX-ACCESS read-only
    STATUS     current
    DESCRIPTION
        "This is round trip delay in milliseconds.
        When you select testdelay option for the chanTestType, 
        the result of the test that is measured in milliseconds
        can be read in chanTestResult."
    ::= { bbChanCnfGrpEntry 42 }

-- CPE side OAM segment loopback

bbChanTestTypeCPESide     OBJECT-TYPE
    SYNTAX  INTEGER {
        testconseg(1),
        notest(2)
    }
    MAX-ACCESS read-write
    STATUS  current
    DESCRIPTION
        "The chanTestType starts testing the segment continuity 
        of a connection.
        It sends OAM Segment loopback cell towards port side (CPE)
        The CPE would loop back the cell
        To test the continuity follow this procedure:
        a- set chanTestTypeCPEside to testconseg
        b- read chanTestState till it is Pass or Fail

        *Note that the chanTestType would go back to notest when the
         test is completed."
    DEFVAL { notest }
    ::= { bbChanCnfGrpEntry 43}

bbChanTestStateCPESide    OBJECT-TYPE
    SYNTAX  INTEGER {
        passed(1),
        failed(2),
        inprogress(3),
        notinprogress(4)
    }
    MAX-ACCESS read-only
    STATUS     current
    DESCRIPTION
        "This shows the state of the test
        When you add a connection then the chanTestState becomes notinprogress
        and when you select any test, it would go to inprogress state and after
        it completes the test, it will go to failed or passed state.
        1 = Passed
        2 = Failed
        3 = In Progress
        4 = Not In Progress"
    ::= { bbChanCnfGrpEntry 44}

bbConnVpcFlag OBJECT-TYPE
    SYNTAX INTEGER {
        vpc (1),
        vcc (2)
    }
    MAX-ACCESS read-write
    STATUS current
    DESCRIPTION
        "This represents the connection type, used for PXM to
        identify VPC/VCC."
    ::= { bbChanCnfGrpEntry 45 }

bbConnServiceType OBJECT-TYPE
    SYNTAX INTEGER{
        cbr    (1),
        vbr    (2),
        ubr    (4),
        abrstd (6),
	vbrrt  (8)
    }
    MAX-ACCESS read-write
    STATUS current
    DESCRIPTION "
        This specifies the service type
          1 ==> Constant Bit Rate
          2 ==> Variable Bit Rate
          4 ==> Unspecified Bit Rate
          6 ==> Available Bit Rate ( standard )
          8 ==> Variable Bit Rate - Real-Time

        Note that this is used by PXM card,
        Also to make it compatible with existing AUSM MIB definition,
        value 3 is not used.

        foresight ABR is not supported in PXM , i.e Virtual Service Module
    "
    ::= { bbChanCnfGrpEntry 46 }

bbConnPCR OBJECT-TYPE
    SYNTAX Integer32
    MAX-ACCESS read-write
    STATUS current
    DESCRIPTION " 
        Peak cell rate, could be derived from the end point parameter
    "
    ::= { bbChanCnfGrpEntry 47 }

bbConnSCR OBJECT-TYPE
    SYNTAX Integer32
    MAX-ACCESS read-write
    STATUS current
    DESCRIPTION " 
        Sustained cell rate, could be derived from the end point parameter
    "
    ::= { bbChanCnfGrpEntry 48 }

bbConnPercentUtil OBJECT-TYPE
    SYNTAX Integer32 ( 0..100 )
    MAX-ACCESS read-write
    STATUS current
    DESCRIPTION "
        This is the expected long-term utilization of the
        channel by this end-point.
    "
	DEFVAL {100}
    ::= {bbChanCnfGrpEntry 49 }

bbRemoteConnPCR OBJECT-TYPE
    SYNTAX Integer32
    MAX-ACCESS read-write
    STATUS current
    DESCRIPTION " 
		Peak cell rate of the other end, if not set, will be
        set to the same as local end PCR (bbChanUpcPCR). However,
        note that if the PCRs for both local and remote end
        are set to the different value (i.e., asymmetric conn),
        then this should be set differently from local end PCR.
    "
    ::= { bbChanCnfGrpEntry 50 }

bbRemoteConnSCR OBJECT-TYPE
    SYNTAX Integer32
    MAX-ACCESS read-write
    STATUS current
    DESCRIPTION " 
		Sustained cell rate of the other end, if not set, will be
        set to the same as local end SCR (bbChanUpcSCR). However,
        note that if the PCRs for both local and remote end
        are set to the different value (i.e., asymmetric conn),
        then this should be set differently from local end SCR.
    "
    ::= { bbChanCnfGrpEntry 51 }

bbRemoteConnPercentUtil OBJECT-TYPE
    SYNTAX Integer32 ( 0..100 )
    MAX-ACCESS read-write
    STATUS current
    DESCRIPTION "
		This is the expected long-term utilization of the
        channel by this end-point. If this is not specified in
        the connection setup request, it'll be defaulted to
        100 percent
    "
	DEFVAL {100}
    ::= {bbChanCnfGrpEntry 52 }

bbChanUpcMCR OBJECT-TYPE
    SYNTAX  Integer32 (1..1412832)
    MAX-ACCESS read-write
    STATUS  current
    DESCRIPTION "
         SCR, Sustainable Cell Rate, is an upper bound on the
         conforming average rate of an ATM connection, over
         time scales which are long relative to those for which
         the PCR is defined. Enforcement of this bound by the UPC
         could allow the network to allocate sufficient resources,
         but less than thos based on the PCR, and still ensure
         that the performance objectives (e.g., Cell Loss Ratio)
         can be achieved.
         . Units: cell per second.
         . Applicable connection types:
           . ABR
         . Ranges:
             T3  :  50-96000
             E3  :  50-80000
             OC3 :  50-353208
             OC12:  50-1412832
         . Default: 50
    "
    ::= { bbChanCnfGrpEntry 53}

-- ---------------------------------------------------------------------

--
--  Next available channel
--

bbChanNumNextAvailable OBJECT-TYPE
    SYNTAX  Integer32 (16..4111)
    MAX-ACCESS  read-only
    STATUS  current
    DESCRIPTION "
        This variable contains the next unused channel number of the possible
        4096 . This number can be used in channel config table.
        ChanNumNextAvailable gets updated whenever this number is used to
        create a new logical channel. Value 0 for this variable indicates that
        no more channels are available. 
    "
    ::= { bbChanCnfGrp 2 }

-- NextAvailable local  VPID

bbChanVpIdNextAvailable OBJECT-TYPE
    SYNTAX  Integer32 (1..4095)
    MAX-ACCESS  read-only
    STATUS  current
    DESCRIPTION "

        This in only valid for a Service Module, will NOT be used in PXM.

        This variable contains the next unused local VPId of the possible
        1 to 4095. This number can be used in channel config table. It gets
        updated if the number is used to create a new vp connection. 

        The max. no. of VP conn.s is limited to the VPI range configured
        for this logical interface.
        Value of 0 for this variable indicates that no more vp connections 
        are available
    "
    ::= { bbChanCnfGrp 3 }

-- ********************************************************************
--
--
--      BROADBAND CHANNEL  State Group
--
--
-- ********************************************************************

bbChanStateGrpTable OBJECT-TYPE
    SYNTAX  SEQUENCE OF BbChanStateGrpEntry
    MAX-ACCESS  not-accessible
    STATUS  current
    DESCRIPTION "
        The Broadband Channel state table is for a channel on logical
        interface.  There will an entry for each of the channel added on the
        logical partition of the physical line.
    "
    ::= { bbChanStateGrp 1 }

bbChanStateGrpEntry OBJECT-TYPE
    SYNTAX  BbChanStateGrpEntry
    MAX-ACCESS  not-accessible
    STATUS  current
    DESCRIPTION "
        The state table is for logical channel.
        The available number of channels on the broadband interface (user ports)
        on the PXM card is restricted to 4K.

        The PXM card has 2 Queue Engines ( QE0 and QE1).
        Current calculations allow 31954 GLCNs on QE0, and 31748 GLCNs on QE1.
    "
    INDEX   { bbChanStateNum }
    ::= { bbChanStateGrpTable  1 }

BbChanStateGrpEntry ::=
    SEQUENCE {
        bbChanStateNum     Integer32,
        bbChanState        INTEGER,
        bbChanEgrXmtState  INTEGER,
        bbChanIngrRcvState INTEGER
    }

bbChanStateNum OBJECT-TYPE
    SYNTAX  Integer32 (16..4111)
    MAX-ACCESS  read-only
    STATUS  current
    DESCRIPTION
        "Refers to the logical channel number."
    ::= { bbChanStateGrpEntry 1}

bbChanState OBJECT-TYPE
    SYNTAX  INTEGER {
        notconfigured (1),
        normal        (2),
        alarm         (3)
    }
    MAX-ACCESS  read-only
    STATUS  current
    DESCRIPTION
        "This variable indicates the state of the VC (channel)."
    ::= { bbChanStateGrpEntry 2}

bbChanEgrXmtState OBJECT-TYPE
    SYNTAX INTEGER {
        other       (1),
        normal      (2),
        sendingAis  (3),
        sendingFerf (4)
	}
    MAX-ACCESS read-only
    STATUS current
    DESCRIPTION
        "Indicates the status of port transmit(Egress)."
    ::= { bbChanStateGrpEntry 3}

bbChanIngrRcvState OBJECT-TYPE
    SYNTAX INTEGER {
               other         (1),
               normal        (2),
               receivingAis  (3),
               receivingFerf (4),
               alarm         (5)
           }
    MAX-ACCESS read-only
    STATUS current
    DESCRIPTION
	"indicates the status of port receive(Ingress)."
    ::= { bbChanStateGrpEntry 4}

-- conformance information

cwbAtmConnMIBConformance OBJECT IDENTIFIER ::= { ciscoWanBbifAtmConnMIB 2 }

cwbAtmConnMIBGroups       OBJECT IDENTIFIER ::= 
                              { cwbAtmConnMIBConformance 1 }
cwbAtmConnMIBCompliances OBJECT IDENTIFIER ::= 
                              { cwbAtmConnMIBConformance 2 }

-- compliance statements

cwbAtmConnCompliance MODULE-COMPLIANCE
    STATUS  current
    DESCRIPTION
        "The compliance statement for SNMP entities 
         which support Frame realy connection MIB."
    MODULE  -- this module
        MANDATORY-GROUPS {
            cwbAtmConnGroup,
            cwbAtmConnStateGroup 
        }

    GROUP cwbAtmConnGeneralGroup
    DESCRIPTION
        "This group is mandatory for systems, where
        it is required to know the next available resource
        for NMS applications."
    ::= { cwbAtmConnMIBCompliances 1 }

cwbAtmConnGroup OBJECT-GROUP
    OBJECTS {
        bbChanCnfNum,
        bbChanRowStatus,
        bbChanConnType,
        bbChanServiceType,
        bbChanConnDesc,
        bbChanSvcFlag,
        bbChanSvcConnId,
        bbChanIfNum,
        bbChanVpi,
        bbChanVci,
        bbChanUpcEnable,
        bbChanUpcPCR,
        bbChanUpcCDVT,
        bbChanUpcSCR,
        bbChanUpcMBS,
        bbChanGcra1Action,
        bbChanGcra2Action,
        bbChanUpcSCRPolicing,
        bbChanEfciThreshold,
        bbChanDiscardOption,
        bbChanFrmDiscardThreshold,
        bbChanClpHiThreshold,
        bbChanClpLoThreshold,
        bbChanCongstUpdateCode,
        bbChanMaxCellMemThreshold,
        bbChanIngrPercentUtil,
        bbChanEgrPercentUtil,
        bbChanEgrSrvRate,
        bbChanOvrSubOvrRide,
        bbChanLocalVpi,
        bbChanLocalVci,
        bbChanLocalNsapAddr,
        bbChanRemoteVpi,
        bbChanRemoteVci,
        bbChanRemoteNsapAddr,
        bbChanMaster,
        bbChanRtePriority,
        bbChanMaxCost,
        bbChanRestrictTrkType,
        bbChanTestType,
        bbChanTestState,
        bbChanTestResult,
        bbChanTestTypeCPESide,
        bbChanTestStateCPESide,
        bbConnVpcFlag,
        bbConnServiceType,
        bbConnPCR,
        bbConnSCR,
        bbConnPercentUtil,
        bbRemoteConnPCR,
        bbRemoteConnSCR,
        bbRemoteConnPercentUtil,
        bbChanUpcMCR
    }
    STATUS current
    DESCRIPTION 
        "A collection of objects providing information
        applicable to an ATM Connection on broad band interfaces."
    ::= { cwbAtmConnMIBGroups 1 }

cwbAtmConnStateGroup OBJECT-GROUP
    OBJECTS {
        bbChanStateNum,
        bbChanState,
        bbChanEgrXmtState,
        bbChanIngrRcvState
    }
    STATUS current
    DESCRIPTION 
        "A collection of objects related to state
        of ATM Connections on Broad band interface."
    ::= { cwbAtmConnMIBGroups 2 }

cwbAtmConnGeneralGroup OBJECT-GROUP
    OBJECTS {
        bbChanNumNextAvailable,
        bbChanVpIdNextAvailable
    }
    STATUS current
    DESCRIPTION 
        "A collection of objects related to next 
        available channeli number and next available
       VPI value of connections supported."
    ::= { cwbAtmConnMIBGroups 3 }

END
