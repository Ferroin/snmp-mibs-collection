CISCO-DISMAN-EVENT-CAPABILITY DEFINITIONS ::= BEGIN

IMPORTS
        MODULE-IDENTITY
                FROM SNMPv2-SMI
        AGENT-CAPABILITIES
                FROM SNMPv2-CONF
        ciscoAgentCapability
                FROM CISCO-SMI;

cdismanEventCapability MODULE-IDENTITY
        LAST-UPDATED    "200601160000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com
                        cs-snmp@cisco.com"
        DESCRIPTION
                "The capabilities description of
                 DISMAN-EVENT-MIB."

        REVISION        "200601160000Z"
        DESCRIPTION
                "Initial version of this MIB module."
        ::= { ciscoAgentCapability 473 }

cdismanEventCapabilityIOSXRV3R2R0CRS1 AGENT-CAPABILITIES
    PRODUCT-RELEASE     "Cisco IOS XR 3.2.0 for CRS-1"
    STATUS              current
    DESCRIPTION         "DISMAN-EVENT-MIB capabilities for
                        IOS XR release 3.2.0"

    SUPPORTS            DISMAN-EVENT-MIB
        INCLUDES        { dismanEventResourceGroup,
                          dismanEventTriggerGroup,
                          dismanEventObjectsGroup,
                          dismanEventEventGroup,
                          dismanEventNotificationObjectGroup }

    VARIATION           mteTriggerContextNameWildcard
    ACCESS              not-implemented
    DESCRIPTION         "Not supported in IOS code from where 
                        this code was ported."

    VARIATION           mteFailedReason
    ACCESS              not-implemented
    DESCRIPTION         "This object is not supported in the current
                        MIB implementation."
    ::= { cdismanEventCapability 1 }

END
