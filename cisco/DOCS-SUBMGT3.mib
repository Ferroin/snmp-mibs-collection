DOCS-SUBMGT3-MIB DEFINITIONS ::= BEGIN 
  IMPORTS 
    MODULE-IDENTITY, 
    OBJECT-TYPE, 
    Unsigned32, 
    Counter64 
             FROM SNMPv2-SMI          -- RFC 2578 
    RowStatus, 
    TruthValue, 
    TimeStamp, 
    MacAddress 
             FROM SNMPv2-TC           -- RFC 2579 
    OBJECT-GROUP, 
    MODULE-COMPLIANCE 
             FROM SNMPv2-CONF         -- RFC 2580 
    InetAddressType, 
    InetAddress, 
    InetAddressPrefixLength, 
    InetPortNumber 
             FROM INET-ADDRESS-MIB    -- RFC 4001 
    docsIf3CmtsCmRegStatusEntry, 
    docsIf3CmtsCmRegStatusId 
             FROM DOCS-IF3-MIB 
   SnmpTagList              
             FROM SNMP-TARGET-MIB     -- RFC 3411 
   DocsL2vpnIfList  
             FROM DOCS-L2VPN-MIB 
    clabProjDocsis 
             FROM CLAB-DEF-MIB; 

docsSubmgt3Mib MODULE-IDENTITY 
     LAST-UPDATED    "200705180000Z" -- May 18, 2007 
     ORGANIZATION    "Cable Television Laboratories, Inc." 
     CONTACT-INFO 
         " 
         Postal: Cable Television Laboratories, Inc. 
         858 Coal Creek Circle 
         Louisville, Colorado 80027-9750 
         U.S.A. 
         Phone: +1 303-661-9100 
         Fax:   +1 303-661-9199 
         E-mail: mibs@cablelabs.com" 
     DESCRIPTION 
        "This MIB module contains the management objects for the 
        CMTS control of the IP4 and IPv6 traffic with origin and 
        destination to CMs and/or CPEs behind the CM." 
    REVISION    "200705180000Z" -- May 18, 2007 
    DESCRIPTION 
            "Revised Version includes ECNs 
            OSSIv3.0-N-07.0445-3 
            OSSIv3.0-N-07.0444-3 
            OSSIv3.0-N-07.0441-4 
            and published as I03" 
     REVISION        "200612071700Z" -- Dec 7, 2006 
     DESCRIPTION 
        "Initial version, published as part of the CableLabs 
        OSSIv3.0 specification CM-SP-OSSIv3.0-I01-061207 
        Copyright 1999-2006 Cable Television Laboratories, Inc. 
        All rights reserved." 
     ::= {  clabProjDocsis 10 } 

-- Textual Conventions 

-- Object Definitions 
docsSubmgt3MibObjects  OBJECT IDENTIFIER ::= { docsSubmgt3Mib 1 } 

docsSubmgt3Base OBJECT IDENTIFIER ::= { docsSubmgt3MibObjects 1 } 

docsSubmgt3BaseCpeMaxIpv4Def OBJECT-TYPE 
     SYNTAX      Unsigned32 (0..1023) 
     MAX-ACCESS  read-write 
     STATUS      current 
     DESCRIPTION 
        "This attribute represents the maximum number of IPv4  
        Addresses allowed for the CM's CPEs if not signaled in the  
        registration process." 
     DEFVAL { 16 } 
     ::= { docsSubmgt3Base 1 } 

docsSubmgt3BaseCpeMaxIpv6PrefixDef OBJECT-TYPE 
     SYNTAX      Unsigned32 (0..1023) 
     MAX-ACCESS  read-write 
     STATUS      current 
     DESCRIPTION 
        "This attribute represents the maximum number of IPv6  
         prefixes allowed for the CM's CPEs if not signaled in 
         the registration process." 
     DEFVAL { 16 } 
     ::= { docsSubmgt3Base 2 } 

docsSubmgt3BaseCpeActiveDef OBJECT-TYPE 
     SYNTAX      TruthValue 
     MAX-ACCESS  read-write 
     STATUS      current 
     DESCRIPTION 
        "This attribute represents the default value for enabling 
        Subscriber Management filters and controls 
        in the CM if the parameter is not signaled in the DOCSIS 
        Registration process." 
     DEFVAL { false } 
     ::= { docsSubmgt3Base 3 } 

docsSubmgt3BaseCpeLearnableDef OBJECT-TYPE 
     SYNTAX      TruthValue 
     MAX-ACCESS  read-write 
     STATUS      current 
     DESCRIPTION 
        "This attribute represents the default value for enabling 
        the CPE learning process for the CM if the parameter 
        is not signaled in the DOCSIS Registration process." 
     DEFVAL { true } 
     ::= { docsSubmgt3Base 4 } 

docsSubmgt3BaseSubFilterDownDef OBJECT-TYPE 
     SYNTAX      Unsigned32 (0..1024) 
     MAX-ACCESS  read-write 
     STATUS      current 
     DESCRIPTION 
        "This attribute represents the default value for the 
        subscriber (CPE) downstream filter group for the 
        CM if the parameter is not signaled in the DOCSIS Registration 
        process." 
     DEFVAL { 0 } 
     ::= { docsSubmgt3Base 5 } 

docsSubmgt3BaseSubFilterUpDef OBJECT-TYPE 
     SYNTAX      Unsigned32 (0..1024) 
     MAX-ACCESS  read-write 
     STATUS      current 
     DESCRIPTION 
        "This attribute represents the default value for the 
        subscriber (CPE) upstream filter group for the CM 
        if the parameter is not signaled in the DOCSIS Registration 
        process." 
     DEFVAL { 0 } 
     ::= { docsSubmgt3Base 6 } 

docsSubmgt3BaseCmFilterDownDef OBJECT-TYPE 
     SYNTAX      Unsigned32 (0..1024) 
     MAX-ACCESS  read-write 
     STATUS      current 
     DESCRIPTION 
        "This attribute represents the default value for the 
        CM stack downstream filter group applying to the CM 
        if the parameter is not signaled in the DOCSIS Registration 
        process." 
     DEFVAL { 0 } 
     ::= { docsSubmgt3Base 7 } 

docsSubmgt3BaseCmFilterUpDef OBJECT-TYPE 
     SYNTAX      Unsigned32 (0..1024) 
     MAX-ACCESS  read-write 
     STATUS      current 
     DESCRIPTION 
        "This attribute represents the default value for the 
        CM stack upstream filter group applying to the CM if 
        the parameter is not signaled in the DOCSIS Registration 
        process." 
     DEFVAL { 0 } 
     ::= { docsSubmgt3Base 8 } 

docsSubmgt3BasePsFilterDownDef OBJECT-TYPE 
     SYNTAX      Unsigned32 (0..1024) 
     MAX-ACCESS  read-write 
     STATUS      current 
     DESCRIPTION 
        "This attribute represents the default value for the 
        PS or eRouter downstream filter group for the CM if 
        the parameter is not signaled in the DOCSIS Registration 
        process." 
     DEFVAL { 0 } 
     ::= { docsSubmgt3Base 9 } 

docsSubmgt3BasePsFilterUpDef OBJECT-TYPE 
     SYNTAX      Unsigned32 (0..1024) 
     MAX-ACCESS  read-write 
     STATUS      current 
     DESCRIPTION 
        "This attribute represents the default value for the 
        PS or eRouter upstream filter group for the CM if the 
        parameter is not signaled in the DOCSIS Registration 
        process." 
     DEFVAL { 0 } 
     ::= { docsSubmgt3Base 10 } 

docsSubmgt3BaseMtaFilterDownDef OBJECT-TYPE 
     SYNTAX      Unsigned32 (0..1024) 
     MAX-ACCESS  read-write 
     STATUS      current 
     DESCRIPTION 
        "This attribute represents the default value for the 
        MTA downstream filter group for the CM if the parameter 
        is not signaled in the DOCSIS Registration process." 
     DEFVAL { 0 } 
     ::= { docsSubmgt3Base 11 } 

docsSubmgt3BaseMtaFilterUpDef OBJECT-TYPE 
     SYNTAX      Unsigned32 (0..1024) 
     MAX-ACCESS  read-write 
     STATUS      current 
     DESCRIPTION 
        "This attribute represents the default value for the 
        MTA upstream filter group for the CM if the parameter 
        is not signaled in the DOCSIS Registration process." 
     DEFVAL { 0 } 
     ::= { docsSubmgt3Base 12 } 

docsSubmgt3BaseStbFilterDownDef OBJECT-TYPE 
     SYNTAX      Unsigned32 (0..1024) 
     MAX-ACCESS  read-write 
     STATUS      current 
     DESCRIPTION 
        "This attribute represents the default value for the 
        STB downstream filter group for the CM if the parameter 
        is not signaled in the DOCSIS Registration process." 
     DEFVAL { 0 } 
     ::= { docsSubmgt3Base 13 } 

docsSubmgt3BaseStbFilterUpDef OBJECT-TYPE 
     SYNTAX      Unsigned32 (0..1024) 
     MAX-ACCESS  read-write 
     STATUS      current 
     DESCRIPTION 
        "This attribute represents the default value for the 
        STB upstream filter group for the CM if the parameter 
        is not signaled in the DOCSIS Registration process." 
     DEFVAL { 0 } 
     ::= { docsSubmgt3Base 14 } 

docsSubmgt3CpeCtrlTable OBJECT-TYPE 
     SYNTAX      SEQUENCE OF DocsSubmgt3CpeCtrlEntry 
     MAX-ACCESS  not-accessible 
     STATUS      current 
     DESCRIPTION 
        "This object maintains per-CM traffic policies enforced 
        by the CMTS. The CMTS acquires the CM traffic policies 
        through the CM registration process, or in the 
        absence of some or all of those parameters, from the 
        Base object. The CM information and controls are meaningful 
        and used by the CMTS, but only after the CM is 
        operational." 
     ::= { docsSubmgt3MibObjects 2} 

docsSubmgt3CpeCtrlEntry OBJECT-TYPE 
     SYNTAX      DocsSubmgt3CpeCtrlEntry 
     MAX-ACCESS  not-accessible 
     STATUS      current 
     DESCRIPTION 
         "The conceptual row of docsSubmgt3CpeCtrlTable. 
          The CMTS does not persist the instances of the CpeCtrl 
          object across reinitializations." 
     AUGMENTS { docsIf3CmtsCmRegStatusEntry } 
     ::= { docsSubmgt3CpeCtrlTable 1 } 

DocsSubmgt3CpeCtrlEntry ::= SEQUENCE { 
     docsSubmgt3CpeCtrlMaxCpeIpv4 
                  Unsigned32, 
     docsSubmgt3CpeCtrlMaxCpeIpv6Prefix 
                  Unsigned32, 
     docsSubmgt3CpeCtrlActive 
                  TruthValue, 
     docsSubmgt3CpeCtrlLearnable 
                  TruthValue, 
     docsSubmgt3CpeCtrlReset 
                  TruthValue, 
     docsSubmgt3CpeCtrlLastReset 
                  TimeStamp 
     } 

docsSubmgt3CpeCtrlMaxCpeIpv4 OBJECT-TYPE 
     SYNTAX      Unsigned32 (0..1023) 
     MAX-ACCESS  read-write 
     STATUS      current 
     DESCRIPTION 
        "This attribute represents the number of simultaneous 
        IP v4 addresses permitted for CPE connected to the CM. 
        When the MaxCpeIpv4 attribute is set to zero (0), all Ipv4 CPE 
        traffic from the CM is dropped. The CMTS configures this 
        attribute with whichever of the 'Subscriber Management CPE IPv4 
        List' or 'Subscriber Management Control-Max_CpeIPv4' signaled 
        encodings is greater, or in the absence of all of those 
        provisioning parameters, with the CpeMaxIp v4Def 
        from the Base object. This limit applies to learned 
        and DOCSIS-provisioned entries but not to entries added 
        through some administrative process at the CMTS. 
        Note that this attribute is only meaningful when the 
        Active attribute of the CM is set to 'true'." 
     REFERENCE 
         "DOCSIS 3.0 MAC and Upper Layer Protocols Interface 
         Specification CM-SP-MULPIv3.0-I04-070518, Subscriber Management 
         TLVs section in the Common Radio Frequency Interface Encodings 
         Annex." 
     ::= { docsSubmgt3CpeCtrlEntry 1 } 

docsSubmgt3CpeCtrlMaxCpeIpv6Prefix OBJECT-TYPE 
     SYNTAX      Unsigned32 (0..1023) 
     MAX-ACCESS  read-write 
     STATUS      current 
     DESCRIPTION 
        "This attribute represents the number of simultaneous 
        IPv6 prefixes permitted for CPE connected to the 
        CM.  
        When the MaxCpeIpv6Prefix is set to zero (0), all IPv6 CPE  
        traffic from the CM is dropped. The CMTS configures this  
        attribute with whichever of the 'Subscriber Management CPE IPv6 List'  
        or'Subscriber Management Control Max Cpe IPv6 Prefix'  
        signaled encodings is greater, or in the absence of all of those 
        provisioning parameters, with the CpeMaxIpv6PrefixDef 
        from the Base object. This limit applies to learned 
        and DOCSIS-provisioned entries but not to entries added 
        through some administrative process at the CMTS. 
        Note that this attribute is only meaningful when the 
        Active attribute of the CM is set to 'true'." 
     REFERENCE 
         "DOCSIS 3.0 MAC and Upper Layer Protocols Interface 
         Specification CM-SP-MULPIv3.0-I04-070518, Subscriber Management 
         TLVs section in the Common Radio Frequency Interface Encodings 
         Annex." 
     ::= { docsSubmgt3CpeCtrlEntry 2 } 

docsSubmgt3CpeCtrlActive OBJECT-TYPE 
     SYNTAX      TruthValue 
     MAX-ACCESS  read-write 
     STATUS      current 
     DESCRIPTION 
        "This attribute controls the application of subscriber 
        management to this CM. If this is set to 'true', 
        CMTS-based CPE control is active, and all the actions 
        required by the various filter policies and controls 
        apply at the CMTS. If this is set to false, no subscriber 
        management filtering is done at the CMTS (but other 
        filters may apply). If not set through DOCSIS provisioning, 
        this object defaults to the value of the Active 
        attribute of the Base object." 
     REFERENCE 
         "DOCSIS 3.0 MAC and Upper Layer Protocols Interface 
         Specification CM-SP-MULPIv3.0-I04-070518, Subscriber Management 
         Control section in the Common Radio Frequency Interface 
         Encodings Annex." 
     ::= { docsSubmgt3CpeCtrlEntry 3 } 

docsSubmgt3CpeCtrlLearnable OBJECT-TYPE 
     SYNTAX      TruthValue 
     MAX-ACCESS  read-write 
     STATUS      current 
     DESCRIPTION 
        "This attribute controls whether the CMTS may learn 
        (and pass traffic for) CPE IP addresses associated 
        with a CM. If this is set to 'true', the CMTS may learn up 
        to the CM MaxCpeIp value less any DOCSIS-provisioned 
        entries related to this CM. The nature of the learning 
        mechanism is not specified here. If not set through 
        DOCSIS provisioning, this object defaults to the 
        value of the CpeLearnableDef attribute from the Base 
        object. Note that this attribute is only meaningful 
        if docsSubMgtCpeControlActive is 'true' to enforce 
        a limit in the number of CPEs learned. CPE learning 
        is always performed for the CMTS for security reasons." 
     REFERENCE 
         "DOCSIS 3.0 MAC and Upper Layer Protocols Interface 
         Specification CM-SP-MULPIv3.0-I04-070518, Subscriber Management 
         Control section in the Common Radio Frequency Interface 
         Encodings Annex." 
     ::= { docsSubmgt3CpeCtrlEntry 4 } 

docsSubmgt3CpeCtrlReset OBJECT-TYPE 
     SYNTAX      TruthValue 
     MAX-ACCESS  read-write 
     STATUS      current 
     DESCRIPTION 
        "If set to 'true', this attribute commands the CMTS 
        to delete the instances denoted as 'learned' addresses 
        in the CpeIp object. This attribute always returns 
        false on read." 
     ::= { docsSubmgt3CpeCtrlEntry 5 } 

docsSubmgt3CpeCtrlLastReset OBJECT-TYPE 
     SYNTAX      TimeStamp 
     MAX-ACCESS  read-write 
     STATUS      current 
     DESCRIPTION 
        "This attribute represents the system Up Time of the 
        last set to 'true' of the Reset attribute of this instance. 
        Zero if never reset." 
     ::= { docsSubmgt3CpeCtrlEntry 6 } 

docsSubmgt3CpeIpTable OBJECT-TYPE 
     SYNTAX      SEQUENCE OF DocsSubmgt3CpeIpEntry 
     MAX-ACCESS  not-accessible 
     STATUS      current 
     DESCRIPTION 
        "This object defines the list of IP Addresses behind 
        the CM known by the CMTS. 

        If the Active attribute of the CpeCtrl object associated 
        with a CM is set to 'true' and the CMTS receives an 
        IP packet from a CM that contains a source IP address that 
        does not match one of the CPE IP addresses associated 
        with this CM, one of two things occurs. If the number 
        of CPE IPs is less than the MaxCpeIp of the CpeCtrl object 
        for that CM, the source IP address is added to this 
        object and the packet is forwarded; otherwise, the 
        packet is dropped." 
     ::= { docsSubmgt3MibObjects 3} 

docsSubmgt3CpeIpEntry OBJECT-TYPE 
     SYNTAX      DocsSubmgt3CpeIpEntry 
     MAX-ACCESS  not-accessible 
     STATUS      current 
     DESCRIPTION 
         "The conceptual row of docsSubmgt3CpeIpTable." 
     INDEX {  
             docsIf3CmtsCmRegStatusId,  
             docsSubmgt3CpeIpId 
           } 
     ::= { docsSubmgt3CpeIpTable 1 } 

DocsSubmgt3CpeIpEntry ::= SEQUENCE { 
     docsSubmgt3CpeIpId 
                  Unsigned32, 
     docsSubmgt3CpeIpAddrType 
                  InetAddressType, 
     docsSubmgt3CpeIpAddr 
                  InetAddress, 
     docsSubmgt3CpeIpAddrPrefixLen 
                  InetAddressPrefixLength, 
     docsSubmgt3CpeIpLearned 
                  TruthValue, 
     docsSubmgt3CpeIpType 
                  INTEGER 
     } 

docsSubmgt3CpeIpId OBJECT-TYPE 
     SYNTAX      Unsigned32 (1..1023) 
     MAX-ACCESS  not-accessible 
     STATUS      current 
     DESCRIPTION 
        "This attribute represents a unique identifier for 
        a CPE IP of the CM. An instance of this attribute exists 
        for each CPE provisioned in the 'Subscriber Management 
        CPE IPv4 Table' or 'Subscriber Management CPE 
        IPv6 Table' encodings. An entry is created either through 
        the included CPE IP addresses in the provisioning 
        object, or CPEs learned from traffic sourced from the 
        CM." 
     ::= { docsSubmgt3CpeIpEntry 1 } 

docsSubmgt3CpeIpAddrType OBJECT-TYPE 
     SYNTAX      InetAddressType 
     MAX-ACCESS  read-only 
     STATUS      current 
     DESCRIPTION 
        "The type of Internet address of the Addr attribute." 
     ::= { docsSubmgt3CpeIpEntry 2 } 

docsSubmgt3CpeIpAddr OBJECT-TYPE 
     SYNTAX      InetAddress 
     MAX-ACCESS  read-only 
     STATUS      current 
     DESCRIPTION 
        "This attribute represents the IP address either set 
        from provisioning or learned via address gleaning 
        or other forwarding means." 
     ::= { docsSubmgt3CpeIpEntry 3 } 

docsSubmgt3CpeIpAddrPrefixLen OBJECT-TYPE 
     SYNTAX      InetAddressPrefixLength 
     MAX-ACCESS  read-only 
     STATUS      current 
     DESCRIPTION 
        "This attribute represents the prefix length associated with 
        the IP subnet prefix either set from provisioning or learned 
        via address gleaning or other forwarding means. For IPv4 CPE 
        addresses this attribute generally reports the value 32  
        (32 bits) to indicate a unicast IPv4 address. For IPv6, this 
        attribute represents either an IPv6 unicast address 
        (128 bits, equal to /128 prefix length) or a subnet prefix  
        length (for example 56 bits, equal to /56 prefix length)." 
     ::= { docsSubmgt3CpeIpEntry 4 } 

docsSubmgt3CpeIpLearned OBJECT-TYPE 
     SYNTAX      TruthValue 
     MAX-ACCESS  read-only 
     STATUS      current 
     DESCRIPTION 
        "This attribute is set to 'true' when the IP address 
        was learned from IP packets sent upstream rather than 
        via the CM provisioning process." 
     ::= { docsSubmgt3CpeIpEntry 5 } 

docsSubmgt3CpeIpType OBJECT-TYPE 
     SYNTAX      INTEGER { 
                           cpe(1), 
                           ps(2), 
                           mta(3), 
                           stb(4), 
                           tea(5), 
                           erouter(6) 
                         } 
     MAX-ACCESS  read-only 
     STATUS      current 
     DESCRIPTION 
        "This attribute represents the type of CPE based on 
        the following classification below: 
                     'cpe' Regular CPE clients. 
                     'ps'  CableHome Portal Server (PS) 
                     'mta' PacketCable Multimedia Terminal Adapter (MTA) 
                     'stb' Digital Set-top Box (STB). 
                     'tea' T1 Emulation adapter (TEA) 
                     'erouter' Embedded Router (eRouter)" 
     ::= { docsSubmgt3CpeIpEntry 6 } 

docsSubmgt3GrpTable OBJECT-TYPE 
     SYNTAX      SEQUENCE OF DocsSubmgt3GrpEntry 
     MAX-ACCESS  not-accessible 
     STATUS      current 
     DESCRIPTION 
        "This object defines the set of downstream and upstream 
        filter groups that the CMTS applies to traffic associated 
        with that CM." 
     REFERENCE 
         "DOCSIS 3.0 MAC and Upper Layer Protocols Interface 
         Specification CM-SP-MULPIv3.0-I01-060804, Subscriber 
         Management TLVs section in the Common Radio Frequency 
         Interface Encodings Annex." 
     ::= { docsSubmgt3MibObjects 4} 

docsSubmgt3GrpEntry OBJECT-TYPE 
     SYNTAX      DocsSubmgt3GrpEntry 
     MAX-ACCESS  not-accessible 
     STATUS      current 
     DESCRIPTION 
         "The conceptual row of docsSubmgt3GrpTable. 
          The CMTS does not persist the instances of the Grp 
          object across reinitializations." 
     AUGMENTS { docsIf3CmtsCmRegStatusEntry } 
     ::= { docsSubmgt3GrpTable 1 } 

DocsSubmgt3GrpEntry ::= SEQUENCE { 
     docsSubMgt3GrpUdcGroupIds 
                  SnmpTagList, 
     docsSubMgt3GrpUdcSentInRegRsp 
                  TruthValue, 
     docsSubmgt3GrpSubFilterDs 
                  Unsigned32, 
     docsSubmgt3GrpSubFilterUs 
                  Unsigned32, 
     docsSubmgt3GrpCmFilterDs 
                  Unsigned32, 
     docsSubmgt3GrpCmFilterUs 
                  Unsigned32, 
     docsSubmgt3GrpPsFilterDs 
                  Unsigned32, 
     docsSubmgt3GrpPsFilterUs 
                  Unsigned32, 
     docsSubmgt3GrpMtaFilterDs 
                  Unsigned32, 
     docsSubmgt3GrpMtaFilterUs 
                  Unsigned32, 
     docsSubmgt3GrpStbFilterDs 
                  Unsigned32, 
     docsSubmgt3GrpStbFilterUs 
                  Unsigned32 
     } 

docsSubMgt3GrpUdcGroupIds OBJECT-TYPE 
     SYNTAX      SnmpTagList 
     MAX-ACCESS  read-write 
     STATUS      current 
     DESCRIPTION 
        "This attribute represents the filter group(s) associated 
        with the CM signaled 'Upstream Drop Classifier Group ID'  
       encodings during the registration process. UDC Group IDs are 
       integer values and this attribute reports them as decimal  
       numbers that are space-separated. The zero-length string indicates  
       that the CM didn't signal UDC Group IDs.  
       This attribute provides two functions:  
       - Communicate the CM the configured UDC Group ID(s), irrespective  
       of the CM being provisioned to filter upstream traffic based  
       on IP Filters or UDCs.  
       - Optionally, and with regards to the CMTS, if the value of the 
       attribute UdcSentInReqRsp is 'true', indicates that the filtering  
       rules associated with the Subscriber Management Group ID(s) will 
       be sent during registration to the CM. It is vendor specific  
       whether the CMTS updates individual CM UDCs after registration 
       when rules are changed in the Grp object." 
     DEFVAL { ''H } 
     ::= { docsSubmgt3GrpEntry 1 } 

docsSubMgt3GrpUdcSentInRegRsp OBJECT-TYPE 
     SYNTAX      TruthValue 
     MAX-ACCESS  read-write 
     STATUS      current 
     DESCRIPTION 
        "This attribute represents the CMTS upstream filtering  
        status for this CM. The value 'true' indicates that the  
        CMTS has sent UDCs to the CM during registration process.  

        In order for a CMTS to send UDCs to a CM, the CMTS MAC Domain 
        needed to be enabled via the MAC Domain attribute  
        SendUdcRulesEnabled and the CM had indicated the UDC capability  
        support during the registration process. The value 'false'  
        indicates that the CMTS was not enabled to sent UDCs to the  
        CMs in the MAC Domain, or the CM does not advertised UDC  
        support in its capabilities encodings, or both. Since the  
        CMTS capability to sent UDCs to CMs during the registration 
        process is optional, the CMTS is not required to implement  
        the value 'true'." 
     DEFVAL { false } 
     ::= { docsSubmgt3GrpEntry 2 } 

docsSubmgt3GrpSubFilterDs OBJECT-TYPE 
     SYNTAX      Unsigned32 (0..1024) 
     MAX-ACCESS  read-write 
     STATUS      current 
     DESCRIPTION 
        "This attribute represents the filter group applied 
        to traffic destined for subscriber's CPE attached to the 
        referenced CM (attached to CM CPE interfaces). This 
        value corresponds to the 'Subscriber Downstream 
        Group' value of the 'Subscriber Management Filter Groups' 
        encoding signaled during the CM registration 
        or in its absence, to the SubFilterDownDef attribute 
        of the Base object. The value zero or a filter group 
        ID not configured in the CMTS means no filtering is applied 
        to traffic destined to hosts attached to this CM." 
     ::= { docsSubmgt3GrpEntry 3 } 

docsSubmgt3GrpSubFilterUs OBJECT-TYPE 
     SYNTAX      Unsigned32 (0..1024) 
     MAX-ACCESS  read-write 
     STATUS      current 
     DESCRIPTION 
        "This attribute represents the filter group applied 
        to traffic originating from subscriber's CPE attached 
        to the referenced CM (attached to CM CPE interfaces). 
        This value corresponds to the 'Subscriber Upstream 
        Group' value of the 'Subscriber Management Filter 
        Groups' encoding signaled during the CM registration 
        or in its absence, to the SubFilterUpDef attribute 
        of the Base object. The value zero or a filter group 
        ID not configured in the CMTS means no filtering 
        is applied to traffic originating from hosts attached 
        to this CM." 
     ::= { docsSubmgt3GrpEntry 4 } 

docsSubmgt3GrpCmFilterDs OBJECT-TYPE 
     SYNTAX      Unsigned32 (0..1024) 
     MAX-ACCESS  read-write 
     STATUS      current 
     DESCRIPTION 
        "This attribute represents the filter group applied 
        to traffic destined for the CM itself. This value corresponds 
        to the 'CM Downstream Group' value of the 
        'Subscriber Management Filter Groups' encoding signaled 
        during the CM registration or in its absence, 
        to the CmFilterDownDef attribute of the Base object. 
        The value zero or a filter group ID not configured in 
        the CMTS means no filtering is applied to traffic destined 
        to the CM." 
     ::= { docsSubmgt3GrpEntry 5 } 

docsSubmgt3GrpCmFilterUs OBJECT-TYPE 
     SYNTAX      Unsigned32 (0..1024) 
     MAX-ACCESS  read-write 
     STATUS      current 
     DESCRIPTION 
        "This attribute represents the filter group applied 
        to traffic originating from the CM itself. This value 
        corresponds to the 'Subscriber Upstream Group' 
        value of the 'Subscriber Management Filter Groups' 
        encoding signaled during the CM registration or in its 
        absence, to the SubFilterUpDef attribute of the Base 
        object. The value zero or a filter group ID not configured 
        in the CMTS means no filtering is applied to traffic 
        originating from this CM." 
     ::= { docsSubmgt3GrpEntry 6 } 

docsSubmgt3GrpPsFilterDs OBJECT-TYPE 
     SYNTAX      Unsigned32 (0..1024) 
     MAX-ACCESS  read-write 
     STATUS      current 
     DESCRIPTION 
        "This attribute represents the filter group applied 
        to traffic destined to the Embedded CableHome Portal 
        Services Element or the Embedded Router on the referenced 
        CM. This value corresponds to the 'PS Downstream 
        Group' value of the 'Subscriber Management Filter 
        Groups' encoding signaled during the CM registration 
        or in its absence, to the SubFilterDownDef attribute 
        of the Base object. The value zero or a filter 
        group ID not configured in the CMTS means no filtering 
        is applied to traffic destined to the Embedded CableHome 
        Portal Services Element or Embedded Router on 
        this CM." 
     ::= { docsSubmgt3GrpEntry 7 } 

docsSubmgt3GrpPsFilterUs OBJECT-TYPE 
     SYNTAX      Unsigned32 (0..1024) 
     MAX-ACCESS  read-write 
     STATUS      current 
     DESCRIPTION 
        "This attribute represents the filter group applied 
        to traffic originating from the Embedded CableHome 
        Portal Services Element or Embedded Router on the 
        referenced CM. This value corresponds to the 'PS Upstream 
        Group' value of the 'Subscriber Management Filter 
        Groups' encoding signaled during the CM registration 
        or in its absence, to the SubFilterUpDef attribute 
        of the Base object. The value zero or a filter group 
        ID not configured in the CMTS means no filtering is 
        applied to traffic originating from the Embedded CableHome 
        Portal Services Element or Embedded Router 
        on this CM." 
     ::= { docsSubmgt3GrpEntry 8 } 

docsSubmgt3GrpMtaFilterDs OBJECT-TYPE 
     SYNTAX      Unsigned32 (0..1024) 
     MAX-ACCESS  read-write 
     STATUS      current 
     DESCRIPTION 
        "This attribute represents the filter group applied 
        to traffic destined to the Embedded Multimedia Terminal 
        Adapter on the referenced CM. This value corresponds 
        to the 'MTA Downstream Group' value of the 'Subscriber 
        Management Filter Groups' encoding signaled 
        during the CM registration or in its absence, to 
        the SubFilterDownDef attribute of the Base object. 
        The value zero or a filter group ID not configured in the 
        CMTS means no filtering is applied to traffic destined 
        to the Embedded Multimedia Terminal Adapter on 
        this CM." 
     ::= { docsSubmgt3GrpEntry 9 } 

docsSubmgt3GrpMtaFilterUs OBJECT-TYPE 
     SYNTAX      Unsigned32 (0..1024) 
     MAX-ACCESS  read-write 
     STATUS      current 
     DESCRIPTION 
        "This attribute represents the filter group applied 
        to traffic originating from the Embedded Multimedia 
        Terminal Adapter on the referenced CM. This value 
        corresponds to the 'MTA Upstream Group' value of the 
        'Subscriber Management Filter Groups' encoding signaled 
        during the CM registration or in its absence, 
        to the SubFilterUpDef attribute of the Base object. 
        The value zero or a filter group ID not configured in 
        the CMTS means no filtering is applied to traffic originating 
        from the Embedded Multimedia Terminal Adapter 
        on this CM." 
     ::= { docsSubmgt3GrpEntry 10 } 

docsSubmgt3GrpStbFilterDs OBJECT-TYPE 
     SYNTAX      Unsigned32 (0..1024) 
     MAX-ACCESS  read-write 
     STATUS      current 
     DESCRIPTION 
        "This attribute represents the filter group applied 
        to traffic destined for the Embedded Set-Top Box on 
        the referenced CM. This value corresponds to the 'STB 
        Downstream Group' value of the 'Subscriber Management 
        Filter Groups' encoding signaled during the CM 
        registration or in its absence, to the SubFilterDownDef 
        attribute of the Base object. The value zero or 
        a filter group ID not configured in the CMTS means no filtering 
        is applied to traffic destined to the Embedded 
        Set-Top Box on this CM." 
     ::= { docsSubmgt3GrpEntry 11 } 

docsSubmgt3GrpStbFilterUs OBJECT-TYPE 
     SYNTAX      Unsigned32 (0..1024) 
     MAX-ACCESS  read-write 
     STATUS      current 
     DESCRIPTION 
        "This attribute represents the filter group applied 
        to traffic originating from the Embedded Set-Top 
        Box on the referenced CM. This value corresponds to the 
        'STB Upstream Group' value of the 'Subscriber Management 
        Filter Groups' encoding signaled during the 
        CM registration or in its absence, to the SubFilterUpDef 
        attribute of the Base object. The value zero or 
        a filter group ID not configured in the CMTS means no filtering 
        is applied to traffic originating from the 
        Embedded Set-Top Box on this CM." 
     ::= { docsSubmgt3GrpEntry 12 } 

docsSubmgt3FilterGrpTable OBJECT-TYPE 
     SYNTAX      SEQUENCE OF DocsSubmgt3FilterGrpEntry 
     MAX-ACCESS  not-accessible 
     STATUS      current 
     DESCRIPTION 
        "This object describes a set of filter or classifier 
        criteria. Classifiers are assigned by group to the 
        individual CMs. That assignment is made via the 'Subscriber 
        Management TLVs' encodings sent upstream from 
        the CM to the CMTS during registration or in their 
        absence, default values configured in the CMTS. 
        A Filter Group ID (GrpId) is a set of rules that correspond 
        to the expansion of a UDC Group ID into UDC individual  
        classification rules.  The Filter Group Ids are generated  
        whenever the CMTS is configured to send UDCs during the CM  
        registration process. Implementation of L2 classification  
        criteria is optional for the CMTS; LLC/MAC upstream and  
        downstream filter criteria can be ignored during the packet 
        matching process." 
     ::= { docsSubmgt3MibObjects 5} 

docsSubmgt3FilterGrpEntry OBJECT-TYPE 
     SYNTAX      DocsSubmgt3FilterGrpEntry 
     MAX-ACCESS  not-accessible 
     STATUS      current 
     DESCRIPTION 
         "The conceptual row of docsSubmgt3FilterGrpTable. 
          The CMTS persists all instances of the FilterGrp object 
          across reinitializations." 
     INDEX {  
             docsSubmgt3FilterGrpGrpId,  
             docsSubmgt3FilterGrpRuleId 
           } 
     ::= { docsSubmgt3FilterGrpTable 1 } 

DocsSubmgt3FilterGrpEntry ::= SEQUENCE { 
     docsSubmgt3FilterGrpGrpId 
                  Unsigned32, 
     docsSubmgt3FilterGrpRuleId 
                  Unsigned32, 
     docsSubmgt3FilterGrpAction 
                  INTEGER, 
     docsSubmgt3FilterGrpPriority 
                  Unsigned32, 
     docsSubmgt3FilterGrpIpTosLow 
                  OCTET STRING, 
     docsSubmgt3FilterGrpIpTosHigh 
                  OCTET STRING, 
     docsSubmgt3FilterGrpIpTosMask 
                  OCTET STRING, 
     docsSubmgt3FilterGrpIpProtocol 
                  Unsigned32, 
     docsSubmgt3FilterGrpInetAddrType 
                  InetAddressType, 
     docsSubmgt3FilterGrpInetSrcAddr 
                  InetAddress, 
     docsSubmgt3FilterGrpInetSrcMask 
                  InetAddress, 
     docsSubmgt3FilterGrpInetDestAddr 
                  InetAddress, 
     docsSubmgt3FilterGrpInetDestMask 
                  InetAddress, 
     docsSubmgt3FilterGrpSrcPortStart 
                  InetPortNumber, 
     docsSubmgt3FilterGrpSrcPortEnd 
                  InetPortNumber, 
     docsSubmgt3FilterGrpDestPortStart 
                  InetPortNumber, 
     docsSubmgt3FilterGrpDestPortEnd 
                  InetPortNumber, 
     docsSubmgt3FilterGrpDestMacAddr 
                  MacAddress, 
     docsSubmgt3FilterGrpDestMacMask 
                  MacAddress, 
     docsSubmgt3FilterGrpSrcMacAddr 
                  MacAddress, 
     docsSubmgt3FilterGrpEnetProtocolType 
                  INTEGER, 
     docsSubmgt3FilterGrpEnetProtocol 
                  Unsigned32, 
     docsSubmgt3FilterGrpUserPriLow 
                  Unsigned32, 
     docsSubmgt3FilterGrpUserPriHigh 
                  Unsigned32, 
     docsSubmgt3FilterGrpVlanId 
                  Unsigned32, 
     docsSubmgt3FilterGrpClassPkts 
                  Counter64, 
     docsSubmgt3FilterGrpFlowLabel 
                  Unsigned32, 
     docsSubmgt3FilterGrpCmInterfaceMask 
                  DocsL2vpnIfList, 
     docsSubmgt3FilterGrpRowStatus 
                  RowStatus 
     } 

docsSubmgt3FilterGrpGrpId OBJECT-TYPE 
     SYNTAX      Unsigned32 (1..65535) 
     MAX-ACCESS  not-accessible 
     STATUS      current 
     DESCRIPTION 
        "This key is an identifier for a set of classifiers known 
        as a filter group. Each CM may be associated with 
        several filter groups for its upstream and downstream 
        traffic, one group per target end point on the CM as 
        defined in the Grp object. Typically, many CMs share 
        a common set of filter groups." 
     ::= { docsSubmgt3FilterGrpEntry 1 } 

docsSubmgt3FilterGrpRuleId OBJECT-TYPE 
     SYNTAX      Unsigned32 (1..65535) 
     MAX-ACCESS  not-accessible 
     STATUS      current 
     DESCRIPTION 
        "This key represents an ordered classifier identifier 
        within the group.  Filters are applied in order if 
        the Priority attribute is not supported." 
     ::= { docsSubmgt3FilterGrpEntry 2 } 

docsSubmgt3FilterGrpAction OBJECT-TYPE 
     SYNTAX      INTEGER { 
                         permit(1), 
                         deny(2) 
                         } 
     MAX-ACCESS  read-create 
     STATUS      current 
     DESCRIPTION 
        "This attribute represents the action to take upon 
        this filter matching.  'permit' means to stop the classification 
        matching and accept the packet for further 
        processing.  'deny' means to drop the packet." 
     DEFVAL { permit } 
     ::= { docsSubmgt3FilterGrpEntry 3 } 

docsSubmgt3FilterGrpPriority OBJECT-TYPE 
     SYNTAX      Unsigned32 (0..65535) 
     MAX-ACCESS  read-create 
     STATUS      current 
     DESCRIPTION 
        "This attribute defines the order in which classifiers 
        are compared against packets. The higher the value, 
        the higher the priority." 
     DEFVAL { 0 } 
     ::= { docsSubmgt3FilterGrpEntry 4 } 

docsSubmgt3FilterGrpIpTosLow OBJECT-TYPE 
     SYNTAX      OCTET STRING (SIZE (1)) 
     MAX-ACCESS  read-create 
     STATUS      current 
     DESCRIPTION 
        "This attribute represents the low value of a range 
        of ToS (Type of Service) octet values. This object is 
        defined as an 8-bit octet as per the DOCSIS Specification 
        for packet classification. 
        The IP ToS octet, as originally defined in RFC 791, has 
        been superseded by the 6-bit Differentiated Services 
        Field (DSField, RFC 3260) and the 2-bit Explicit 
        Congestion Notification Field (ECN field, RFC 3168)." 
     REFERENCE 
         "DOCSIS 3.0 MAC and Upper Layer Protocols Interface 
         Specification CM-SP-MULPIv3.0-I01-060804. 
         RFC 791. 
         RFC 3260. 
         RFC 3168." 
     DEFVAL { '00'H } 
     ::= { docsSubmgt3FilterGrpEntry 5 } 

docsSubmgt3FilterGrpIpTosHigh OBJECT-TYPE 
     SYNTAX      OCTET STRING (SIZE (1)) 
     MAX-ACCESS  read-create 
     STATUS      current 
     DESCRIPTION 
        "This attribute represents the high value of a range 
        of ToS octet values. This object is defined as an 8-bit 
        octet as per the DOCSIS Specification for packet classification. 
        The IP ToS octet, as originally defined in RFC 791, has 
        been superseded by the 6-bit Differentiated Services 
        Field (DSField, RFC 3260) and the 2-bit Explicit 
        Congestion Notification Field (ECN field, RFC 3168)." 
     REFERENCE 
         "DOCSIS 3.0 MAC and Upper Layer Protocols Interface 
         Specification CM-SP-MULPIv3.0-I01-060804. 
         RFC 791. 
         RFC 3260. 
         RFC 3168." 
     DEFVAL { '00'H } 
     ::= { docsSubmgt3FilterGrpEntry 6 } 

docsSubmgt3FilterGrpIpTosMask OBJECT-TYPE 
     SYNTAX      OCTET STRING (SIZE (1)) 
     MAX-ACCESS  read-create 
     STATUS      current 
     DESCRIPTION 
        "This attribute represents the mask value that is bitwise 
        ANDed with ToS octet in an IP packet, and the resulting value 
        is used for range checking of IpTosLow and IpTosHigh." 
     DEFVAL { '00'H } 
     ::= { docsSubmgt3FilterGrpEntry 7 } 

docsSubmgt3FilterGrpIpProtocol OBJECT-TYPE 
     SYNTAX      Unsigned32 (0..257) 
     MAX-ACCESS  read-create 
     STATUS      current 
     DESCRIPTION 
        "This attribute represents the value of the IP Protocol 
        field required for IP packets to match this rule. 
        The value 256 matches traffic with any IP Protocol value. 
        The value 257 by convention matches both TCP and 
        UDP." 
     DEFVAL { 256 } 
     ::= { docsSubmgt3FilterGrpEntry 8 } 

docsSubmgt3FilterGrpInetAddrType OBJECT-TYPE 
     SYNTAX      InetAddressType 
     MAX-ACCESS  read-create 
     STATUS      current 
     DESCRIPTION 
        "The type of the Internet address for InetSrcAddr, 
        InetSrcMask, InetDestAddr, and InetDestMask." 
     DEFVAL { unknown } 
     ::= { docsSubmgt3FilterGrpEntry 9 } 

docsSubmgt3FilterGrpInetSrcAddr OBJECT-TYPE 
     SYNTAX      InetAddress 
     MAX-ACCESS  read-create 
     STATUS      current 
     DESCRIPTION 
        "This attribute specifies the value of the IP Source Address 
        required for packets to match this rule. An IP packet 
        matches the rule when the packet's IP Source Address 
        bitwise ANDed with the InetSrcMask value equals 
        the InetSrcAddr value. The address type of this object 
        is specified by the InetAddressType attribute." 
     DEFVAL { ''H } 
     ::= { docsSubmgt3FilterGrpEntry 10 } 

docsSubmgt3FilterGrpInetSrcMask OBJECT-TYPE 
     SYNTAX      InetAddress 
     MAX-ACCESS  read-create 
     STATUS      current 
     DESCRIPTION 
        "This attribute represents which bits of a packet's 
        IP Source Address are compared to match this rule. An 
        IP packet matches the rule when the packet's IP Source 
        Address bitwise ANDed with the InetSrcMask value equals 
        the InetSrcAddr value. The address type of this 
        object is specified by InetAddrType." 
     DEFVAL { ''H } 
     ::= { docsSubmgt3FilterGrpEntry 11 } 

docsSubmgt3FilterGrpInetDestAddr OBJECT-TYPE 
     SYNTAX      InetAddress 
     MAX-ACCESS  read-create 
     STATUS      current 
     DESCRIPTION 
        "This attribute specifies the value of the IP Destination 
        Address required for packets to match this rule. 
        An IP packet matches the rule when the packet's IP Destination 
        Address bitwise ANDed with the InetSrcMask 
        value equals the InetDestAddr value. The address type 
        of this object is specified by the InetAddrType attribute." 
     DEFVAL { ''H } 
     ::= { docsSubmgt3FilterGrpEntry 12 } 

docsSubmgt3FilterGrpInetDestMask OBJECT-TYPE 
     SYNTAX      InetAddress 
     MAX-ACCESS  read-create 
     STATUS      current 
     DESCRIPTION 
        "This attribute represents which bits of a packet's 
        IP Destination Address are compared to match this rule. 
        An IP packet matches the rule when the packet's IP Destination 
        Address bitwise ANDed with the InetDestMask value 
        equals the InetDestAddr value. The address type 
        of this object is specified by InetAddrType." 
     DEFVAL { ''H } 
     ::= { docsSubmgt3FilterGrpEntry 13 } 

docsSubmgt3FilterGrpSrcPortStart OBJECT-TYPE 
     SYNTAX      InetPortNumber 
     MAX-ACCESS  read-create 
     STATUS      current 
     DESCRIPTION 
        "This attribute represents the low-end inclusive 
        range of TCP/UDP source port numbers to which a packet 
        is compared. This attribute is irrelevant for non-TCP/UDP 
        IP packets." 
     DEFVAL { 0 } 
     ::= { docsSubmgt3FilterGrpEntry 14 } 

docsSubmgt3FilterGrpSrcPortEnd OBJECT-TYPE 
     SYNTAX      InetPortNumber 
     MAX-ACCESS  read-create 
     STATUS      current 
     DESCRIPTION 
        "This attribute represents the high-end inclusive 
        range of TCP/UDP source port numbers to which a packet 
        is compared. This attribute is irrelevant for non-TCP/UDP 
        IP packets." 
     DEFVAL { 65535 } 
     ::= { docsSubmgt3FilterGrpEntry 15 } 

docsSubmgt3FilterGrpDestPortStart OBJECT-TYPE 
     SYNTAX      InetPortNumber 
     MAX-ACCESS  read-create 
     STATUS      current 
     DESCRIPTION 
        "This attribute represents the low-end inclusive 
        range of TCP/UDP destination port numbers to which a 
        packet is compared. This attribute is irrelevant for 
        non-TCP/UDP IP packets." 
     DEFVAL { 0 } 
     ::= { docsSubmgt3FilterGrpEntry 16 } 

docsSubmgt3FilterGrpDestPortEnd OBJECT-TYPE 
     SYNTAX      InetPortNumber 
     MAX-ACCESS  read-create 
     STATUS      current 
     DESCRIPTION 
        "This attribute represents the high-end inclusive 
        range of TCP/UDP destination port numbers to which a packet 
        is compared. This attribute is irrelevant for non-TCP/UDP 
        IP packets." 
     DEFVAL { 65535 } 
     ::= { docsSubmgt3FilterGrpEntry 17 } 

docsSubmgt3FilterGrpDestMacAddr OBJECT-TYPE 
     SYNTAX      MacAddress 
     MAX-ACCESS  read-create 
     STATUS      current 
     DESCRIPTION 
        "This attribute represents the criteria to match against 
        an Ethernet packet MAC address bitwise ANDed 
        with DestMacMask." 
     DEFVAL { '000000000000'H } 
     ::= { docsSubmgt3FilterGrpEntry 18 } 

docsSubmgt3FilterGrpDestMacMask OBJECT-TYPE 
     SYNTAX      MacAddress 
     MAX-ACCESS  read-create 
     STATUS      current 
     DESCRIPTION 
        "An Ethernet packet matches an entry when its 
        destination MAC address bitwise ANDed with 
        the DestMacMask attribute equals the value of 
        the DestMacAddr attribute." 
     DEFVAL { '000000000000'H } 
     ::= { docsSubmgt3FilterGrpEntry 19 } 

docsSubmgt3FilterGrpSrcMacAddr OBJECT-TYPE 
     SYNTAX      MacAddress 
     MAX-ACCESS  read-create 
     STATUS      current 
     DESCRIPTION 
        "This attribute represents the value to match against 
        an Ethernet packet source MAC address." 
     DEFVAL { 'FFFFFFFFFFFF'H } 
     ::= { docsSubmgt3FilterGrpEntry 20 } 

docsSubmgt3FilterGrpEnetProtocolType OBJECT-TYPE 
     SYNTAX      INTEGER { 
                         none(0), 
                         ethertype(1), 
                         dsap(2), 
                         mac(3), 
                         all(4) 
                         } 
     MAX-ACCESS  read-create 
     STATUS      current 
     DESCRIPTION 
        "This attribute indicates the format of the layer 3 
        protocol ID in the Ethernet packet. A value of 'none' 
        means that the rule does not use the layer 3 protocol 
        type as a matching criteria. A value of 'ethertype' 
        means that the rule applies only to frames that contain 
        an EtherType value. EtherType values are contained 
        in packets using the DEC-Intel-Xerox (DIX) encapsulation 
        or the RFC 1042 Sub-Network Access Protocol 
        (SNAP) encapsulation formats. A value of 'dsap' means 
        that the rule applies only to frames using the IEEE802.3 
        encapsulation format with a Destination Service 
        Access Point (DSAP) other than 0xAA (which is reserved 
        for SNAP). A value of 'mac' means that the rule 
        applies only to MAC management messages for MAC management 
        messages. A value of 'all' means that the rule 
        matches all Ethernet packets. If the Ethernet frame 
        contains an 802.1P/Q Tag header (i.e., EtherType 
        0x8100), this attribute applies to the embedded EtherType 
        field within the 802.1p/Q header. 
        The value 'mac' is only used for passing UDCs to CMs during  
        Registration. The CMTS ignores filter rules that include  
        the value of this attribute set to 'mac' for CMTS enforced  
        upstream and downstream subscriber management filter group 
        rules." 
     REFERENCE 
        "RFC1042 Sub-Network Access Protocol (SNAP) encapsulation 
        formats." 
     DEFVAL { none } 
     ::= { docsSubmgt3FilterGrpEntry 21 } 

docsSubmgt3FilterGrpEnetProtocol OBJECT-TYPE 
     SYNTAX      Unsigned32 (0..65535) 
     MAX-ACCESS  read-create 
     STATUS      current 
     DESCRIPTION 
        "This attribute represents the Ethernet protocol 
        type to be matched against the packets. For EnetProtocolType 
        set to 'none', this attribute is ignored when considering 
        whether a packet matches the current rule. 
        If the attribute EnetProtocolType is 'ethertype', 
        this attribute gives the 16-bit value of the EtherType 
        that the packet must match in order to match the rule. 
        If the attribute EnetProtocolType is 'dsap', the lower 
        8 bits of this attribute's value must match the DSAP 
        octet of the packet in order to match the rule. If the Ethernet 
        frame contains an 802.1p/Q Tag header (i.e., 
        EtherType 0x8100), this attribute applies to the embedded 
        EtherType field within the 802.1p/Q header." 
     DEFVAL { 0 } 
     ::= { docsSubmgt3FilterGrpEntry 22 } 

docsSubmgt3FilterGrpUserPriLow OBJECT-TYPE 
     SYNTAX      Unsigned32 (0..7) 
     MAX-ACCESS  read-create 
     STATUS      current 
     DESCRIPTION 
        "This attribute applies only to Ethernet frames using 
        the 802.1p/Q tag header (indicated with EtherType 
        0x8100). Such frames include a 16-bit Tag that contains 
        a 3-bit Priority field and a 12-bit VLAN number. 
        Tagged Ethernet packets must have a 3-bit Priority 
        field within the range of PriLow to PriHigh in order to 
        match this rule." 
     DEFVAL { 0 } 
     ::= { docsSubmgt3FilterGrpEntry 23 } 

docsSubmgt3FilterGrpUserPriHigh OBJECT-TYPE 
     SYNTAX      Unsigned32 (0..7) 
     MAX-ACCESS  read-create 
     STATUS      current 
     DESCRIPTION 
        "This attribute applies only to Ethernet frames using 
        the 802.1p/Q tag header (indicated with EtherType 
        0x8100). Such frames include a 16-bit Tag that contains 
        a 3-bit Priority field and a 12-bit VLAN number. 
        Tagged Ethernet packets must have a 3-bit Priority 
        field within the range of PriLow to PriHigh in order to 
        match this rule." 
     DEFVAL { 7 } 
     ::= { docsSubmgt3FilterGrpEntry 24 } 

docsSubmgt3FilterGrpVlanId OBJECT-TYPE 
     SYNTAX      Unsigned32 (0 | 1..4094) 
     MAX-ACCESS  read-create 
     STATUS      current 
     DESCRIPTION 
        "This attribute applies only to Ethernet frames using 
        the 802.1p/Q tag header. Tagged packets must have 
        a VLAN Identifier that matches the value in order to 
        match the rule." 
     ::= { docsSubmgt3FilterGrpEntry 25 } 

docsSubmgt3FilterGrpClassPkts OBJECT-TYPE 
     SYNTAX      Counter64 
     MAX-ACCESS  read-only 
     STATUS      current 
     DESCRIPTION 
        "This attribute counts the number of packets 
        that have been classified (matched) using this rule 
        entry. This includes all packets delivered to a Service 
        Flow maximum rate policing function, whether 
        or not that function drops the packets. Discontinuities 
        in the value of this counter can occur at re-initialization 
        of the managed system, and at other times 
        as indicated by the value of ifCounterDiscontinuityTime 
        for the CM MAC Domain interface." 
     ::= { docsSubmgt3FilterGrpEntry 26 } 

docsSubmgt3FilterGrpFlowLabel OBJECT-TYPE 
     SYNTAX      Unsigned32 (0..1048575) 
     MAX-ACCESS  read-create 
     STATUS      current 
     DESCRIPTION 
        "This attribute represents the Flow Label field in 
        the IPv6 header to be matched by the classifier. 
        The value zero indicates that the Flow Label is not specified 
        as part of the classifier and is not matched against packets." 
     REFERENCE 
        "DOCSIS 3.0 MAC and Upper Layer Protocols Interface 
        Specification CM-SP-MULPIv3.0-I03-070223, IPv6 Flow  
        Label section in the Common Radio Frequency Interface 
        Encodings Annex." 
     ::= { docsSubmgt3FilterGrpEntry 27 } 

docsSubmgt3FilterGrpCmInterfaceMask OBJECT-TYPE 
     SYNTAX      DocsL2vpnIfList 
     MAX-ACCESS  read-create 
     STATUS      current 
     DESCRIPTION 
        "This attribute represents a bit-mask of the CM in-bound 
        interfaces to which this classifier applies. 
        This attribute only applies to upstream Drop Classifiers  
        being sent to CMs during the registration process." 
     REFERENCE 
        "DOCSIS 3.0 MAC and Upper Layer Protocols Interface 
        Specification CM-SP-MULPIv3.0-I03-070223, CM  
        Interface Mask (CMIM) Encoding section in the Common  
        Radio Frequency Interface Encodings Annex." 
     ::= { docsSubmgt3FilterGrpEntry 28 } 

docsSubmgt3FilterGrpRowStatus OBJECT-TYPE 
     SYNTAX      RowStatus 
     MAX-ACCESS  read-create 
     STATUS      current 
     DESCRIPTION 
        "The conceptual row status of this object." 
     ::= { docsSubmgt3FilterGrpEntry 29 } 

-- Conformance Definitions 
docsSubmgt3MibConformance OBJECT IDENTIFIER ::= { docsSubmgt3Mib 2 } 
docsSubmgt3MibCompliances OBJECT IDENTIFIER 
                                 ::= { docsSubmgt3MibConformance 1 } 
docsSubmgt3MibGroups      OBJECT IDENTIFIER 
                                 ::= { docsSubmgt3MibConformance 2 } 

docsSubmgt3Compliance MODULE-COMPLIANCE 
STATUS      current 
DESCRIPTION 
        "The compliance statement for devices that implement the DOCSIS 
         Subscriber Management 3 MIB." 

    MODULE -- this MODULE 
MANDATORY-GROUPS { 
     docsSubmgt3Group 
     } 
::= { docsSubmgt3MibCompliances 1 } 
docsSubmgt3Group OBJECT-GROUP 
    OBJECTS { 
     docsSubmgt3BaseCpeMaxIpv4Def, 
     docsSubmgt3BaseCpeMaxIpv6PrefixDef, 
     docsSubmgt3BaseCpeActiveDef, 
     docsSubmgt3BaseCpeLearnableDef, 
     docsSubmgt3BaseSubFilterDownDef, 
     docsSubmgt3BaseSubFilterUpDef, 
     docsSubmgt3BaseCmFilterDownDef, 
     docsSubmgt3BaseCmFilterUpDef, 
     docsSubmgt3BasePsFilterDownDef, 
     docsSubmgt3BasePsFilterUpDef, 
     docsSubmgt3BaseMtaFilterDownDef, 
     docsSubmgt3BaseMtaFilterUpDef, 
     docsSubmgt3BaseStbFilterDownDef, 
     docsSubmgt3BaseStbFilterUpDef, 
     docsSubmgt3CpeCtrlMaxCpeIpv4, 
     docsSubmgt3CpeCtrlMaxCpeIpv6Prefix, 
     docsSubmgt3CpeCtrlActive, 
     docsSubmgt3CpeCtrlLearnable, 
     docsSubmgt3CpeCtrlReset, 
     docsSubmgt3CpeCtrlLastReset, 
     docsSubmgt3CpeIpAddrType, 
     docsSubmgt3CpeIpAddr, 
     docsSubmgt3CpeIpAddrPrefixLen, 
     docsSubmgt3CpeIpLearned, 
     docsSubmgt3CpeIpType, 
     docsSubMgt3GrpUdcGroupIds, 
     docsSubMgt3GrpUdcSentInRegRsp, 
     docsSubmgt3GrpSubFilterDs, 
     docsSubmgt3GrpSubFilterUs, 
     docsSubmgt3GrpCmFilterDs, 
     docsSubmgt3GrpCmFilterUs, 
     docsSubmgt3GrpPsFilterDs, 
     docsSubmgt3GrpPsFilterUs, 
     docsSubmgt3GrpMtaFilterDs, 
     docsSubmgt3GrpMtaFilterUs, 
     docsSubmgt3GrpStbFilterDs, 
     docsSubmgt3GrpStbFilterUs, 
     docsSubmgt3FilterGrpAction, 
     docsSubmgt3FilterGrpPriority, 
     docsSubmgt3FilterGrpIpTosLow, 
     docsSubmgt3FilterGrpIpTosHigh, 
     docsSubmgt3FilterGrpIpTosMask, 
     docsSubmgt3FilterGrpIpProtocol, 
     docsSubmgt3FilterGrpInetAddrType, 
     docsSubmgt3FilterGrpInetSrcAddr, 
     docsSubmgt3FilterGrpInetSrcMask, 
     docsSubmgt3FilterGrpInetDestAddr, 
     docsSubmgt3FilterGrpInetDestMask, 
     docsSubmgt3FilterGrpSrcPortStart, 
     docsSubmgt3FilterGrpSrcPortEnd, 
     docsSubmgt3FilterGrpDestPortStart, 
     docsSubmgt3FilterGrpDestPortEnd, 
     docsSubmgt3FilterGrpDestMacAddr, 
     docsSubmgt3FilterGrpDestMacMask, 
     docsSubmgt3FilterGrpSrcMacAddr, 
     docsSubmgt3FilterGrpEnetProtocolType, 
     docsSubmgt3FilterGrpEnetProtocol, 
     docsSubmgt3FilterGrpUserPriLow, 
     docsSubmgt3FilterGrpUserPriHigh, 
     docsSubmgt3FilterGrpVlanId, 
     docsSubmgt3FilterGrpClassPkts, 
     docsSubmgt3FilterGrpFlowLabel, 
     docsSubmgt3FilterGrpCmInterfaceMask, 
     docsSubmgt3FilterGrpRowStatus 
     } 
    STATUS      current 
    DESCRIPTION 
         "Group of objects implemented in the CMTS." 
    ::= { docsSubmgt3MibGroups 1 } 
END
