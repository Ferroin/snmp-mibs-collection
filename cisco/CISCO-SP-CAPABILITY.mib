CISCO-SP-CAPABILITY DEFINITIONS ::= BEGIN

IMPORTS
        MODULE-IDENTITY
                FROM SNMPv2-SMI
        AGENT-CAPABILITIES
                FROM SNMPv2-CONF
        ciscoAgentCapability
                FROM CISCO-SMI;

cSpCapability MODULE-IDENTITY
                LAST-UPDATED    "200106060000Z"
                ORGANIZATION    "Cisco Systems, Inc."
                CONTACT-INFO
                        "       Cisco Systems
                                Customer Service

                        Postal: 170 West Tasman Drive
                                San Jose, CA  95134
                                USA

                           Tel: +1 800 553-NETS

                        E-mail: cs-ss7@cisco.com"
                DESCRIPTION
                        "Agent capabilities for the CISCO-SP-MIB."
                REVISION        "200106060000Z"
                DESCRIPTION
                        "Initial version of this MIB module."
        ::= { ciscoAgentCapability 189 }

cSpCapabilityV12R021MB1 AGENT-CAPABILITIES

PRODUCT-RELEASE "Cisco IOS 12.2(1)MB1"
  STATUS          current
  DESCRIPTION     "IOS 12.2(1)MB1 Cisco CISCO-SP-MIB.my User Agent
                   MIB capabilities."

SUPPORTS        CISCO-SP-MIB
  INCLUDES      { 
                  ciscoSpSwitchGroup,            
                  ciscoSpLinksetGroup,           
                  ciscoSpLinkGroup,              
                  ciscoSpRouteGroup,             
                  ciscoSpAccessListGroup,        
                  ciscoSpAccountingGroup,        
                  ciscoSpNotificationsEnableGroup
                }  

  VARIATION cSpLinkXmitQueueDepthHigh
    ACCESS    read-only
    DESCRIPTION "write not implemented"

  VARIATION cSpLinkQ752T1E2
    ACCESS    not-implemented
    DESCRIPTION "Not implemented."

  VARIATION cSpLinkQ752T1E3     
    ACCESS    not-implemented
    DESCRIPTION "Not implemented."

  VARIATION cSpLinkQ752T1E4     
    ACCESS    not-implemented
    DESCRIPTION "Not implemented."

  VARIATION cSpLinkQ752T1E5         
    ACCESS    not-implemented
    DESCRIPTION "Not implemented."

  VARIATION cSpLinkQ752T1E6
    ACCESS    not-implemented
    DESCRIPTION "Not implemented."

  VARIATION cSpLinkQ752T1E7         
    ACCESS    not-implemented
    DESCRIPTION "Not implemented."

  VARIATION cSpLinkQ752T1E8         
    ACCESS    not-implemented
    DESCRIPTION "Not implemented."

  VARIATION cSpLinkQ752T1E9         
    ACCESS    not-implemented
    DESCRIPTION "Not implemented."

  VARIATION cSpLinkQ752T1E10         
    ACCESS    not-implemented
    DESCRIPTION "Not implemented."

  VARIATION cSpLinkQ752T1E11        
    ACCESS    not-implemented
    DESCRIPTION "Not implemented."

  VARIATION cSpLinkQ752T2E5        
    ACCESS    not-implemented
    DESCRIPTION "Not implemented."

  VARIATION cSpLinkQ752T2E6        
    ACCESS    not-implemented
    DESCRIPTION "Not implemented."

  VARIATION cSpLinkQ752T2E7        
    ACCESS    not-implemented
    DESCRIPTION "Not implemented."

  VARIATION cSpLinkQ752T2E9        
    ACCESS    not-implemented
    DESCRIPTION "Not implemented."

  VARIATION cSpLinkQ752T2E10        
    ACCESS    not-implemented
    DESCRIPTION "Not implemented."

  VARIATION cSpLinkQ752T2E15        
    ACCESS    not-implemented
    DESCRIPTION "Not implemented."

  VARIATION cSpLinkQ752T2E16
    ACCESS    not-implemented
    DESCRIPTION "Not implemented."

  VARIATION cSpLinkQ752T2E18
    ACCESS    not-implemented
    DESCRIPTION "Not implemented."

  VARIATION cSpLinkQ752T3E6   
    ACCESS    not-implemented
    DESCRIPTION "Not implemented."

  VARIATION cSpLinkQ752T3E7    
    ACCESS    not-implemented
    DESCRIPTION "Not implemented."

  VARIATION cSpLinkQ752T3E10L1 
    ACCESS    not-implemented
    DESCRIPTION "Not implemented."

  VARIATION cSpLinkQ752T3E10L2 
    ACCESS    not-implemented
    DESCRIPTION "Not implemented."

  VARIATION cSpLinkQ752T3E10L3 
    ACCESS    not-implemented
    DESCRIPTION "Not implemented."

  VARIATION cSpLinkQ752T3E11L1 
    ACCESS    not-implemented
    DESCRIPTION "Not implemented."

  VARIATION cSpLinkQ752T3E11L2 
    ACCESS    not-implemented
    DESCRIPTION "Not implemented."

  VARIATION cSpLinkQ752T3E11L3 
    ACCESS    not-implemented
    DESCRIPTION "Not implemented."
::= { cSpCapability 1 }

END
