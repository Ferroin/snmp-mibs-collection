CISCO-HC-RMON-CAPABILITY DEFINITIONS ::= BEGIN

IMPORTS
        MODULE-IDENTITY
                FROM SNMPv2-SMI
        AGENT-CAPABILITIES
                FROM SNMPv2-CONF
        ciscoAgentCapability
                FROM CISCO-SMI;

ciscoHcRmonCapability MODULE-IDENTITY
        LAST-UPDATED    "200309300000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com
                        cs-rmon@cisco.com"
        DESCRIPTION
                "The capabilities description of 
                 HC-RMON-MIB."

        REVISION        "200309300000Z"
        DESCRIPTION
                "Initial version of this MIB module."
        ::= { ciscoAgentCapability 358 }

ciscoHcRmonCapCatOSV08R0101  AGENT-CAPABILITIES
    PRODUCT-RELEASE     "Cisco CatOS 8.1(1)." 
    STATUS              current
    DESCRIPTION         "HC-RMON-MIB capabilities."

    SUPPORTS            HC-RMON-MIB
    INCLUDES            { etherStatsHighCapacityGroup,
                          hcRMONInformationGroup,
                          mediaIndependentGroup,
                          etherHistoryHighCapacityGroup,
                          usrHistoryHighCapacityGroup
                        }
    VARIATION       mediaIndependentDroppedFrames
    SYNTAX          Counter32 
    DESCRIPTION     "Hardcoded to 0"
    ::= { ciscoHcRmonCapability 1 }

END
