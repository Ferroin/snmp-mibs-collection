CISCO-GTP-CAPABILITY DEFINITIONS ::= BEGIN

IMPORTS
        MODULE-IDENTITY
                FROM SNMPv2-SMI
        AGENT-CAPABILITIES
                FROM SNMPv2-CONF
        ciscoAgentCapability
                FROM CISCO-SMI;

ciscoGtpCapability MODULE-IDENTITY
        LAST-UPDATED    "200304020900Z"
        ORGANIZATION    "Cisco Systems, Inc."
        CONTACT-INFO
                "       Cisco Systems
                        Customer Service

                        Postal: 170 West Tasman Drive
                                San Jose, CA  95134
                                USA
                                Tel: +1 800 553-NETS

                        E-mail: cs-gprs@cisco.com"
        DESCRIPTION
                "Agent capabilities for CISCO-GTP-MIB"
        REVISION        "200304020900Z"
        DESCRIPTION
                "Updated for GPRS R4.0 release."
        REVISION        "200203211600Z"
        DESCRIPTION
                "Initial version of this MIB module."
        ::= { ciscoAgentCapability 263 }

cGtpCapabilityV12R02Rev08YD AGENT-CAPABILITIES
        PRODUCT-RELEASE  "Cisco IOS 12.2(8)YD"
        STATUS           current
        DESCRIPTION      "CISCO GTP MIB capabilities"
        SUPPORTS         CISCO-GTP-MIB
        INCLUDES         {
                          cGtpConfigurationsGroupRev1,
                          cGtpStatusGroupRev1,
                          cGtpStatisticsGroupRev1,
                          cGtpNotifGroup
                          }

        VARIATION        cGtpGSNService
        SYNTAX           BITS { sgsn(1) }
        DESCRIPTION      "SGSN GPRS service is not supported"

        VARIATION        cGtpVersion
        ACCESS           read-only
        DESCRIPTION      "Write Access not yet supported"

        VARIATION        cGtpT3TunnelTimer
        ACCESS           not-implemented
        DESCRIPTION      "Both read and write access are not supported"
        ::= { ciscoGtpCapability 1 }

cGtpCapabilityV12R02Rev08YY AGENT-CAPABILITIES

        PRODUCT-RELEASE  "Cisco IOS 12.2(8)YY"
        STATUS           current
        DESCRIPTION      "CISCO GTP MIB capabilities for GGSN R3.1."
        SUPPORTS         CISCO-GTP-MIB
        INCLUDES         {
                          cGtpConfigurationsGroupRev2,
                          cGtpStatusGroupRev1,
                          cGtpStatisticsGroupRev1,
                          cGtpNotifGroup
                          }

        VARIATION        cGtpGSNService
        SYNTAX           BITS { sgsn(1) }
        DESCRIPTION      "SGSN GPRS service is not supported"

        VARIATION        cGtpVersion
        ACCESS           read-only
        DESCRIPTION      "Write Access not yet supported"

        VARIATION        cGtpGSNAddressType
        SYNTAX           INTEGER {ipv4(1)} -- subset of InetAddressType
        DESCRIPTION
           "Only IPv4 Addresses are supported. IPv6 and DNS are
           not supported."
        ::= { ciscoGtpCapability 2 }

cGtpCapabilityV12R02Rev08YW AGENT-CAPABILITIES

        PRODUCT-RELEASE  "Cisco IOS 12.2(8)YW"
        STATUS           current
        DESCRIPTION      "CISCO GTP MIB capabilities for GGSN R4.0."
        SUPPORTS         CISCO-GTP-MIB
        INCLUDES         { cGtpConfigurationsGroupRev2,
                           cGtpStatusGroupRev3,
                           cGtpStatisticsGroupRev1,
                           cGtpNotifGroup
                         }
        VARIATION        cGtpGSNService
        SYNTAX           BITS { sgsn(1) }
        DESCRIPTION      "SGSN GPRS service is not supported"

        VARIATION        cGtpVersion
        ACCESS           read-only
        DESCRIPTION      "Write Access not yet supported"

        VARIATION        cGtpPathAddressType
        SYNTAX           INTEGER {ipv4(1)} -- subset of InetAddressType
        DESCRIPTION
           "Only IPv4 Addresses are supported. IPv6 and DNS are
           not supported."
        ::= { ciscoGtpCapability 3 }

END
