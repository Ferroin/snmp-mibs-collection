CISCO-IETF-SCTP-CAPABILITY DEFINITIONS ::= BEGIN

IMPORTS
        MODULE-IDENTITY
                FROM SNMPv2-SMI

        AGENT-CAPABILITIES
                FROM SNMPv2-CONF

        ciscoAgentCapability
                FROM CISCO-SMI; 

ciscoSctpCapability MODULE-IDENTITY
        LAST-UPDATED    "200110240000Z"
        ORGANIZATION    "Cisco Systems, Inc."
        CONTACT-INFO
                "       Cisco Systems
                        Customer Service

                Postal: 170 West Tasman Drive
                        San Jose, CA  95134
                        USA

                   Tel: +1 800 553-NETS

                E-mail: cs-sctp@cisco.com"
        DESCRIPTION
                "Agent capabilities for the CISCO-IETF-SCTP-MIB."
        REVISION        "200110240000Z"
        DESCRIPTION
                "Initial version of this MIB module."
        ::= { ciscoAgentCapability 215 }

ciscoSctpCapabilityV12R024MB1 AGENT-CAPABILITIES

PRODUCT-RELEASE "Cisco IOS 12.2(4)MB1"
  STATUS          current
  DESCRIPTION     "IOS 12.2(4)MB1 Cisco CISCO-IETF-SCTP-MIB.my User Agent
                   MIB capabilities."

SUPPORTS        CISCO-IETF-SCTP-MIB
  INCLUDES      { 
                  cSctpGeneralVariablesGroup,
                  cSctpAssocTablesVariablesGroup,
                  cSctpStateStatGroup,
                  cSctpOtherStatGroup,
                  cSctpAssocStatGroup
                }  
::= { ciscoSctpCapability 1 }

END
