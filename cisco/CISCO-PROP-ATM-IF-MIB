CISCO-PROP-ATM-IF-MIB DEFINITIONS ::= BEGIN
IMPORTS
        MODULE-IDENTITY, 
        OBJECT-TYPE,
        Integer32,
        Counter32,
        Counter64,
        Unsigned32              FROM SNMPv2-SMI
        MODULE-COMPLIANCE,
        OBJECT-GROUP            FROM SNMPv2-CONF
        ifIndex                 FROM IF-MIB
        ciscoMgmt               FROM CISCO-SMI;

ciscoPropAtmIfMIB MODULE-IDENTITY
        LAST-UPDATED        "200212040000Z"
        ORGANIZATION        "Cisco Systems, Inc."
        CONTACT-INFO
                "       Cisco Systems
                        Customer Service

                Postal: 170 W Tasman Drive
                        San Jose, CA  95134
                        USA

                   Tel: +1 800 553-NETS

                E-mail: cs-voice-gateway@cisco.com"
         DESCRIPTION
            "This MIB is designed for Propietary ATM (propAtm) 
             interfaces.              
             The propAtm interfaces are identified in the ifTable 
             entries with ifType 197 (as defined in IANAifType-MIB).
             This interface is a switch virtual interface which does 
             not have any physical connector(jack).
            "
         REVISION        "200212040000Z"
         DESCRIPTION
            "Initial version of this MIB module."
         ::= {ciscoMgmt 319 }

ciscoPropAtmIfMIBNotifs   OBJECT IDENTIFIER
                                 ::= { ciscoPropAtmIfMIB 0 }
ciscoPropAtmIfMIBObjects  OBJECT IDENTIFIER 
                                 ::= { ciscoPropAtmIfMIB 1}
cpAtmIfConfig             OBJECT IDENTIFIER 
                                 ::= { ciscoPropAtmIfMIBObjects 1}
cpAtmIfVirtualPortStats           OBJECT IDENTIFIER 
                                 ::= { ciscoPropAtmIfMIBObjects 2}

-- *********************************************************************
-- cpAtmIfConfigTable
-- *********************************************************************

cpAtmIfConfigTable OBJECT-TYPE
        SYNTAX  SEQUENCE OF CpAtmIfConfigEntry
        MAX-ACCESS not-accessible
        STATUS     current
        DESCRIPTION
          "This table is used to configure propAtm interfaces.
           Each entry in this table has a corresponding ifTable
           entry with ifType propAtm(197).  The ifIndex value
           of that associated ifTable entry is used to index
           this this table.
           The entry of this table is added after its associated  
           ifEntry is added in the ifTable of IF-MIB.
           It is impossible to add/delete entry to/from this table.
          "
        ::= { cpAtmIfConfig 1 }

cpAtmIfConfigEntry OBJECT-TYPE
        SYNTAX     CpAtmIfConfigEntry
        MAX-ACCESS not-accessible
        STATUS     current
        DESCRIPTION
            "An entry in the cpAtmIfConfigTable table for 
             each propAtm port interface.
           ."
        INDEX   { ifIndex }
        ::= { cpAtmIfConfigTable 1 }

CpAtmIfConfigEntry ::=
        SEQUENCE {
              cpAtmIfMaxBandwidth    Unsigned32
              } 

cpAtmIfMaxBandwidth OBJECT-TYPE
        SYNTAX     Unsigned32(0..4294967295)
        UNITS      "cells-per-second"
        MAX-ACCESS read-write
        STATUS current 
        DESCRIPTION 
             "The propATM interface's maximum cell rate.
             "
        DEFVAL{ 7000000 }
        ::= { cpAtmIfConfigEntry 1 } 

-- *********************************************************************
-- cpAtmIfStatsEgressTable
-- *********************************************************************

cpAtmIfStatsEgressTable OBJECT-TYPE
        SYNTAX  SEQUENCE OF CpAtmIfStatsEgressEntry
        MAX-ACCESS not-accessible
        STATUS     current
        DESCRIPTION
          "This table reflects real-time statistics associated with
           each of propAtm interfaces on the egress side.

           Ingress terminology is used for the cells that are generated
           by the voice gateway on the TDM side and are going toward
           the ATM switch.

           Egress terminology means the cells that are coming from the
           ATM switch into the TDM side. This table contains
           statistics from this egress point of view.
          "
        ::= { cpAtmIfVirtualPortStats 1 }

cpAtmIfStatsEgressEntry OBJECT-TYPE
        SYNTAX     CpAtmIfStatsEgressEntry
        MAX-ACCESS not-accessible
        STATUS     current
        DESCRIPTION
            "An entry in the cpAtmIfStatsEgressTable table for 
             each propAtm port interface.

             CLP-0 means Cell Loss Priority = 0, 
             CLP-1 means Cell Loss Priority = 1.
            "
        INDEX   { ifIndex }
        ::= { cpAtmIfStatsEgressTable 1 }

CpAtmIfStatsEgressEntry ::=
        SEQUENCE {
                  cpAtmIfEgrRcvClp0Cells      Counter32,
                  cpAtmIfEgrRcvClp1Cells      Counter32,
                  cpAtmIfEgrClp0DiscCells     Counter32,
                  cpAtmIfEgrClp1DiscCells     Counter32,
                  cpAtmIfEgrRcvOAMCells       Counter32,
                  cpAtmIfEgrRcvEFCICells      Counter32,
                  cpAtmIfHCEgrRcvClp0Cells    Counter64,
                  cpAtmIfHCEgrRcvClp1Cells    Counter64,
                  cpAtmIfHCEgrClp0DiscCells   Counter64,
                  cpAtmIfHCEgrClp1DiscCells   Counter64,
                  cpAtmIfHCEgrRcvOAMCells     Counter64,
                  cpAtmIfHCEgrRcvEFCICells    Counter64
                 } 

cpAtmIfEgrRcvClp0Cells  OBJECT-TYPE
        SYNTAX     Counter32
        MAX-ACCESS read-only
        STATUS current 
        DESCRIPTION 
             "The number of CLP-0 cells received from switch
              at the traffic management and policing device.
             "
        ::= { cpAtmIfStatsEgressEntry 1 }  

cpAtmIfEgrRcvClp1Cells  OBJECT-TYPE
        SYNTAX     Counter32
        MAX-ACCESS read-only
        STATUS current 
        DESCRIPTION 
             "The number of CLP-1 cells received from switch
              at the traffic management and policing device.
             "
        ::= { cpAtmIfStatsEgressEntry 2 }

cpAtmIfEgrClp0DiscCells  OBJECT-TYPE
        SYNTAX     Counter32
        MAX-ACCESS read-only
        STATUS current 
        DESCRIPTION 
             "The number of CLP-0 cells discarded due to policing.
             "
        ::= { cpAtmIfStatsEgressEntry 3 }

cpAtmIfEgrClp1DiscCells  OBJECT-TYPE
        SYNTAX     Counter32
        MAX-ACCESS read-only
        STATUS current 
        DESCRIPTION 
             "The number of CLP-1 cells discarded due to policing.
             "
        ::= { cpAtmIfStatsEgressEntry 4 }

cpAtmIfEgrRcvOAMCells  OBJECT-TYPE
        SYNTAX     Counter32
        MAX-ACCESS read-only
        STATUS current 
        DESCRIPTION 
             "The number of OAM cells received from the switch
              at the traffic management and policing device.
             "
        ::= { cpAtmIfStatsEgressEntry 5 }

cpAtmIfEgrRcvEFCICells  OBJECT-TYPE
        SYNTAX     Counter32
        MAX-ACCESS read-only
        STATUS current 
        DESCRIPTION 
             "The number of EFCI cells received from the switch
              at traffic management and policing device.
             "
        ::= { cpAtmIfStatsEgressEntry 6 }

--
-- High Capacity Counter objects.  These objects are all
-- 64 bit versions of the "basic" counters.  These
-- objects all have the same basic semantics as their 32-bit
-- counterparts, however, their syntax has been extended
-- to 64 bits.
--

cpAtmIfHCEgrRcvClp0Cells  OBJECT-TYPE
        SYNTAX     Counter64
        MAX-ACCESS read-only
        STATUS current 
        DESCRIPTION 
             "The number of CLP-0 cells received from switch
              at the traffic management and policing device.
              This object is a 64-bit version of 
              cpAtmIfEgrRcvClp0Cells.
             "
        ::= { cpAtmIfStatsEgressEntry 7 }  

cpAtmIfHCEgrRcvClp1Cells  OBJECT-TYPE
        SYNTAX     Counter64
        MAX-ACCESS read-only
        STATUS current 
        DESCRIPTION 
             "The number of CLP-1 cells received from switch
              at the traffic management and policing device.
              This object is a 64-bit version of 
              cpAtmIfEgrRcvClp1Cells.
             "
        ::= { cpAtmIfStatsEgressEntry 8 }

cpAtmIfHCEgrClp0DiscCells  OBJECT-TYPE
        SYNTAX     Counter64
        MAX-ACCESS read-only
        STATUS current 
        DESCRIPTION 
             "The number of CLP-0 cells discarded due to policing.
              This object is a 64-bit version of 
              cpAtmIfEgrClp0DiscCells.
             "
        ::= { cpAtmIfStatsEgressEntry 9 }

cpAtmIfHCEgrClp1DiscCells  OBJECT-TYPE
        SYNTAX     Counter64
        MAX-ACCESS read-only
        STATUS current 
        DESCRIPTION 
             "The number of CLP-1 cells discarded due to policing.
              This object is a 64-bit version of 
              cpAtmIfEgrClp1DiscCells.
             "
        ::= { cpAtmIfStatsEgressEntry 10 }

cpAtmIfHCEgrRcvOAMCells  OBJECT-TYPE
        SYNTAX     Counter64
        MAX-ACCESS read-only
        STATUS current 
        DESCRIPTION 
             "The number of OAM cells received from the switch
              at the traffic management and policing device.
              This object is a 64-bit version of 
              cpAtmIfEgrRcvOAMCells.
             "
        ::= { cpAtmIfStatsEgressEntry 11 }

cpAtmIfHCEgrRcvEFCICells  OBJECT-TYPE
        SYNTAX     Counter64
        MAX-ACCESS read-only
        STATUS current 
        DESCRIPTION 
             "The number of EFCI cells received from the switch
              at traffic management and policing device.
              This object is a 64-bit version of 
              cpAtmIfEgrRcvEFCICells.
             "
        ::= { cpAtmIfStatsEgressEntry 12 }

-- *********************************************************************
-- cpAtmIfEgressIntervalTable
-- *********************************************************************

cpAtmIfEgressIntervalTable OBJECT-TYPE
        SYNTAX  SEQUENCE OF CpAtmIfEgressIntervalEntry
        MAX-ACCESS not-accessible
        STATUS     current
        DESCRIPTION
          "This table reflects interval(each 15 minute) statistics
           associated witheach of the propAtm interfaces on egress side.
          "
        ::= { cpAtmIfVirtualPortStats 2 }

cpAtmIfEgressIntervalEntry OBJECT-TYPE
        SYNTAX     CpAtmIfEgressIntervalEntry
        MAX-ACCESS not-accessible
        STATUS     current
        DESCRIPTION
            "An entry in the cpAtmIfEgressIntervalTable table 
             for each propAtm port interface.

             CLP-0 means Cell Loss Priority = 0, 
             CLP-1 means Cell Loss Priority = 1.
            "
        INDEX   { ifIndex, cpAtmIfEgressIntervalNumber}
        ::= { cpAtmIfEgressIntervalTable 1 }

CpAtmIfEgressIntervalEntry ::=
        SEQUENCE {
                  cpAtmIfEgressIntervalNumber    Integer32,
                  cpAtmIfIntEgrRcvClp0Cells      Counter32,
                  cpAtmIfIntEgrRcvClp1Cells      Counter32,
                  cpAtmIfIntEgrClp0DiscCells     Counter32,
                  cpAtmIfIntEgrClp1DiscCells     Counter32,
                  cpAtmIfIntEgrRcvOAMCells       Counter32,
                  cpAtmIfIntEgrRcvEFCICells      Counter32,
                  cpAtmIfHCIntEgrRcvClp0Cells    Counter64,
                  cpAtmIfHCIntEgrRcvClp1Cells    Counter64,
                  cpAtmIfHCIntEgrClp0DiscCells   Counter64,
                  cpAtmIfHCIntEgrClp1DiscCells   Counter64,
                  cpAtmIfHCIntEgrRcvOAMCells     Counter64,
                  cpAtmIfHCIntEgrRcvEFCICells    Counter64
                 } 

cpAtmIfEgressIntervalNumber  OBJECT-TYPE
        SYNTAX     Integer32(1..96)
        MAX-ACCESS not-accessible
        STATUS current 
        DESCRIPTION 
             "Index of the table which represents the interval number.
              An interval number between 1 and 96, where 1 is the
              most recently completed 15 minute interval and 96 is 
              the 15 minutes interval completed 23 hours an 45
              minutes prior to interval 1.
             "
        ::= { cpAtmIfEgressIntervalEntry 1 }

cpAtmIfIntEgrRcvClp0Cells  OBJECT-TYPE
        SYNTAX     Counter32
        MAX-ACCESS read-only
        STATUS current 
        DESCRIPTION 
             "The number of CLP-0 cells received from switch
              at the traffic management and policing device
              during a 15 minute interval.
             "
        ::= { cpAtmIfEgressIntervalEntry 2 }  

cpAtmIfIntEgrRcvClp1Cells  OBJECT-TYPE
        SYNTAX     Counter32
        MAX-ACCESS read-only
        STATUS current 
        DESCRIPTION 
             "The number of CLP-1 cells received from switch
              at the traffic management and policing device 
              during a 15 minute interval.
             "
        ::= { cpAtmIfEgressIntervalEntry 3 }

cpAtmIfIntEgrClp0DiscCells  OBJECT-TYPE
        SYNTAX     Counter32
        MAX-ACCESS read-only
        STATUS current 
        DESCRIPTION 
             "The number of CLP-0 cells discarded due to policing
              during a 15 minute interval.
             "
        ::= { cpAtmIfEgressIntervalEntry 4 }

cpAtmIfIntEgrClp1DiscCells  OBJECT-TYPE
        SYNTAX     Counter32
        MAX-ACCESS read-only
        STATUS current 
        DESCRIPTION 
             "The number of CLP-1 cells discarded due to policing
              during a 15 minute interval.
             "
        ::= { cpAtmIfEgressIntervalEntry 5 }

cpAtmIfIntEgrRcvOAMCells  OBJECT-TYPE
        SYNTAX     Counter32
        MAX-ACCESS read-only
        STATUS current 
        DESCRIPTION 
             "The number of OAM cells received from the switch
              at the traffic management and policing device 
              during a 15 minute interval.
             "
        ::= { cpAtmIfEgressIntervalEntry 6 }

cpAtmIfIntEgrRcvEFCICells  OBJECT-TYPE
        SYNTAX     Counter32
        MAX-ACCESS read-only
        STATUS current 
        DESCRIPTION 
             "The number of EFCI cells received from the switch
              at traffic management and policing device during a 15
              minute interval.
             "
        ::= { cpAtmIfEgressIntervalEntry 7 }

--
-- High Capacity Counter objects.  These objects are all
-- 64 bit versions of the "basic" counters.  These
-- objects all have the same basic semantics as their 32-bit
-- counterparts, however, their syntax has been extended
-- to 64 bits.
--

cpAtmIfHCIntEgrRcvClp0Cells  OBJECT-TYPE
        SYNTAX     Counter64
        MAX-ACCESS read-only
        STATUS current 
        DESCRIPTION 
             "The number of CLP-0 cells received from switch
              at the traffic management and policing device
              during a 15 minute interval.
              This object is a 64-bit version of 
              cpAtmIfIntEgrRcvClp0Cells.
             "
        ::= { cpAtmIfEgressIntervalEntry 8 }  

cpAtmIfHCIntEgrRcvClp1Cells  OBJECT-TYPE
        SYNTAX     Counter64
        MAX-ACCESS read-only
        STATUS current 
        DESCRIPTION 
             "The number of CLP-1 cells received from switch
              at the traffic management and policing device 
              during a 15 minute interval.
              This object is a 64-bit version of 
              cpAtmIfIntEgrRcvClp1Cells.
             "
        ::= { cpAtmIfEgressIntervalEntry 9 }

cpAtmIfHCIntEgrClp0DiscCells  OBJECT-TYPE
        SYNTAX     Counter64
        MAX-ACCESS read-only
        STATUS current 
        DESCRIPTION 
             "The number of CLP-0 cells discarded due to policing
              during a 15 minute interval.
              This object is a 64-bit version of 
              cpAtmIfIntEgrClp0DiscCells.
             "
        ::= { cpAtmIfEgressIntervalEntry 10 }

cpAtmIfHCIntEgrClp1DiscCells  OBJECT-TYPE
        SYNTAX     Counter64
        MAX-ACCESS read-only
        STATUS current 
        DESCRIPTION 
             "The number of CLP-1 cells discarded due to policing
              during a 15 minute interval.
              This object is a 64-bit version of 
              cpAtmIfIntEgrClp1DiscCells.
             "
        ::= { cpAtmIfEgressIntervalEntry 11 }

cpAtmIfHCIntEgrRcvOAMCells  OBJECT-TYPE
        SYNTAX     Counter64
        MAX-ACCESS read-only
        STATUS current 
        DESCRIPTION 
             "The number of OAM cells received from the switch
              at the traffic management and policing device 
              during a 15 minute interval.
              This object is a 64-bit version of 
              cpAtmIfIntEgrRcvOAMCells.
             "
        ::= { cpAtmIfEgressIntervalEntry 12 }

cpAtmIfHCIntEgrRcvEFCICells  OBJECT-TYPE
        SYNTAX     Counter64
        MAX-ACCESS read-only
        STATUS current 
        DESCRIPTION 
             "The number of EFCI cells received from the switch
              at traffic management and policing device during a 15
              minute interval.
              This object is a 64-bit version of 
              cpAtmIfIntEgrRcvEFCICells.
             "
        ::= { cpAtmIfEgressIntervalEntry 13 }

-- *********************************************************************
-- cpAtmIfStatsIngressTable
-- *********************************************************************
cpAtmIfStatsIngressTable OBJECT-TYPE
        SYNTAX  SEQUENCE OF CpAtmIfStatsIngressEntry
        MAX-ACCESS not-accessible
        STATUS     current
        DESCRIPTION
          "This table reflects real time statistics associated with
           each of the the propAtm interfaces on the ingress side.

           Ingress terminology is used for the cells that are generated
           by the voice gateway on the TDM side and are going toward
           the ATM switch.

           Egress terminology means the cells that are coming from the
           ATM switch into TDM side. This table contains statistics
           from this ingress point of view.
          "
        ::= { cpAtmIfVirtualPortStats 3 }

cpAtmIfStatsIngressEntry OBJECT-TYPE
        SYNTAX     CpAtmIfStatsIngressEntry
        MAX-ACCESS not-accessible
        STATUS     current
        DESCRIPTION
            "An entry in the cpAtmIfStatsIngressTable table for 
             each propAtm port interface.

             CLP-0 means Cell Loss Priority = 0, 
             CLP-1 means Cell Loss Priority = 1.
            "
        INDEX   { ifIndex }
        ::= { cpAtmIfStatsIngressTable 1 }

CpAtmIfStatsIngressEntry ::=
        SEQUENCE {
                  cpAtmIfIngXmtClp0Cells    Counter32,
                  cpAtmIfIngXmtClp1Cells    Counter32,
                  cpAtmIfIngXmtEFCICells    Counter32,
                  cpAtmIfIngXmtOAMCells     Counter32,
                  cpAtmIfHCIngXmtClp0Cells  Counter64,
                  cpAtmIfHCIngXmtClp1Cells  Counter64,
                  cpAtmIfHCIngXmtEFCICells  Counter64,
                  cpAtmIfHCIngXmtOAMCells   Counter64
                 } 

cpAtmIfIngXmtClp0Cells OBJECT-TYPE
        SYNTAX     Counter32
        MAX-ACCESS read-only
        STATUS     current
        DESCRIPTION
           "The number of CLP-0 cells transmitted to the switch
            after traffic management and policing in
            ingress direction."
        ::= {cpAtmIfStatsIngressEntry 1 }

cpAtmIfIngXmtClp1Cells OBJECT-TYPE
        SYNTAX     Counter32
        MAX-ACCESS read-only
        STATUS     current
        DESCRIPTION
           "The number of CLP-1 cells transmitted to the switch
            after traffic management and policing in
            ingress direction."
        ::= {cpAtmIfStatsIngressEntry 2 }

cpAtmIfIngXmtEFCICells OBJECT-TYPE
        SYNTAX     Counter32
        MAX-ACCESS read-only
        STATUS     current
        DESCRIPTION
           "The number of EFCI cells transmitted to the switch 
            after traffic management and policing in
            ingress direction."
        ::= {cpAtmIfStatsIngressEntry 3 }

cpAtmIfIngXmtOAMCells OBJECT-TYPE
        SYNTAX     Counter32
        MAX-ACCESS read-only
        STATUS     current
        DESCRIPTION
           "The number of OAM loopback cells transmitted to switch
            after traffic management and policing in
            ingress direction."
        ::= {cpAtmIfStatsIngressEntry 4 }

--
-- High Capacity Counter objects.  These objects are all
-- 64 bit versions of the "basic" counters.  These
-- objects all have the same basic semantics as their 32-bit
-- counterparts, however, their syntax has been extended
-- to 64 bits.
--

cpAtmIfHCIngXmtClp0Cells OBJECT-TYPE
        SYNTAX     Counter64
        MAX-ACCESS read-only
        STATUS     current
        DESCRIPTION
           "The number of CLP-0 cells transmitted to the switch
            after traffic management and policing in
            ingress direction.
            This object is a 64-bit version of 
            cpAtmIfIngXmtClp0Cells.
           "
        ::= {cpAtmIfStatsIngressEntry 5 }

cpAtmIfHCIngXmtClp1Cells OBJECT-TYPE
        SYNTAX     Counter64
        MAX-ACCESS read-only
        STATUS     current
        DESCRIPTION
           "The number of CLP-1 cells transmitted to the switch
            after traffic management and policing in
            ingress direction.
            This object is a 64-bit version of 
            cpAtmIfIngXmtClp1Cells.
           "
        ::= {cpAtmIfStatsIngressEntry 6 }

cpAtmIfHCIngXmtEFCICells OBJECT-TYPE
        SYNTAX     Counter64
        MAX-ACCESS read-only
        STATUS     current
        DESCRIPTION
           "The number of EFCI cells transmitted to the switch 
            after traffic management and policing in
            ingress direction.
            This object is a 64-bit version of 
            cpAtmIfIngXmtEFCICells.
           "
        ::= {cpAtmIfStatsIngressEntry 7 }

cpAtmIfHCIngXmtOAMCells OBJECT-TYPE
        SYNTAX     Counter64
        MAX-ACCESS read-only
        STATUS     current
        DESCRIPTION
           "The number of OAM loopback cells transmitted to switch
            after traffic management and policing in
            ingress direction.
            This object is a 64-bit version of 
            cpAtmIfIngXmtOAMCells."
        ::= {cpAtmIfStatsIngressEntry 8 }

-- *********************************************************************
-- conformance information
-- *********************************************************************

cpAtmIfMIBConformance
     OBJECT IDENTIFIER ::= { ciscoPropAtmIfMIB 2 }

cpAtmIfMIBCompliances
     OBJECT IDENTIFIER ::= { cpAtmIfMIBConformance 1 }

cpAtmIfMIBGroups
     OBJECT IDENTIFIER ::= { cpAtmIfMIBConformance 2 }

--
--Conformance and compliance statements
--

cpAtmIfMIBCompliance  MODULE-COMPLIANCE
    STATUS  current
    DESCRIPTION
        "The compliance statement for the SNMP entities which implement
         ciscoPropAtmIfMIB."
    MODULE  -- this module
    MANDATORY-GROUPS {
                      cpAtmIfConfigGroup
                     }

    GROUP cpAtmIfEgressStatMIBGroup
    DESCRIPTION
        "This group is for the counters with a 32-bit version."

    GROUP cpAtmIfEgressIntervalMIBGroup
    DESCRIPTION
        "This group is for the counters with a 32-bit version."

    GROUP cpAtmIfIngressStatMIBGroup
    DESCRIPTION
        "This group is for the counters with a 32-bit version."

    GROUP cpAtmIfHCEgressStatMIBGroup
    DESCRIPTION
        "This group is for the counters with a 64-bit version."

    GROUP cpAtmIfHCEgressIntervalMIBGroup
    DESCRIPTION
        "This group is for the counters with a 64-bit version."

    GROUP cpAtmIfHCIngressStatMIBGroup
    DESCRIPTION
        "This group is for the counters with a 64-bit version." 
    ::= { cpAtmIfMIBCompliances 1 }                                                                              

--
--units of conformance
--
--MIB Groups
--
cpAtmIfConfigGroup  OBJECT-GROUP
    OBJECTS {
             cpAtmIfMaxBandwidth
            }
    STATUS    current
    DESCRIPTION
      "These are objects related to configuration of propAtm 
       Interface.
      "
    ::= { cpAtmIfMIBGroups 1 }

cpAtmIfEgressStatMIBGroup  OBJECT-GROUP
    OBJECTS {
             cpAtmIfEgrRcvClp0Cells,
             cpAtmIfEgrRcvClp1Cells,
             cpAtmIfEgrClp0DiscCells,
             cpAtmIfEgrClp1DiscCells,
             cpAtmIfEgrRcvOAMCells,
             cpAtmIfEgrRcvEFCICells
            }
    STATUS    current
    DESCRIPTION
        "These are objects related to Egress Statistics of propAtm 
         interfaces.
        "
    ::= { cpAtmIfMIBGroups 2 }

cpAtmIfEgressIntervalMIBGroup  OBJECT-GROUP
    OBJECTS {
             cpAtmIfIntEgrRcvClp0Cells,
             cpAtmIfIntEgrRcvClp1Cells,
             cpAtmIfIntEgrClp0DiscCells,
             cpAtmIfIntEgrClp1DiscCells,
             cpAtmIfIntEgrRcvOAMCells,
             cpAtmIfIntEgrRcvEFCICells      
            }
    STATUS    current
    DESCRIPTION
        "These are objects related to Egress Interval Statistics of  
         propAtm Interfaces.
        "
    ::= { cpAtmIfMIBGroups 3 }

cpAtmIfIngressStatMIBGroup  OBJECT-GROUP
    OBJECTS {
             cpAtmIfIngXmtClp0Cells,
             cpAtmIfIngXmtClp1Cells,
             cpAtmIfIngXmtEFCICells,
             cpAtmIfIngXmtOAMCells
            } 
    STATUS    current
    DESCRIPTION
        "These are objects related to Ingress Statistics of propAtm 
         interfaces.
        "
    ::= { cpAtmIfMIBGroups 4 }

cpAtmIfHCEgressStatMIBGroup  OBJECT-GROUP
    OBJECTS {
             cpAtmIfHCEgrRcvClp0Cells,
             cpAtmIfHCEgrRcvClp1Cells,
             cpAtmIfHCEgrClp0DiscCells,
             cpAtmIfHCEgrClp1DiscCells,
             cpAtmIfHCEgrRcvOAMCells,
             cpAtmIfHCEgrRcvEFCICells
            }
    STATUS    current
    DESCRIPTION
        "These are objects related to Egress Statistics of propAtm 
         interfaces.
         This group is a 64-bit version of cpAtmIfEgressStatMIBGroup.
        "
    ::= { cpAtmIfMIBGroups 5 }

cpAtmIfHCEgressIntervalMIBGroup  OBJECT-GROUP
    OBJECTS {
             cpAtmIfHCIntEgrRcvClp0Cells,
             cpAtmIfHCIntEgrRcvClp1Cells,
             cpAtmIfHCIntEgrClp0DiscCells,
             cpAtmIfHCIntEgrClp1DiscCells,
             cpAtmIfHCIntEgrRcvOAMCells,
             cpAtmIfHCIntEgrRcvEFCICells      
            }
    STATUS    current
    DESCRIPTION
        "These are objects related to Egress Interval Statistics of  
         propAtm Interfaces.
         This group is a 64-bit version of 
         cpAtmIfEgressIntervalMIBGroup.
        "
    ::= { cpAtmIfMIBGroups 6 }

cpAtmIfHCIngressStatMIBGroup  OBJECT-GROUP
    OBJECTS {
             cpAtmIfHCIngXmtClp0Cells,
             cpAtmIfHCIngXmtClp1Cells,
             cpAtmIfHCIngXmtEFCICells,
             cpAtmIfHCIngXmtOAMCells
            } 
    STATUS    current
    DESCRIPTION
        "These are objects related to Ingress Statistics of propAtm 
         interfaces.
         This group is a 64-bit version of cpAtmIfIngressStatMIBGroup.
        "
    ::= { cpAtmIfMIBGroups 7 }

 END
