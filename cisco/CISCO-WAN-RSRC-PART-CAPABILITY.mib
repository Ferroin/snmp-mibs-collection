CISCO-WAN-RSRC-PART-CAPABILITY DEFINITIONS ::= BEGIN

IMPORTS
        MODULE-IDENTITY, Unsigned32, Integer32
                FROM SNMPv2-SMI
        AGENT-CAPABILITIES
                FROM SNMPv2-CONF
        ciscoAgentCapability
                FROM CISCO-SMI;   

ciscoWanRsrcPartCapability MODULE-IDENTITY
        LAST-UPDATED    "200504260000Z"
        ORGANIZATION    "Cisco Systems, Inc."
        CONTACT-INFO
                "       Cisco Systems
                        Customer Service

                Postal: 170 W Tasman Drive
                        San Jose, CA  95134
                        USA

                        Tel: +1 800 553-NETS

                E-mail: cs-wanatm@cisco.com"
        DESCRIPTION
            "The Agent Capabilities for CISCO-WAN-RSRC-PART-MIB."

        REVISION "200504260000Z"
        DESCRIPTION
             "Added the agent capabilities 
             cwRsrcPartCapabilityAxsmeV2R00,
             cwRsrcPartCapabilityAxsmeV4R00 & 
             cwRsrcPartCapabilityAxsmeV5R00 for AXSME to
             add the variations for OIDs cwRsrcPartVciLo,
             cwRsrcPartVciHigh & cwRsrcPartMaxCon."

        REVISION "200409290000Z" 
        DESCRIPTION 
            "Updated cwRsrcPartCapabilityV5R00,cwRsrcPartCapabilityV4R00
             and cwRsrcPartCapabilityV2R00 with variations for the 
             OIDs cwRsrcPartEgrPctBwUsed,cwRsrcPartIngPctBwUsed,
             cwRsrcPartEgrPctBwAvail and cwRsrcPartIngPctBwAvail for
             AXSM,AXSME,AXSM-XG and PXM1E service modules."  

        REVISION "200311130000Z"
        DESCRIPTION
            "Added the capability cwRsrcPartCapabilityV5R00
             for MGX8850 Release 5.0.0"

        REVISION "200211110000Z"
        DESCRIPTION
            "Added ciscoWanRsrcPartCapability(4)
             for version 4.0.0 for AXSM, AXSME,
             AXSM-XG and PXM1E service modules."

        REVISION "200203130000Z"
        DESCRIPTION
            "Initial version of this MIB module."
        ::= { ciscoAgentCapability 260 }

cwRsrcPartCapabilityV2R00 AGENT-CAPABILITIES
    PRODUCT-RELEASE      "MGX8850 Release 2.0.00
                          and Release 2.1.00"
    STATUS               current
    DESCRIPTION          "CISCO-WAN-RSRC-PART-MIB Capabilities for
                         ATM Switch Service Module(AXSM)." 

    SUPPORTS CISCO-WAN-RSRC-PART-MIB
        INCLUDES { cwRsrcPartMIBGroup, 
                   cwRsrcPartIlmiMIBGroup}

        VARIATION   cwRsrcPartID
        SYNTAX      Unsigned32(1..20)
        DESCRIPTION "Maximum value supported is 20."

        VARIATION   cwRsrcPartController
        SYNTAX      Unsigned32(1..20)
        DESCRIPTION "Maximum value supported is 20."

        VARIATION   cwRsrcPartRowStatus
        SYNTAX      INTEGER { 
                        active(1), notInService(2),createAndGo(4),destroy(6)
                    }
        DESCRIPTION "Does not support createAndWait(5)."

        VARIATION   cwRsrcPartEgrPctBwUsed
        DESCRIPTION "The MIB object description expects data to be in
                    percentage bandwidth used by the resource partition.
                    However the agent implementation for this object 
                    has the bandwidth in  cells per second used 
                    by the resource partition."

        VARIATION   cwRsrcPartIngPctBwUsed
        DESCRIPTION "The MIB object description expects data to be in
                    percentage bandwidth used by the resource
                    partition. However the agent implementation 
                    for this object has the bandwidth in cells 
                    per second used  by the resource partition." 

        VARIATION   cwRsrcPartEgrPctBwAvail
        DESCRIPTION "The MIB object description expects data to be in
                    percentage bandwidth available on the resource 
                    partition. However the agent implementation 
                    for this object has the bandwidth in cells
                    per second available on the resource partition." 

        VARIATION   cwRsrcPartIngPctBwAvail
        DESCRIPTION "The MIB object description expects data to be in
                    percentage bandwidth available on the resource 
                    partition. However the agent implementation   
                    for this object has the bandwidth in cells
                    per second available on  the resource partition."  
    ::= { ciscoWanRsrcPartCapability 1 }

cwRsrcPartCapabilityRpmV2R0160 AGENT-CAPABILITIES
    PRODUCT-RELEASE      "MGX8850 Release 2.1.60"
    STATUS               current
    DESCRIPTION          "Agent Capabilities for CISCO-WAN-RSRC-PART-MIB
                          for RPM-PR Module."

    SUPPORTS CISCO-WAN-RSRC-PART-MIB

        INCLUDES { cwRsrcPartMIBGroup }

        VARIATION   cwRsrcPartID
        SYNTAX      Unsigned32 (1..10)
        DESCRIPTION "Only limited range is supported.
                     The Value 1 is reserved for PNNI Controller."

        VARIATION   cwRsrcPartController
        DESCRIPTION "Value 2 is assumed to be for PNNI Controller."

        VARIATION cwRsrcPartEgrGuarPctBwConf
        DESCRIPTION
            "Only whole percentage is supported. For example
             1%, 10% etc."

        VARIATION cwRsrcPartEgrMaxPctBwConf
        DESCRIPTION
            "Only whole percentage is supported. For example
             1%, 10% etc."

        VARIATION cwRsrcPartIngGuarPctBwConf
        DESCRIPTION
            "Only whole percentage is supported. For example
             1%, 10% etc."

        VARIATION cwRsrcPartIngMaxPctBwConf
        DESCRIPTION
            "Only whole percentage is supported. For example
             1%, 10% etc."

        VARIATION cwRsrcPartVpiLo
        SYNTAX Unsigned32 (0..255)
        DESCRIPTION
            "Restricted range is supported.

             For VCC partition, only value zero
             is supported.

             For VPC partition, (1..255) are supported."

        VARIATION cwRsrcPartVpiHigh
        SYNTAX Unsigned32 (0..255)
        DESCRIPTION
            "Restricted range is supported.

             For VCC partition, only value zero
             is supported.

             For VPC partition, (1..255) are supported."

        VARIATION cwRsrcPartVciLo
        SYNTAX Unsigned32 (1..65535)
        DESCRIPTION
            "Restricted range is supported.
             For VCC partiton, the valid range is (1..3808).
             For VPC partiton, the valid range is (0..65535)."

        VARIATION cwRsrcPartVciHigh
        SYNTAX Unsigned32 (1..65535)
        DESCRIPTION
            "Restricted range is supported.
             For VCC partiton, the valid range is (1..3808).
             For VPC partiton, the valid range is (0..65535)."

        VARIATION cwRsrcPartGuarCon
        ACCESS    read-only
        DESCRIPTION
            "Write operation is not supported."

        VARIATION cwRsrcPartMaxCon
        ACCESS    read-only
        DESCRIPTION
            "Write operation is not supported."

        VARIATION   cwRsrcPartRowStatus
        SYNTAX      INTEGER {
                        active(1),
                        createAndGo(4),
                        destroy(6)
                    }
        DESCRIPTION "Does not support notInService(2),
                     notReady(3) and createAndWait(5)."
    ::= { ciscoWanRsrcPartCapability 2 }

cwRsrcPartCapabilityRpmxfV12R02 AGENT-CAPABILITIES
    PRODUCT-RELEASE      "IOS Release 12.2.
                          MGX8850 Release 3.0.00."
    STATUS               current
    DESCRIPTION          "Agent Capabilities for CISCO-WAN-RSRC-PART-MIB
                          for RPM-XF Module."

    SUPPORTS CISCO-WAN-RSRC-PART-MIB

        INCLUDES { cwRsrcPartMIBGroup }

        VARIATION   cwRsrcPartID
        SYNTAX      Unsigned32 (1..10)
        DESCRIPTION "Only limited range is supported.
                     The Value 1 is reserved for PNNI Controller."

        VARIATION   cwRsrcPartController
        DESCRIPTION "Value 2 is assumed to be for PNNI Controller.
                     Value 3 is assumed to be for LSC Controller."

        VARIATION cwRsrcPartEgrGuarPctBwConf
        DESCRIPTION
            "Only whole percentage is supported. For example
             1%, 10% etc."

        VARIATION cwRsrcPartEgrMaxPctBwConf
        DESCRIPTION
            "Only whole percentage is supported. For example
             1%, 10% etc."

        VARIATION cwRsrcPartIngGuarPctBwConf
        DESCRIPTION
            "Only whole percentage is supported. For example
             1%, 10% etc."

        VARIATION cwRsrcPartIngMaxPctBwConf
        DESCRIPTION
            "Only whole percentage is supported. For example
             1%, 10% etc."

        VARIATION cwRsrcPartVpiLo
        SYNTAX Unsigned32 (0..240)
        DESCRIPTION
            "Restricted range is supported."

        VARIATION cwRsrcPartVpiHigh
        SYNTAX Unsigned32 (0..240)
        DESCRIPTION
            "Restricted range is supported."

        VARIATION cwRsrcPartVciLo
        SYNTAX Unsigned32 (32..65535)
        DESCRIPTION
            "Restricted range is supported."

        VARIATION cwRsrcPartVciHigh
        SYNTAX Unsigned32 (32..65535)
        DESCRIPTION
            "Restricted range is supported."

        VARIATION cwRsrcPartGuarCon
        SYNTAX Unsigned32(0..15744)
        DESCRIPTION
            "Restricted range is supported."

        VARIATION cwRsrcPartMaxCon
        SYNTAX Unsigned32(0..15744)
        DESCRIPTION
            "Restricted range is supported."

        VARIATION   cwRsrcPartRowStatus
        SYNTAX      INTEGER {
                        active(1),
                        createAndGo(4),
                        destroy(6)
                    }
        DESCRIPTION "Does not support notInService(2),
                     notReady(3) and createAndWait(5)."
    ::= { ciscoWanRsrcPartCapability 3 }

cwRsrcPartCapabilityV4R00 AGENT-CAPABILITIES
    PRODUCT-RELEASE      "MGX8850 Release 4.0.00"
    STATUS               current
    DESCRIPTION          "CISCO-WAN-RSRC-PART-MIB Capabilities for
                         ATM Switch Service Module(AXSM), AXSM-XG
                         and PXM1E"

    SUPPORTS CISCO-WAN-RSRC-PART-MIB
    INCLUDES { cwRsrcPartMIBGroup, 
               cwRsrcPartIlmiMIBGroup}

    VARIATION   cwRsrcPartID
    SYNTAX      Unsigned32(1..20)
    DESCRIPTION "Maximum value supported is 20."

    VARIATION   cwRsrcPartController
    SYNTAX      Unsigned32(1..20)
    DESCRIPTION "Maximum value supported is 20."

    VARIATION   cwRsrcPartRowStatus
    SYNTAX      INTEGER { 
                active(1), notInService(2),createAndGo(4),destroy(6)
                }
    DESCRIPTION "Does not support createAndWait(5)."

    VARIATION   cwRsrcPartIlmiEstablishConPollIntvl
    SYNTAX      Unsigned32(1..16)
    DESCRIPTION "Maximum value supported is 16."

    VARIATION   cwRsrcPartIlmiCheckConPollIntvl
    SYNTAX      Unsigned32(0..255)
    DESCRIPTION "Maximum value supported is 255."

    VARIATION   cwRsrcPartIlmiConPollInactFactor
    SYNTAX      Unsigned32(1..255)
    DESCRIPTION "Minimum value supported is 1 and 
                 maximum value supported is 255."

     VARIATION   cwRsrcPartEgrPctBwUsed
     DESCRIPTION "The MIB object description expects data to be in
                  percentage bandwidth used by the resource partition.
                  However the agent implementation for this object
                  has the bandwidth in  cells per second used
                  by the resource partition."

     VARIATION   cwRsrcPartIngPctBwUsed
     DESCRIPTION "The MIB object description expects data to be in
                  percentage bandwidth used by the resource partition.
                  However the agent implementation for this object
                  has the bandwidth in  cells per second used
                  by the resource partition."

     VARIATION   cwRsrcPartEgrPctBwAvail
     DESCRIPTION "The MIB object description expects data to be in
                  percentage bandwidth available on the resource 
                  partition. However the agent implementation for
                  this object has the bandwidth in  cells per second
                  available on the resource partition."

     VARIATION    cwRsrcPartIngPctBwAvail
     DESCRIPTION  "The MIB object description expects data to be in
                   percentage bandwidth available on the resource 
                   partition. However the agent implementation for
                   this object has the bandwidth in  cells per second
                   available on the resource partition."
    ::= { ciscoWanRsrcPartCapability 4 }

cwRsrcPartCapabilityV5R00 AGENT-CAPABILITIES
    PRODUCT-RELEASE "MGX8850 Release 5.0.0"
    STATUS          current
    DESCRIPTION     "Agent capabilities for VXSM module in 
                     Release 5.0.0."

    SUPPORTS        CISCO-WAN-RSRC-PART-MIB

    INCLUDES { cwRsrcPartMIBGroup, 
               cwRsrcSvcAggrGroup }

    VARIATION   cwRsrcPartConfEntry
    CREATION-REQUIRES {
                         cwRsrcPartController,
                         cwRsrcPartEgrGuarPctBwConf,
                         cwRsrcPartEgrMaxPctBwConf,
                         cwRsrcPartIngGuarPctBwConf,
                         cwRsrcPartIngMaxPctBwConf,
                         cwRsrcPartVpiLo,
                         cwRsrcPartVpiHigh,
                         cwRsrcPartVciLo,
                         cwRsrcPartVciHigh,
                         cwRsrcPartGuarCon,
                         cwRsrcPartMaxCon
                      }
    DESCRIPTION "These objects must be explicitly set by NMS in
                 entry creation.
                 Object cwRsrcPartController cannot be modified if 
                 cwRsrcPartRowStatus value is 'active'."

    VARIATION   cwRsrcSvcAggregateEntry
    CREATION-REQUIRES {
                         cwRsrcSvcAggrVpiLow, 
                         cwRsrcSvcAggrVpiHigh,
                         cwRsrcSvcAggrEgrPctBw, 
                         cwRsrcSvcAggrIngPctBw
                      }
    DESCRIPTION "These objects must be explicitly set by NMS in
                 entry creation.
                 The following objects cannot be modified if the
                 entry is active: 
                     cwRsrcSvcAggrVpiLow
                     cwRsrcSvcAggrVpiHigh."

    VARIATION   cwRsrcPartRowStatus
    SYNTAX      INTEGER {
                        active(1),
                        createAndGo(4),
                        destroy(6)
                }
    DESCRIPTION "Does not support notInService(2),
                 notReady(3) and createAndWait(5)."

    VARIATION   cwRsrcPartID
    SYNTAX      Unsigned32 (1..1)
    DESCRIPTION "Only one resource partition is supported."

    VARIATION   cwRsrcPartController
    SYNTAX      Unsigned32 (2..2)
    DESCRIPTION "The valid value is 2."

    VARIATION   cwRsrcPartEgrGuarPctBwConf
    DESCRIPTION "The value of this object must be the same as that of
                 cwRsrcPartIngGuarPctBwConf."

    VARIATION   cwRsrcPartEgrMaxPctBwConf
    DESCRIPTION "The value of this object must be the same as that of
                 cwRsrcPartIngMaxPctBwConf."

    VARIATION   cwRsrcPartIngGuarPctBwConf
    DESCRIPTION "The value of this object must be the same as that of
                 cwRsrcPartEgrGuarPctBwConf."

    VARIATION   cwRsrcPartIngMaxPctBwConf
    DESCRIPTION "The value of this object must be the same as that of
                 cwRsrcPartEgrMaxPctBwConf."

    VARIATION   cwRsrcPartVpiLo
    SYNTAX      Unsigned32 (0..255)
    DESCRIPTION "Range is from 0 to 255"

    VARIATION   cwRsrcPartVpiHigh
    SYNTAX      Unsigned32 (0..255)
    DESCRIPTION "Range is from 0 to 255"

    VARIATION   cwRsrcPartVciLo
    SYNTAX      Unsigned32 (1..65535)
    DESCRIPTION "Restricted range is supported."

    VARIATION   cwRsrcPartVciHigh
    SYNTAX      Unsigned32 (1..65535)
    DESCRIPTION "Restricted range is supported."

    VARIATION   cwRsrcPartGuarCon
    SYNTAX      Unsigned32 (0..8300)
    DESCRIPTION "Range is from 0 to 8300"

    VARIATION   cwRsrcPartMaxCon
    SYNTAX      Unsigned32 (0..8300)
    DESCRIPTION "Range is from 0 to 8300"

    VARIATION   cwRsrcSvcAggrRowStatus
    SYNTAX      INTEGER {
                        active(1),
                        createAndGo(4),
                        destroy(6)
                }
    DESCRIPTION "Does not support notInService(2),
                 notReady(3) and createAndWait(5)."

    VARIATION   cwRsrcSvcAggrVpiLow
    SYNTAX      Unsigned32 (0..255)
    DESCRIPTION "Range is from 0 to 255.
                 Equal values of cwRsrcSvcAggrVpiLow and 
                 cwRsrcSvcAggrVpiHigh are recommended because
                 VCI range of the containing resource partition
                 is usually sufficient for maximum number of
                 connections. "

    VARIATION   cwRsrcSvcAggrVpiHigh
    SYNTAX      Unsigned32 (0..255)
    DESCRIPTION "Range is from 0 to 255"

    VARIATION   cwRsrcSvcAggrEgrPctBw
    SYNTAX      Integer32 (1..90)
    DESCRIPTION "Limited range is supported.
                 The value of this object must be the same as that of
                 cwRsrcSvcAggrIngPctPw."

    VARIATION   cwRsrcSvcAggrIngPctBw
    SYNTAX      Integer32 (1..90)
    DESCRIPTION "Limited range is supported.
                 The value of this object must be the same as that of
                 cwRsrcSvcAggrEgrPctPw."

--
-- Variations applicable to AXSM,AXSM-XG,PXM1E.
--
    VARIATION   cwRsrcPartEgrPctBwUsed
    DESCRIPTION "The MIB object description expects data to be in
                 percentage bandwidth used by the resource partition.
                 However the agent implementation for this object has
                 the bandwidth in  cells per second used
                 by the resource partition." 

     VARIATION   cwRsrcPartIngPctBwUsed
     DESCRIPTION "The MIB object description expects data to be in
                  percentage bandwidth used by the resource partition.
                  However the agent implementation for this object has
                  the bandwidth in  cells per second used
                  by the resource partition." 

     VARIATION   cwRsrcPartEgrPctBwAvail
     DESCRIPTION "The MIB object description expects data to be in
                  percentage bandwidth available on the resource 
                  partition. However the agent implementation for
                  this object has the bandwidth in  cells per second
                  available on the resource partition."

     VARIATION  cwRsrcPartIngPctBwAvail
     DESCRIPTION "The MIB object description expects data to be in
                  percentage bandwidth available on the resource 
                  partition. However the agent implementation for
                  this object has the bandwidth in  cells per second
                  available on the resource partition."
    ::= { ciscoWanRsrcPartCapability 5 }

cwRsrcPartCapabilityAxsmeV2R00 AGENT-CAPABILITIES
    PRODUCT-RELEASE      "MGX8850 Release 2.0.00
                          and Release 2.1.00"
    STATUS               current
    DESCRIPTION          "CISCO-WAN-RSRC-PART-MIB Capabilities for
                         Enhanced AXSM(AXSM-E)."

    SUPPORTS CISCO-WAN-RSRC-PART-MIB

    INCLUDES { cwRsrcPartMIBGroup,
               cwRsrcPartIlmiMIBGroup}

    VARIATION   cwRsrcPartID
    SYNTAX      Unsigned32(1..20)
    DESCRIPTION "Maximum value supported is 20."

    VARIATION   cwRsrcPartController
    SYNTAX      Unsigned32(1..20)
    DESCRIPTION "Maximum value supported is 20."

    VARIATION   cwRsrcPartRowStatus
    SYNTAX      INTEGER {
                    active(1), notInService(2),createAndGo(4),destroy(6)
                }
    DESCRIPTION "Does not support createAndWait(5)."

    VARIATION   cwRsrcPartEgrPctBwUsed
    DESCRIPTION "The MIB object description expects data to be in
                percentage bandwidth used by the resource partition.
                However the agent implementation for this object
                has the bandwidth in  cells per second used
                by the resource partition."

    VARIATION   cwRsrcPartIngPctBwUsed
    DESCRIPTION "The MIB object description expects data to be in
                percentage bandwidth used by the resource
                partition. However the agent implementation
                for this object has the bandwidth in cells
                per second used  by the resource partition."

    VARIATION   cwRsrcPartEgrPctBwAvail
    DESCRIPTION "The MIB object description expects data to be in
                percentage bandwidth available on the resource
                partition. However the agent implementation
                for this object has the bandwidth in cells
                per second available on the resource partition."

    VARIATION  cwRsrcPartIngPctBwAvail
    DESCRIPTION "The MIB object description expects data to be in
                percentage bandwidth available on the resource
                partition. However the agent implementation for
                this object has the bandwidth in  cells per second
                available on the resource partition."

    VARIATION   cwRsrcPartVciLo
    SYNTAX      Unsigned32 (1..65535)
    DESCRIPTION "Restricted range is supported."

    VARIATION   cwRsrcPartVciHigh
    SYNTAX      Unsigned32 (1..65535)
    DESCRIPTION "Restricted range is supported."

    VARIATION   cwRsrcPartMaxCon
    SYNTAX      Unsigned32 (10..60768)
    DESCRIPTION "Range is from 10 to 60768"
    ::= { ciscoWanRsrcPartCapability 6 }

cwRsrcPartCapabilityAxsmeV4R00 AGENT-CAPABILITIES
    PRODUCT-RELEASE      "MGX8850 Release 4.0.00"
    STATUS               current
    DESCRIPTION          "CISCO-WAN-RSRC-PART-MIB Capabilities for
                         Enhanced AXSM(AXSM-E)"

    SUPPORTS CISCO-WAN-RSRC-PART-MIB

    INCLUDES { cwRsrcPartMIBGroup,
               cwRsrcPartIlmiMIBGroup}

    VARIATION   cwRsrcPartID
    SYNTAX      Unsigned32(1..20)
    DESCRIPTION "Maximum value supported is 20."

    VARIATION   cwRsrcPartController
    SYNTAX      Unsigned32(1..20)
    DESCRIPTION "Maximum value supported is 20."

    VARIATION   cwRsrcPartRowStatus
    SYNTAX      INTEGER {
                active(1), notInService(2),createAndGo(4),destroy(6)
                }
    DESCRIPTION "Does not support createAndWait(5)."

    VARIATION   cwRsrcPartIlmiEstablishConPollIntvl
    SYNTAX      Unsigned32(1..16)
    DESCRIPTION "Maximum value supported is 16."

    VARIATION   cwRsrcPartIlmiCheckConPollIntvl
    SYNTAX      Unsigned32(0..255)
    DESCRIPTION "Maximum value supported is 255."

    VARIATION   cwRsrcPartIlmiConPollInactFactor
    SYNTAX      Unsigned32(1..255)
    DESCRIPTION "Minimum value supported is 1 and
                maximum value supported is 255."

    VARIATION   cwRsrcPartEgrPctBwUsed
    DESCRIPTION "The MIB object description expects data to be in
                percentage bandwidth used by the resource partition.
                However the agent implementation for this object
                has the bandwidth in  cells per second used
                by the resource partition."

    VARIATION   cwRsrcPartIngPctBwUsed
    DESCRIPTION "The MIB object description expects data to be in
                percentage bandwidth used by the resource partition.
                However the agent implementation for this object
                has the bandwidth in  cells per second used
                by the resource partition."

    VARIATION   cwRsrcPartEgrPctBwAvail
    DESCRIPTION "The MIB object description expects data to be in
                percentage bandwidth available on the resource
                partition. However the agent implementation for
                this object has the bandwidth in  cells per second
                available on the resource partition."

    VARIATION    cwRsrcPartIngPctBwAvail
    DESCRIPTION  "The MIB object description expects data to be in
                 percentage bandwidth available on the resource
                 partition. However the agent implementation for
                 this object has the bandwidth in  cells per second
                 available on the resource partition."

    VARIATION   cwRsrcPartVciLo
    SYNTAX      Unsigned32 (1..65535)
    DESCRIPTION "Restricted range is supported."

    VARIATION   cwRsrcPartVciHigh
    SYNTAX      Unsigned32 (1..65535)
    DESCRIPTION "Restricted range is supported."

    VARIATION   cwRsrcPartMaxCon
    SYNTAX      Unsigned32 (10..60768)
    DESCRIPTION "Range is from 10 to 60768"
    ::= { ciscoWanRsrcPartCapability 7 }

cwRsrcPartCapabilityAxsmeV5R00 AGENT-CAPABILITIES
    PRODUCT-RELEASE      "MGX8850 Release 5.0.00"
    STATUS               current
    DESCRIPTION          "CISCO-WAN-RSRC-PART-MIB Capabilities for
                         Enhanced AXSM(AXSM-E)."

    SUPPORTS CISCO-WAN-RSRC-PART-MIB

    INCLUDES { cwRsrcPartMIBGroup,
               cwRsrcPartIlmiMIBGroup}

    VARIATION   cwRsrcPartID
    SYNTAX      Unsigned32(1..20)
    DESCRIPTION "Maximum value supported is 20."

    VARIATION   cwRsrcPartController
    SYNTAX      Unsigned32(1..20)
    DESCRIPTION "Maximum value supported is 20."

    VARIATION   cwRsrcPartRowStatus
    SYNTAX      INTEGER {
                active(1), notInService(2),createAndGo(4),destroy(6)
                }
    DESCRIPTION "Does not support createAndWait(5)."

    VARIATION   cwRsrcPartIlmiEstablishConPollIntvl
    SYNTAX      Unsigned32(1..16)
    DESCRIPTION "Maximum value supported is 16."

    VARIATION   cwRsrcPartIlmiCheckConPollIntvl
    SYNTAX      Unsigned32(0..255)
    DESCRIPTION "Maximum value supported is 255."

    VARIATION   cwRsrcPartIlmiConPollInactFactor
    SYNTAX      Unsigned32(1..255)
    DESCRIPTION "Minimum value supported is 1 and
                maximum value supported is 255."

    VARIATION   cwRsrcPartEgrPctBwUsed
    DESCRIPTION "The MIB object description expects data to be in
                 percentage bandwidth used by the resource partition.
                 However the agent implementation for this object has
                 the bandwidth in  cells per second used
                 by the resource partition."

    VARIATION   cwRsrcPartIngPctBwUsed
    DESCRIPTION "The MIB object description expects data to be in
                 percentage bandwidth used by the resource partition.
                 However the agent implementation for this object has
                 the bandwidth in  cells per second used
                 by the resource partition."

    VARIATION   cwRsrcPartEgrPctBwAvail
    DESCRIPTION "The MIB object description expects data to be in
                 percentage bandwidth available on the resource
                 partition. However the agent implementation for
                 this object has the bandwidth in  cells per second
                 available on the resource partition."

    VARIATION  cwRsrcPartIngPctBwAvail
    DESCRIPTION "The MIB object description expects data to be in
                 percentage bandwidth available on the resource
                 partition. However the agent implementation for
                 this object has the bandwidth in  cells per second
                 available on the resource partition."

    VARIATION   cwRsrcPartVciLo
    SYNTAX      Unsigned32 (1..65535)
    DESCRIPTION "Restricted range is supported."

    VARIATION   cwRsrcPartVciHigh
    SYNTAX      Unsigned32 (1..65535)
    DESCRIPTION "Restricted range is supported."

    VARIATION   cwRsrcPartMaxCon
    SYNTAX      Unsigned32 (10..60768)
    DESCRIPTION "Range is from 10 to 60768"
    ::= { ciscoWanRsrcPartCapability 8 }
END
