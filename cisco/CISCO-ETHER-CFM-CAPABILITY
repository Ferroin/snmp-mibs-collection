CISCO-ETHER-CFM-CAPABILITY DEFINITIONS ::= BEGIN

IMPORTS
    MODULE-IDENTITY
        FROM SNMPv2-SMI

    AGENT-CAPABILITIES
        FROM SNMPv2-CONF

    ciscoAgentCapability
        FROM CISCO-SMI;

ciscoEtherCfmMibCapability MODULE-IDENTITY
    LAST-UPDATED    "200502110000Z"
    ORGANIZATION    "Cisco Systems, Inc."
    CONTACT-INFO    
        "            Cisco Systems
                     Customer Service
             Postal: 170 W Tasman Drive
                     San Jose, CA 95134
                     USA
                Tel: +1 800 553-NETS
             E-mail: cs-ethermibs@cisco.com"
    DESCRIPTION
        "Agent capabilities for the CISCO-ETHER-CFM-MIB."
    REVISION        "200502110000Z"
    DESCRIPTION     
        "Initial version of this MIB module."
    ::= { ciscoAgentCapability 431 }

ciscoEtherCfmMibCapabilityV122 AGENT-CAPABILITIES

    PRODUCT-RELEASE "Cisco IOS 12.2X (exact rev TBD)"
    STATUS          current
    DESCRIPTION     "CISCO-ETHER-CFM-MIB capabilities."

    SUPPORTS        CISCO-ETHER-CFM-MIB
    INCLUDES        { ciscoEtherCfmMIBEventGroup,
                      ciscoEtherCfmMIBNotifGroup 
                    }

    VARIATION       cEtherCfmMaxEventIndex
    ACCESS          not-implemented
    DESCRIPTION     "This object is not supported."

    VARIATION       cEtherCfmEventDomainName
    ACCESS          not-implemented
    DESCRIPTION     "This object is not supported."

    VARIATION       cEtherCfmEventType
    ACCESS          not-implemented
    DESCRIPTION     "This object is not supported."

    VARIATION       cEtherCfmEventLastChange
    ACCESS          not-implemented
    DESCRIPTION     "This object is not supported."

    VARIATION       cEtherCfmEventServiceId    
    ACCESS          accessible-for-notify
    DESCRIPTION     "This object is inaccessible except through CFM
                    notification messages."

    VARIATION       cEtherCfmEventLclMepid
    ACCESS          accessible-for-notify
    DESCRIPTION     "This object is inaccessible except through CFM
                    notification messages."

    VARIATION       cEtherCfmEventLclMacAddress
    ACCESS          accessible-for-notify
    DESCRIPTION     "This object is inaccessible except through CFM
                    notification messages."

    VARIATION       cEtherCfmEventLclMepCount
    ACCESS          accessible-for-notify
    DESCRIPTION     "This object is inaccessible except through CFM
                    notification messages."

    VARIATION       cEtherCfmEventLclIfCount
    ACCESS          accessible-for-notify
    DESCRIPTION     "This object is inaccessible except through CFM
                    notification messages."

    VARIATION       cEtherCfmEventRmtMepid
    ACCESS          accessible-for-notify
    DESCRIPTION     "This object is inaccessible except through CFM
                    notification messages."

    VARIATION       cEtherCfmEventRmtMacAddress
    ACCESS          accessible-for-notify
    DESCRIPTION     "This object is inaccessible except through CFM
                    notification messages."

    VARIATION       cEtherCfmEventRmtPortState
    ACCESS          accessible-for-notify
    DESCRIPTION     "This object is inaccessible except through CFM
                    notification messages."

    VARIATION       cEtherCfmEventRmtServiceId 
    ACCESS          accessible-for-notify
    DESCRIPTION     "This object is inaccessible except through CFM
                    notification messages."

    VARIATION       cEtherCfmEventCode 
    ACCESS          accessible-for-notify
    DESCRIPTION     "This object is inaccessible except through CFM
                    notification messages."

    VARIATION       cEtherCfmEventDeleteRow
    ACCESS          not-implemented
    DESCRIPTION     "This object is not supported."
    ::= { ciscoEtherCfmMibCapability 1 }

END
