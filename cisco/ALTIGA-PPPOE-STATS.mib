ALTIGA-PPPOE-STATS-MIB DEFINITIONS ::= BEGIN

   IMPORTS
      MODULE-IDENTITY, OBJECT-TYPE, Integer32, Counter32, 
      Gauge32, Unsigned32
         FROM SNMPv2-SMI
      DisplayString, MacAddress
         FROM SNMPv2-TC
      OBJECT-GROUP, MODULE-COMPLIANCE
         FROM SNMPv2-CONF
      alStatsPPPoE, alPPPoEGroup
         FROM ALTIGA-MIB
      alPPPoEMibModule
         FROM ALTIGA-GLOBAL-REG; 

   altigaPPPoEStatsMibModule MODULE-IDENTITY
      LAST-UPDATED   "200707110000Z"
      ORGANIZATION   "Cisco Systems, Inc."
      CONTACT-INFO
         "Cisco Systems
          170 W Tasman Drive
          San Jose, CA  95134
          USA

          Tel: +1 800 553-NETS
          E-mail: cs-cvpn3000@cisco.com"
      DESCRIPTION
         "The Altiga PPPoE Statistics MIB models counters and objects that are
          of management interest for PPPoE.

          Acronyms
          The following acronyms are used in this document:

            MIB:        Management Information Base

            PADI:       PPPoE Active Discovery Initiation

            PADO:       PPPoE Active Discovery Offer

            PADS:       PPPoE Active Discovery Session-confirmation

            PADT:       PPPoE Active Discovery Terminate

            PPPoE:      Point-to-Point Protocol over Ethernet
         "
        REVISION "200707110000Z"
       DESCRIPTION
                "Added range for Index Object alPPPoEStatsIfIndex object "
        REVISION "200209051300Z"
        DESCRIPTION
                "Added module compliance."

        REVISION "200207100000Z"
        DESCRIPTION
                "Updated with new header"
      ::= { alPPPoEMibModule 2 }

-- +++++++++++++++++++++++++++++++++++++++++++++++++++++++
-- MIB Objects
-- +++++++++++++++++++++++++++++++++++++++++++++++++++++++

alStatsPPPoEGlobal OBJECT IDENTIFIER ::= { alStatsPPPoE 1 }

alPPPoEStatsActiveSessions OBJECT-TYPE
   SYNTAX         Gauge32
   MAX-ACCESS     read-only
   STATUS         current
   DESCRIPTION
      "The number of active sessions on the interface
       (currently should max at 1)."
   ::= { alStatsPPPoEGlobal 1 }

alPPPoEStatsTotalSessions  OBJECT-TYPE
   SYNTAX         Counter32
   MAX-ACCESS     read-only
   STATUS         current
   DESCRIPTION    
      "Total Sessions since last reset."
   ::= { alStatsPPPoEGlobal 2 }

alPPPoEStatsMaxSessions    OBJECT-TYPE
   SYNTAX         Counter32
   MAX-ACCESS     read-only
   STATUS         current
   DESCRIPTION
      "Peak number of sessions since last reset."
   ::= { alStatsPPPoEGlobal 3 }

alPPPoEStatsIfTable     OBJECT-TYPE
   SYNTAX         SEQUENCE OF AlPPPoEStatsIfEntry
   MAX-ACCESS     not-accessible
   STATUS         current
   DESCRIPTION
      "Contains the PPPoE binding entries for stats."
   ::= { alStatsPPPoE 2 }

alPPPoEStatsIfEntry     OBJECT-TYPE
   SYNTAX         AlPPPoEStatsIfEntry
   MAX-ACCESS     not-accessible
   STATUS         current
   DESCRIPTION
      "Contains the PPPoE entries for the status 
       binding table."
   INDEX          { alPPPoEStatsIfIndex }
   ::= { alPPPoEStatsIfTable 1 }

AlPPPoEStatsIfEntry ::= SEQUENCE {
   alPPPoEStatsIfIndex        Integer32,
   alPPPoEStatsIfPADTRx       Counter32,
   alPPPoEStatsIfPADTTx       Counter32,
   alPPPoEStatsIfGenericErrorsRx    Counter32,
   alPPPoEStatsIfMalformedPacketsRx Counter32,
   alPPPoEStatsIfPADITimeouts    Counter32,
   alPPPoEStatsIfPADRTimeouts    Counter32,
   alPPPoEStatsIfMultPADORx      Counter32,
   alPPPoEStatsIfSessionID       Integer32,
   alPPPoEStatsIfPeerAddr        MacAddress,
   alPPPoEStatsIfSessionState    INTEGER,
   alPPPoEStatsIfVersion         Integer32,
   alPPPoEStatsIfType         Integer32,
   alPPPoEStatsIfConnectTime     Unsigned32,
   alPPPoEStatsIfDuration        Unsigned32,
   alPPPoEStatsIfPeerName        DisplayString,
   alPPPoEStatsIfACCookie        OCTET STRING,
   alPPPoEStatsIfHostUnique      OCTET STRING,
   alPPPoEStatsIfRelaySessID     OCTET STRING
}

alPPPoEStatsIfIndex     OBJECT-TYPE
   SYNTAX         Integer32 (1..2147483647)
   MAX-ACCESS     read-only
   STATUS         current
   DESCRIPTION
      "The interface index for PPPoE status binding table."
   ::= { alPPPoEStatsIfEntry 1 }

alPPPoEStatsIfPADTRx    OBJECT-TYPE
   SYNTAX         Counter32
   MAX-ACCESS     read-only
   STATUS         current
   DESCRIPTION 
      "Number of PADT received."
   ::= { alPPPoEStatsIfEntry 2 }

alPPPoEStatsIfPADTTx    OBJECT-TYPE
   SYNTAX         Counter32
   MAX-ACCESS     read-only
   STATUS         current
   DESCRIPTION
      "Number of PADT transmitted."
   ::= { alPPPoEStatsIfEntry 3 }

alPPPoEStatsIfGenericErrorsRx OBJECT-TYPE
   SYNTAX         Counter32
   MAX-ACCESS     read-only
   STATUS         current
   DESCRIPTION
      "Number of Generic Errors Received."
   ::= { alPPPoEStatsIfEntry 4 }

alPPPoEStatsIfMalformedPacketsRx OBJECT-TYPE
   SYNTAX            Counter32
   MAX-ACCESS        read-only
   STATUS            current
   DESCRIPTION
      "Number of back packets received."
   ::= { alPPPoEStatsIfEntry 5 }

alPPPoEStatsIfPADITimeouts OBJECT-TYPE
   SYNTAX         Counter32   
   MAX-ACCESS     read-only
   STATUS         current
   DESCRIPTION
      "Number of times timedout waiting for a PADO."
   ::= { alPPPoEStatsIfEntry 6 }

alPPPoEStatsIfPADRTimeouts OBJECT-TYPE
   SYNTAX         Counter32
   MAX-ACCESS     read-only
   STATUS         current
   DESCRIPTION
      "Number of times timed out waiting for a PADS."
   ::= { alPPPoEStatsIfEntry 7 }

alPPPoEStatsIfMultPADORx   OBJECT-TYPE
   SYNTAX         Counter32
   MAX-ACCESS     read-only
   STATUS         current
   DESCRIPTION
      "Number of times we received more than 1 PADO."
   ::= { alPPPoEStatsIfEntry 8 }

alPPPoEStatsIfSessionID    OBJECT-TYPE
   SYNTAX         Integer32
   MAX-ACCESS     read-only
   STATUS         current
   DESCRIPTION
      "Session ID given by the AC."
   ::= { alPPPoEStatsIfEntry 9 }

alPPPoEStatsIfPeerAddr     OBJECT-TYPE
   SYNTAX         MacAddress
   MAX-ACCESS     read-only
   STATUS         current
   DESCRIPTION
      "MAC address of the remote AC."
   ::= { alPPPoEStatsIfEntry 10 }

alPPPoEStatsIfSessionState OBJECT-TYPE
   SYNTAX         INTEGER {
            noState(1),
            pADISent(2),
            pADIRcvd(3),
            pADOSent(4),
            pADORcvd(5),
            pADRSent(6),
            pADRRcvd(7),
            pADSSent(8),
            pADSRcvd(9),
            sessionStage(10)
            }
   MAX-ACCESS     read-only
   STATUS         current
   DESCRIPTION
      "State that the session is in."
   ::= { alPPPoEStatsIfEntry 11 }

alPPPoEStatsIfVersion      OBJECT-TYPE
   SYNTAX         Integer32
   MAX-ACCESS     read-only
   STATUS         current
   DESCRIPTION
      "Version as given in the PPPoE RFC."
   ::= { alPPPoEStatsIfEntry 12 }

alPPPoEStatsIfType      OBJECT-TYPE
   SYNTAX         Integer32
   MAX-ACCESS     read-only
   STATUS         current
   DESCRIPTION
      "Type as given in the PPPoE RFC."
   ::= { alPPPoEStatsIfEntry 13 }

alPPPoEStatsIfConnectTime  OBJECT-TYPE
   SYNTAX         Unsigned32
   MAX-ACCESS     read-only
   STATUS         current
   DESCRIPTION
      "Time_t of when the session was established."
   ::= { alPPPoEStatsIfEntry 14 }

alPPPoEStatsIfDuration     OBJECT-TYPE
   SYNTAX         Unsigned32
   MAX-ACCESS     read-only
   STATUS         current
   DESCRIPTION
      "Number of seconds since the session was 
       established."
   ::= { alPPPoEStatsIfEntry 15 }

alPPPoEStatsIfPeerName     OBJECT-TYPE
   SYNTAX         DisplayString
   MAX-ACCESS     read-only
   STATUS         current
   DESCRIPTION
      "UTF-8 string of the AC name."
   ::= { alPPPoEStatsIfEntry 16 }

alPPPoEStatsIfACCookie     OBJECT-TYPE
   SYNTAX         OCTET STRING (SIZE(0..64))
   MAX-ACCESS     read-only
   STATUS         current
   DESCRIPTION
      "Binary sequence representing the AC cookie given in 
       negotiations."
   ::= { alPPPoEStatsIfEntry 17 }

alPPPoEStatsIfHostUnique   OBJECT-TYPE
   SYNTAX         OCTET STRING (SIZE(4))
   MAX-ACCESS     read-only
   STATUS         current
   DESCRIPTION
      "Binary sequence representing the value we assigned the PADI."
   ::= { alPPPoEStatsIfEntry 18 }

alPPPoEStatsIfRelaySessID  OBJECT-TYPE
   SYNTAX         OCTET STRING (SIZE(2))
   MAX-ACCESS     read-only
   STATUS         current
   DESCRIPTION
      "12 octets representing the Relay session if one exists."
   ::= { alPPPoEStatsIfEntry 19 }

altigaPPPoEStatsMibConformance OBJECT IDENTIFIER ::= { altigaPPPoEStatsMibModule 1 }
altigaPPPoEStatsMibCompliances OBJECT IDENTIFIER ::= { altigaPPPoEStatsMibConformance 1 }

altigaPPPoEStatsMibCompliance MODULE-COMPLIANCE
   STATUS         current
   DESCRIPTION
      "The compliance statement for agents which 
       implement the Altiga PPPoE Statistics MIB."
   MODULE
   MANDATORY-GROUPS { 
      altigaPPPoEStatsGroup
   }
   ::= { altigaPPPoEStatsMibCompliances 1 }

altigaPPPoEStatsGroup      OBJECT-GROUP
   OBJECTS
   {
      alPPPoEStatsActiveSessions,
      alPPPoEStatsTotalSessions,
      alPPPoEStatsMaxSessions,
      alPPPoEStatsIfIndex,
      alPPPoEStatsIfPADTRx,
      alPPPoEStatsIfPADTTx,
      alPPPoEStatsIfGenericErrorsRx,
      alPPPoEStatsIfMalformedPacketsRx,
      alPPPoEStatsIfPADITimeouts,
      alPPPoEStatsIfPADRTimeouts,
      alPPPoEStatsIfMultPADORx,
      alPPPoEStatsIfSessionID,
      alPPPoEStatsIfPeerAddr,
      alPPPoEStatsIfSessionState,
      alPPPoEStatsIfVersion,
      alPPPoEStatsIfType,
      alPPPoEStatsIfConnectTime,
      alPPPoEStatsIfDuration,
      alPPPoEStatsIfPeerName,
      alPPPoEStatsIfACCookie,
      alPPPoEStatsIfHostUnique,
      alPPPoEStatsIfRelaySessID
   }
   STATUS         current
   DESCRIPTION
      "The objects for PPPoE Statistics."
   ::= { alPPPoEGroup 2 }

END
