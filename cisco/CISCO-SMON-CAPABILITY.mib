CISCO-SMON-CAPABILITY DEFINITIONS ::= BEGIN

IMPORTS
        MODULE-IDENTITY
                FROM SNMPv2-SMI
        AGENT-CAPABILITIES
                FROM SNMPv2-CONF
        ciscoAgentCapability
                FROM CISCO-SMI;

ciscoSmonCapability MODULE-IDENTITY
        LAST-UPDATED    "200401220000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "Agent capabilities for SMON-MIB."

        REVISION        "200401220000Z"
        DESCRIPTION
                "Initial version of this MIB module."
        ::= { ciscoAgentCapability 381 }

csCapV12R0214SXCat6KPfc3 AGENT-CAPABILITIES
    PRODUCT-RELEASE     "Cisco IOS 12.2(14)SX on Catalyst 6000/6500
                         and Cisco 7600 series devices with the 
                         Policy Feature Card 3 (PFC 3)."
    STATUS              current
    DESCRIPTION         "SMON-MIB agent capabilities."

    SUPPORTS            SMON-MIB
        INCLUDES        { dataSourceCapsGroup,
                          smonVlanStatsGroup,
                          hcVlanTo100mbGroup,
                          hcVlan100mbPlusGroup,
                          smonVlanStatsExtGroup,
                          smonInformationGroup,
                          portCopyConfigGroup     
                        }

        VARIATION       smonVlanStatsControlDataSource
            ACCESS      read-only
            DESCRIPTION "Supports VLAN-based data sources only."

        VARIATION       smonVlanStatsControlOwner
            ACCESS      read-only
            DESCRIPTION "Always returns 'monitor'."

        VARIATION       smonVlanStatsControlStatus
            SYNTAX      INTEGER {
                            active(1)
                        }
            ACCESS      read-only
            DESCRIPTION "Only supports active(1)."
    ::= { ciscoSmonCapability 1 }

csCapV12R0113ECat6KPfc2 AGENT-CAPABILITIES
    PRODUCT-RELEASE     "Cisco IOS 12.1(13)E on Catalyst 6000/6500
                         and Cisco 7600 series devices with the 
                         Policy Feature Card 2 (PFC 2)."
    STATUS              current
    DESCRIPTION         "SMON-MIB agent capabilities."

    SUPPORTS            SMON-MIB
        INCLUDES        { dataSourceCapsGroup,
                          smonVlanStatsGroup,
                          hcVlanTo100mbGroup,
                          hcVlan100mbPlusGroup,
                          smonVlanStatsExtGroup,
                          smonInformationGroup,
                          portCopyConfigGroup     
                        }

        VARIATION       smonVlanStatsControlDataSource
            ACCESS      read-only
            DESCRIPTION "Supports VLAN-based data sources only."

        VARIATION       smonVlanStatsControlOwner
            ACCESS      read-only
            DESCRIPTION "Always returns 'monitor'."

        VARIATION       smonVlanStatsControlStatus
            SYNTAX      INTEGER {
                            active(1)
                        }
            ACCESS      read-only
            DESCRIPTION "Only supports active(1)."
    ::= { ciscoSmonCapability 2 }

csCapCatOSV07R0102Cat6KPfc2 AGENT-CAPABILITIES
    PRODUCT-RELEASE     "Cisco CatOS 7.1(2) on Catalyst 6000/6500
                         and Cisco 7600 series devices with the 
                         Policy Feature Card 2 (PFC 2)."
    STATUS              current
    DESCRIPTION         "SMON-MIB agent capabilities."

    SUPPORTS            SMON-MIB
        INCLUDES        { dataSourceCapsGroup,
                          smonVlanStatsGroup,      
                          hcVlanTo100mbGroup,        
                          hcVlan100mbPlusGroup,      
                          smonVlanStatsExtGroup,   
                          smonInformationGroup,
                          portCopyConfigGroup
                        }

        VARIATION       smonVlanStatsControlDataSource
            ACCESS      read-only
            DESCRIPTION "Supports VLAN-based data sources only."

        VARIATION       smonVlanStatsControlOwner
            ACCESS      read-only
            DESCRIPTION "Always returns 'monitor'."

        VARIATION       smonVlanStatsControlStatus
            SYNTAX      INTEGER {
                            active(1)
                        }
            ACCESS      read-only
            DESCRIPTION "Only supports active(1)."
    ::= { ciscoSmonCapability 3 }
END
