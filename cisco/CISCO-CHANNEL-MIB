CISCO-CHANNEL-MIB DEFINITIONS ::= BEGIN

IMPORTS
    MODULE-IDENTITY, OBJECT-TYPE, NOTIFICATION-TYPE,
    Counter32,
    Counter64,
    Integer32,
    IpAddress,
    TimeTicks
        FROM SNMPv2-SMI
    DisplayString, TruthValue, TimeStamp, RowStatus
        FROM SNMPv2-TC
    MODULE-COMPLIANCE, OBJECT-GROUP
      FROM SNMPv2-CONF
    ciscoMgmt
	FROM CISCO-SMI
;

channel MODULE-IDENTITY
        LAST-UPDATED  "9703260000Z"
        ORGANIZATION  "cisco IBM engineering Working Group"
	CONTACT-INFO
		"	
			Cisco Systems
				Customer Service

			Postal:	170 West Tasman Drive
				San Jose, CA  95134
				USA

			   Tel:	+1 800 553-NETS

			E-mail:	tac@cisco.com"
	DESCRIPTION
		"This is the MIB module for objects used to manage
                 the Cisco Mainframe Channel Connection (CMCC) cards."

	REVISION        "9801060000Z"
	DESCRIPTION
		"With the addition of Cisco's new Channel Port
                 Adapter cards, all the references to CIP in the
                 MIB description and object descriptions are changed
                 to CMCC (Cisco Mainframe Channel Connection). The
                 object names in the form of cip... or cipCard...
                 will remain the same, but will be valid objects
                 for the Channel Port Adapter cards."

	REVISION        "9808140000Z"
	DESCRIPTION
		"Added cipCardSubChannelResetEvent to cipCardSubChannelTable
		 Added cipCardSubChannelShortBusy to cipCardSubChannelTable
		 Added cipCardSubChannelCMDRetry to cipCardSubChannelTable
		 Added cipCardSubChannelBufferWait to cipCardSubChannelTable
		 Added cipCardSubChannelStatPending to cipCardSubChannelTable
		 Added cipCardSubChannelSuspend to cipCardSubChannelTable
		 Added cipCardSubChannelFBLWait to cipCardSubChannelTable"

	REVISION        "9703260000Z"
	DESCRIPTION
		"Added cipCardEntryCpuLoad1m to cipCardTable
                 Added cipCardEntryCpuLoad5m to cipCardTable
                 Added cipCardEntryCpuLoad60m to cipCardTable
                 Added cipCardEntryDmaLoad1m to cipCardTable
                 Added cipCardEntryDmaLoad5m to cipCardTable
                 Added cipCardEntryDmaLoad60m to cipCardTable
                 Added cipCardDtrBrdChannelLoad1m to cipCardDaughterBoardTable
                 Added cipCardDtrBrdChannelLoad5m to cipCardDaughterBoardTable
                 Added cipCardDtrBrdChannelLoad60m to cipCardDaughterBoardTable
                 Added cipCardClawConfigBroadcastEnable to cipCardClawConfigTable
                 Added cipCardClawConfigRowStatus to cipCardClawConfigTable
                 Enhanced the description for cipCardEntryCpuUtilization"

        REVISION        "9606130000Z"
	DESCRIPTION
		"Add cipCardSubChannelCmdRetries to cipCardSubChannelTable
                 Add cipCardDtrBrdLastStat and cipCardDtrBrdNextStat
                 to cipCardDaughterBoardTable."

        REVISION	"9509250000Z"
 	DESCRIPTION
 		"Added cipCardApplicationTable.
                 Added conformance section.
                 Added cipCardEntryMajorSwRevisionNr,
                       cipCardEntryMinorSwRevisionNr,
                       cipCardEntryMajorHwRevisionNr and
                       cipCardEntryMinorHwRevisionNr to cipCardTable.
                 Enhanced the description for 
                   cipCardSubChannelIndex,
                   cipCardClawConfigPath,
                   cipCardClawConfigDevice, 
                   cipCardClawConfigIpAddr"

        REVISION	"9411170000Z"
 	DESCRIPTION
 		"Changed from CHANNEL-MIB to CISCO-CHANNEL-MIB."
	::= { ciscoMgmt 20 }

cipCard   OBJECT IDENTIFIER ::= { channel 1 }

cipCardTable        OBJECT-TYPE
                    SYNTAX      SEQUENCE OF CipCardEntry
                    MAX-ACCESS  not-accessible
                    STATUS      current
                    DESCRIPTION
                        "This table contains a list of values for the
                         CMCC card which can be accessed to 
                         determine the general state of the CMCC.

                         This table extends CardTable in the cisco.mib"
                    ::= {cipCard 1}

cipCardEntry        OBJECT-TYPE
                    SYNTAX      CipCardEntry
                    MAX-ACCESS  not-accessible
                    STATUS      current
                    DESCRIPTION
                        "A list of values for a CMCC Card. 

                         This extends cardTableEntry in the cisco.mib"
                    INDEX   { cipCardEntryIndex }
                    ::= { cipCardTable 1 }

CipCardEntry        ::= SEQUENCE
{
	cipCardEntryIndex              Integer32 (0..2147483647),
        cipCardEntryName               DisplayString (SIZE (1..32)),
        cipCardEntryTotalMemory        Integer32,
        cipCardEntryFreeMemory         Integer32,
        cipCardEntryCpuUtilization     INTEGER,
        cipCardEntryTimeSinceLastReset Counter32,
        cipCardEntryMajorSwRevisionNr  Integer32,
        cipCardEntryMinorSwRevisionNr  Integer32,
        cipCardEntryMajorHwRevisionNr  Integer32,
        cipCardEntryMinorHwRevisionNr  Integer32,
        cipCardEntryCpuLoad1m          INTEGER,
        cipCardEntryCpuLoad5m          INTEGER,
        cipCardEntryCpuLoad60m         INTEGER,
        cipCardEntryDmaLoad1m          INTEGER,
        cipCardEntryDmaLoad5m          INTEGER,
        cipCardEntryDmaLoad60m         INTEGER
}

cipCardEntryIndex   OBJECT-TYPE
                    SYNTAX      Integer32 (0..2147483647)
                    MAX-ACCESS  not-accessible
                    STATUS      current
                    DESCRIPTION
                           "Index into cardTable (not physical chassis
                           slot number, matches cisco chassis MIB cardindex)."
                    ::= { cipCardEntry 1 }

cipCardEntryName    OBJECT-TYPE
                    SYNTAX      DisplayString(SIZE (1..32))
                    MAX-ACCESS  read-write
                    STATUS      current
                    DESCRIPTION
                        "The configured name for the CMCC."
                    ::= {cipCardEntry 2}

cipCardEntryTotalMemory
                    OBJECT-TYPE
                    SYNTAX      Integer32
                    UNITS       "kilo bytes"
                    MAX-ACCESS  read-only
                    STATUS      current
                    DESCRIPTION
                        "Total memory on the card."
                    ::= {cipCardEntry 3}

cipCardEntryFreeMemory
                    OBJECT-TYPE
                    SYNTAX      Integer32
                    UNITS       "kilo bytes"
                    MAX-ACCESS  read-only
                    STATUS      current
                    DESCRIPTION
                        "Total free memory on the card, that is the
                         amount of memory not in use."
                    ::= {cipCardEntry 4}

cipCardEntryCpuUtilization
                    OBJECT-TYPE
                    SYNTAX      INTEGER (0..100)
                    MAX-ACCESS  read-only
                    STATUS      current
                    DESCRIPTION
                        "The average, over the last minute, of the
                         percentage of time that this processor was
                         running.  This includes time spent on 
                         non-productive polling and time used by
                         routine maintenance tasks.  This value is 
                         not a measure of the processor's ability 
                         to handle more work, which is represented
                         by the cipCardEntryCpuLoad information.  The
                         ability to handle more work could also be 
                         affected by DMA and channel load, represented
                         by the cipCardEntryDmaLoad and cipCardDtrBrd-
                         ChannelAdapterLoad statistics."
                    ::= {cipCardEntry 5}

cipCardEntryTimeSinceLastReset
                    OBJECT-TYPE
                    SYNTAX      Counter32
                    UNITS       "seconds"
                    MAX-ACCESS  read-only
                    STATUS      current
                    DESCRIPTION
                        "The amount of time the CMCC card has been running."
                    ::= {cipCardEntry 6}

cipCardEntryMajorSwRevisionNr
                    OBJECT-TYPE
                    SYNTAX      Integer32
                    MAX-ACCESS  read-only
                    STATUS      current
                    DESCRIPTION
                        "The major software revision number for the software
                         loaded on the CMCC card."
                    ::= {cipCardEntry 7}

cipCardEntryMinorSwRevisionNr
                    OBJECT-TYPE
                    SYNTAX      Integer32
                    MAX-ACCESS  read-only
                    STATUS      current
                    DESCRIPTION
                        "The minor software revision number for the software
                         loaded on the CMCC card."
                    ::= {cipCardEntry 8}

cipCardEntryMajorHwRevisionNr
                    OBJECT-TYPE
                    SYNTAX      Integer32
                    MAX-ACCESS  read-only
                    STATUS      current
                    DESCRIPTION
                        "The major hardware revision number for the software
                         loaded on the CMCC card."
                    ::= {cipCardEntry 9}

cipCardEntryMinorHwRevisionNr
                    OBJECT-TYPE
                    SYNTAX      Integer32
                    MAX-ACCESS  read-only
                    STATUS      current
                    DESCRIPTION
                        "The minor hardware revision number for the software
                         loaded on the CMCC card."
                    ::= {cipCardEntry 10}

cipCardEntryCpuLoad1m
                    OBJECT-TYPE
                    SYNTAX      INTEGER (0..100)
                    UNITS       "percent"
                    MAX-ACCESS  read-only
                    STATUS      current
                    DESCRIPTION
                        "The average, over the last minute, of the
                       	 percentage of time that this processor was
                         utilized to transfer data. It does not include
                         idle time or time used by routine maintenance
                         tasks."
                    ::= {cipCardEntry 11}

cipCardEntryCpuLoad5m
                    OBJECT-TYPE
                    SYNTAX      INTEGER (0..100)
                    UNITS       "percent"
                    MAX-ACCESS  read-only
                    STATUS      current
                    DESCRIPTION
                        "The average, over the last 5 minutes, of the
                       	 percentage of time that this processor was
                         utilized to transfer data. It does not include
                         idle time or time used by routine maintenance
                         tasks."
                    ::= {cipCardEntry 12}

cipCardEntryCpuLoad60m
                    OBJECT-TYPE
                    SYNTAX      INTEGER (0..100)
                    UNITS       "percent"
                    MAX-ACCESS  read-only
                    STATUS      current
                    DESCRIPTION
                        "The average, over the last 60 minutes, of the
                       	 percentage of time that this processor was
                         utilized to transfer data. It does not include
                         idle time or time used by routine maintenance
                         tasks."
                    ::= {cipCardEntry 13}

cipCardEntryDmaLoad1m
                    OBJECT-TYPE
                    SYNTAX      INTEGER (0..100)
                    UNITS       "percent"
                    MAX-ACCESS  read-only
                    STATUS      current
                    DESCRIPTION
                        "The average, over the last minute, of the
                         percentage of time the DMA controller was
                         being used to transfer data between the CMCC
                         card and the route processor."
                    ::= {cipCardEntry 14}

cipCardEntryDmaLoad5m
                    OBJECT-TYPE
                    SYNTAX      INTEGER (0..100)
                    UNITS       "percent"
                    MAX-ACCESS  read-only
                    STATUS      current
                    DESCRIPTION
                        "The average, over the last 5 minutes, of the
                         percentage of time the DMA controller was
                         being used to transfer data between the CMCC
                         card and the route processor."
                    ::= {cipCardEntry 15}

cipCardEntryDmaLoad60m
                    OBJECT-TYPE
                    SYNTAX      INTEGER (0..100)
                    UNITS       "percent"
                    MAX-ACCESS  read-only
                    STATUS      current
                    DESCRIPTION
                        "The average, over the last 60 minutes, of the
                         percentage of time the DMA controller was
                         being used to transfer data between the CMCC
                         card and the route processor."
                    ::= {cipCardEntry 16}

-- ;;;;;;;;;;;;;;;;;;;;;;; cipCardApplicationTable ;;;;;;;;;;;;;;;;;;;;;;;;;
cipCardApplicationTable
                    OBJECT-TYPE 
                    SYNTAX      SEQUENCE OF CipCardApplicationEntry
                    MAX-ACCESS  not-accessible
                    STATUS      current
                    DESCRIPTION
                        "This table contains information on the applications
                         loaded on the CMCC card."
                    ::= {cipCard 6}

cipCardApplicationEntry
                    OBJECT-TYPE
                    SYNTAX      CipCardApplicationEntry
                    MAX-ACCESS  not-accessible
                    STATUS      current
                    DESCRIPTION
                        "A list of application information."
                    INDEX   { cipCardEntryIndex,
                              cipCardApplicationNameIndex
                            }
                    ::= { cipCardApplicationTable 1 }

CipCardApplicationEntry ::= SEQUENCE
{
        cipCardApplicationNameIndex    DisplayString (SIZE (32)),
        cipCardApplicationRevision     Integer32,
        cipCardApplicationCompileInfo  DisplayString (SIZE (1..64))
}

cipCardApplicationNameIndex
                    OBJECT-TYPE
                    SYNTAX      DisplayString(SIZE (32))
                    MAX-ACCESS  not-accessible
                    STATUS      current
                    DESCRIPTION
                        "The application name."
                    ::= {cipCardApplicationEntry 1}

cipCardApplicationRevision
                    OBJECT-TYPE
                    SYNTAX      Integer32
                    MAX-ACCESS  read-only
                    STATUS      current
                    DESCRIPTION
                        "The application's software revision number."
                    ::= {cipCardApplicationEntry 2}

cipCardApplicationCompileInfo
                    OBJECT-TYPE
                    SYNTAX      DisplayString(SIZE (1..64))
                    MAX-ACCESS  read-only
                    STATUS      current
                    DESCRIPTION
                        "The application's compilation information 
                         (date and user-id)"
                    ::= {cipCardApplicationEntry 3}

-- ;;;;;;;;;;;;;;;;;;;;;;; cipCardDaughterBoardTable ;;;;;;;;;;;;;;;;;;;;;;;;;

cipCardDaughterBoardTable
                    OBJECT-TYPE 
                    SYNTAX      SEQUENCE OF CipCardDaughterBoardEntry
                    MAX-ACCESS  not-accessible
                    STATUS      current
                    DESCRIPTION
                        "This table contains a list of objects pertaining to
                         the daughter board on the CMCC card."
                    ::= {cipCard 2}

cipCardDaughterBoardEntry
                    OBJECT-TYPE
                    SYNTAX      CipCardDaughterBoardEntry
                    MAX-ACCESS  not-accessible
                    STATUS      current
                    DESCRIPTION
                        "A list of daughter board values."
                    INDEX   { cipCardEntryIndex,
                              cipCardDtrBrdIndex }
                    ::= { cipCardDaughterBoardTable 1 }

CipCardDaughterBoardEntry ::= SEQUENCE
{
        cipCardDtrBrdIndex                Integer32 (0..2147483647),
        cipCardDtrBrdType                 INTEGER,
        cipCardDtrBrdStatus               TruthValue,
        cipCardDtrBrdSignal               TruthValue,
        cipCardDtrBrdOnline               TruthValue,
        implicitIncidents                 Counter32,
        codeViolationErrors               Counter32,
        linkFailureSignalOrSyncLoss       Counter32,
        linkFailureNOSs                   Counter32,
        linkFailureSequenceTimeouts       Counter32,
        linkFailureInvalidSequences       Counter32,
        linkIncidentTrapCause             INTEGER,
        cipCardDtrBrdLastStat             TimeTicks,
        cipCardDtrBrdNextStat             TimeTicks,
        cipCardDtrBrdChannelLoad1m        INTEGER,
        cipCardDtrBrdChannelLoad5m        INTEGER,
        cipCardDtrBrdChannelLoad60m       INTEGER
}

cipCardDtrBrdIndex  OBJECT-TYPE
                    SYNTAX      Integer32 (0..2147483647)
                    MAX-ACCESS  not-accessible
                    STATUS      current
                    DESCRIPTION
                        "This indicates which daughter board is
                         is being referenced for a particular CMCC card."
                    ::= {cipCardDaughterBoardEntry 1}

cipCardDtrBrdType   OBJECT-TYPE
                    SYNTAX      INTEGER
                    {
                      escon       (1),  -- Enterprise System Connection
                      busAndTag   (2)
                    }
                    MAX-ACCESS  read-only
                    STATUS      current
                    DESCRIPTION
                        "This indicates the channel path interface type."
                    ::= {cipCardDaughterBoardEntry 2}

cipCardDtrBrdStatus OBJECT-TYPE
                    SYNTAX      TruthValue 
                    MAX-ACCESS  read-only
                    STATUS      current
                    DESCRIPTION
                        "cipCardDtrBrdStatus is true when the
                         microcode for the daughter board has been
                         successfully loaded and is executing, false
                         otherwise."
                    ::= {cipCardDaughterBoardEntry 3}

cipCardDtrBrdSignal OBJECT-TYPE
                    SYNTAX      TruthValue
                    MAX-ACCESS  read-only
                    STATUS      current
                    DESCRIPTION
                        "For ESCON, cipCardDtrBrdSignal is true when 
                         light has been seen on the fiber and synchronization 
                         has been established, false otherwise.

                         For the Parallel Channel Adapter (PCA) which provides
                         the Bus and Tag connection, cipCardDtrBrdSignal is 
                         true when Operational out has been sensed, false 
                         otherwise."
                    ::= {cipCardDaughterBoardEntry 4}

cipCardDtrBrdOnline OBJECT-TYPE
                    SYNTAX      TruthValue
                    MAX-ACCESS  read-only
                    STATUS      current
                    DESCRIPTION
                        "For ESCON, cipCardDtrBrdOnline is true when a path 
                         has been established with at least one channel,
                         false otherwise.

                         For PCA, cipCardDtrBrdOnline is true when the PCA
                         is online to the channel. It will respond to at
                         least one device address"
                    ::= {cipCardDaughterBoardEntry 5}

implicitIncidents   OBJECT-TYPE
                    SYNTAX      Counter32
                    MAX-ACCESS  read-only
                    STATUS      current
                    DESCRIPTION
                        "This counts the number of times the ESCON Processor
                         recovers from an internal error."
                    ::= {cipCardDaughterBoardEntry 6}

codeViolationErrors OBJECT-TYPE
                    SYNTAX      Counter32
                    MAX-ACCESS  read-only
                    STATUS      current
                    DESCRIPTION
                        "The number of recognized code-violation errors.
                         A trap is issued when this number exceeds the bit
                         error rate threshold for ESCON. The bit 
                         error rate threshold is set at 15 error burst 
                         within a 5 minute period. An error burst is the
                         time period of 1.5 seconds plus or minus 0.05 
                         seconds during which one or more code violations
                         errors occur."
                    ::= {cipCardDaughterBoardEntry 7}

linkFailureSignalOrSyncLoss
                    OBJECT-TYPE
                    SYNTAX      Counter32
                    MAX-ACCESS  read-only
                    STATUS      current
                    DESCRIPTION
                        "The number of link failures recognized as a
                         result of a loss of signal or loss of 
                         synchronization that persisted longer than the
                         link interval duration, the link interval 
                         duration is one second with a tolerance of +1.5
                         seconds and -0 seconds."
                    ::= {cipCardDaughterBoardEntry 8}

linkFailureNOSs     OBJECT-TYPE
                    SYNTAX      Counter32
                    MAX-ACCESS  read-only
                    STATUS      current
                    DESCRIPTION
                        "The number of link failures recognized as a result of
                         the not-operational sequence (NOS)."
                    ::= {cipCardDaughterBoardEntry 9}

linkFailureSequenceTimeouts
                    OBJECT-TYPE
                    SYNTAX      Counter32
                    MAX-ACCESS  read-only
                    STATUS      current
                    DESCRIPTION
                        "The number of link failures recognized as a result of
                         a connection recovery timeout or response timeout 
                         occurring while in transmit OLS state."
                    ::= {cipCardDaughterBoardEntry 10}

linkFailureInvalidSequences
                    OBJECT-TYPE
                    SYNTAX      Counter32
                    MAX-ACCESS  read-only
                    STATUS      current
                    DESCRIPTION
                        "The number of link failures recognized as a result of
                         an invalid sequence for Link-Level-Facility State.
                         Either a UD or UDR sequence was recognized while in
                         wait-for-offline-sequence state."
                    ::= {cipCardDaughterBoardEntry 11}

linkIncidentTrapCause
                    OBJECT-TYPE
                    SYNTAX      INTEGER
                    {
                      liOther (1),
                      liStatus (2),
                      liImplicitIncidents (3),
                      liBERthreshold (4),
                      liSignalOrSyncLoss (5),
                      liNotOperationalSequence (6),
                      liSequenceTimeouts (7),
                      liInvalidSequences (8)
                    }
                    MAX-ACCESS  read-only
                    STATUS      current
                    DESCRIPTION
                        "This indicates the reason for the last link
                         failure.

                         liStatus indicates that the daughter board status
                         has changed.

                         liImplicitIncident indicates that a condition which
                         may cause the recognition of a link incident in the
                         attached node has been recognized.

                         liBERthreshold indicates that the code violation
                         error rate exceeded the threshold. 

                         liSignalOrSyncLoss indicates a loss of signal or 
                         loss of synchronization that persisted longer 
                         than the link interval duration.

                         liNotOperationalSequence indicates the recognition
                         of not-operational sequence, usually due to the
                         operator taking the channel offline.

                         liSequenceTimeout indicates a connection recovery
                         timeout or response timeout occurring while in
                         transmit OLS state.

                         linvalidSequence indicates a UD or UDR sequence was
                         recognized while in wait-for-offline-sequence state.
                        "
                    ::= {cipCardDaughterBoardEntry 12}

cipCardDtrBrdLastStat
                    OBJECT-TYPE
                    SYNTAX      TimeTicks
                    MAX-ACCESS  read-only
                    STATUS      current
                    DESCRIPTION
                        "This object indicates how old the statistics are."
                    ::= {cipCardDaughterBoardEntry 13}

cipCardDtrBrdNextStat
                    OBJECT-TYPE
                    SYNTAX      TimeTicks
                    MAX-ACCESS  read-only
                    STATUS      current
                    DESCRIPTION
                        "This object indicates when statistics will next
                         be read."
                    ::= {cipCardDaughterBoardEntry 14}

cipCardDtrBrdChannelLoad1m
                    OBJECT-TYPE
                    SYNTAX      INTEGER (0..100)
                    UNITS       "percent"
                    MAX-ACCESS  read-only
                    STATUS      current
                    DESCRIPTION
                        "The average, over the last minute, of the
                         percentage of time the channel adapter was
                         busy communicating to a host."
                    ::= {cipCardDaughterBoardEntry 15}                    

cipCardDtrBrdChannelLoad5m
                    OBJECT-TYPE
                    SYNTAX      INTEGER (0..100)
                    UNITS       "percent"
                    MAX-ACCESS  read-only
                    STATUS      current
                    DESCRIPTION
                        "The average, over the last 5 minutes, of the
                         percentage of time the channel adapter was
                         busy communicating to a host."
                    ::= {cipCardDaughterBoardEntry 16} 

cipCardDtrBrdChannelLoad60m
                    OBJECT-TYPE
                    SYNTAX      INTEGER (0..100)
                    UNITS       "percent"
                    MAX-ACCESS  read-only
                    STATUS      current
                    DESCRIPTION
                        "The average, over the last 60 minutes, of the
                         percentage of time the channel adapter was
                         busy communicating to a host."
                    ::= {cipCardDaughterBoardEntry 17}

-- ;;;;;;;;;;;;;;;;;;;;;;;;;;; cipCardSubChannelTable ;;;;;;;;;;;;;;;;;;;;

cipCardSubChannelTable
                    OBJECT-TYPE 
                    SYNTAX      SEQUENCE OF CipCardSubChannelEntry
                    MAX-ACCESS  not-accessible
                    STATUS      current
                    DESCRIPTION
                        "This table contains a list of objects pertaining to
                         each host connection."
                    ::= {cipCard 3}

cipCardSubChannelEntry
                    OBJECT-TYPE
                    SYNTAX      CipCardSubChannelEntry
                    MAX-ACCESS  not-accessible
                    STATUS      current
                    DESCRIPTION
                        "A list of host connection statistics."
                    INDEX   { cipCardEntryIndex,
                              cipCardDtrBrdIndex,
                              cipCardSubChannelIndex
                            }
                    ::= { cipCardSubChannelTable 1 }

CipCardSubChannelEntry ::= SEQUENCE
{
        cipCardSubChannelIndex              Integer32 (0..2147483647),
        cipCardSubChannelConnections        Counter32,
        cipCardSubChannelCancels            Counter32,
        cipCardSubChannelSelectiveResets    Counter32,
        cipCardSubChannelSystemResets       Counter32,
        cipCardSubChannelDeviceErrors       Counter32,
        cipCardSubChannelWriteBlocksDropped Counter32,
        cipCardSubChannelLastSenseData      OCTET STRING (SIZE (2)),
        cipCardSubChannelLastSenseDataTime  TimeStamp,
        cipCardSubChannelCuBusies           Counter32,
        cipCardSubChannelCmdRetries         Counter32,
        cipCardSubChannelResetEvent         TruthValue,
        cipCardSubChannelShortBusy          TruthValue,
        cipCardSubChannelCMDRetry           TruthValue,
        cipCardSubChannelBufferWait         TruthValue,
        cipCardSubChannelStatPending        TruthValue,
        cipCardSubChannelSuspend            TruthValue,
        cipCardSubChannelFBLWait            TruthValue
}

cipCardSubChannelIndex     OBJECT-TYPE
                    SYNTAX      Integer32 (0..2147483647)
                    MAX-ACCESS  read-only
                    STATUS      current
                    DESCRIPTION
                        "This indicates which subchannel is being referenced
                         for a particular daughter board on a CMCC card.
                         This value is constructed as follows:
                           path * 256 + device
                         Path and device are the values in 
                         CipCardClawConfigTable."
                    ::= {cipCardSubChannelEntry 1}

cipCardSubChannelConnections
                    OBJECT-TYPE
                    SYNTAX      Counter32
                    MAX-ACCESS  read-only
                    STATUS      current
                    DESCRIPTION
                        "Number of times a device was connected to the
                         subchannel. For some devices, this correlates with
                         the number of start subchannels."
                    ::= {cipCardSubChannelEntry 2}

cipCardSubChannelCancels   OBJECT-TYPE
                    SYNTAX      Counter32
                    MAX-ACCESS  read-only
                    STATUS      current
                    DESCRIPTION
                        "Number of halt subchannels."
                    ::= {cipCardSubChannelEntry 3}

cipCardSubChannelSelectiveResets
                    OBJECT-TYPE
                    SYNTAX      Counter32
                    MAX-ACCESS  read-only
                    STATUS      current
                    DESCRIPTION
                        "Number of selective resets."
                    ::= {cipCardSubChannelEntry 4}

cipCardSubChannelSystemResets
                    OBJECT-TYPE
                    SYNTAX      Counter32
                    MAX-ACCESS  read-only
                    STATUS      current
                    DESCRIPTION
                        "Number of system resets."
                    ::= {cipCardSubChannelEntry 5}

cipCardSubChannelDeviceErrors
                    OBJECT-TYPE
                    SYNTAX      Counter32
                    MAX-ACCESS  read-only
                    STATUS      current
                    DESCRIPTION
                        "Number of device level errors."
                    ::= {cipCardSubChannelEntry 6}

cipCardSubChannelWriteBlocksDropped
                    OBJECT-TYPE
                    SYNTAX      Counter32
                    MAX-ACCESS  read-only
                    STATUS      current
                    DESCRIPTION
                        "Number of times a block was received by the channel
                         and a router buffer was not available so the block 
                         was discarded."
                    ::= {cipCardSubChannelEntry 7}

cipCardSubChannelLastSenseData
                    OBJECT-TYPE
                    SYNTAX      OCTET STRING (SIZE (2))
                    MAX-ACCESS  read-only
                    STATUS      current
                    DESCRIPTION
                        "This is the last sense data sent to the channel 
                         by this device."
                    ::= {cipCardSubChannelEntry 8}

cipCardSubChannelLastSenseDataTime
                    OBJECT-TYPE
                    SYNTAX      TimeStamp
                    MAX-ACCESS  read-only
                    STATUS      current
                    DESCRIPTION
                        "This indicates the time when the last sense data
                         was sent to the channel by this device."
                    ::= {cipCardSubChannelEntry 9}

cipCardSubChannelCuBusies  OBJECT-TYPE
                    SYNTAX      Counter32
                    MAX-ACCESS  read-only
                    STATUS      current
                    DESCRIPTION
                        "This is the number of control unit busies sent to the
                         channel when this device was requested."
                    ::= {cipCardSubChannelEntry 10}

cipCardSubChannelCmdRetries
                    OBJECT-TYPE
                    SYNTAX      Counter32
                    MAX-ACCESS  read-only
                    STATUS      current
                    DESCRIPTION
                        "Number of times the subchannel went into command
                         retry state. The sum of this value and 
                         cipCardSubChannelConnections gives
                         the number of start subchannels."
                    ::= {cipCardSubChannelEntry 11}

cipCardSubChannelResetEvent
                    OBJECT-TYPE
                    SYNTAX      TruthValue
                    MAX-ACCESS  read-only
                    STATUS      current
                    DESCRIPTION
                        "A state that a device gets into after a system reset 
                         and is cleared by a resetting event unit check."
                    ::= {cipCardSubChannelEntry 12}

cipCardSubChannelShortBusy
                    OBJECT-TYPE
                    SYNTAX      TruthValue
                    MAX-ACCESS  read-only
                    STATUS      current
                    DESCRIPTION
                        "A transient state that a device can get into during 
                         processing of various resets."
                    ::= {cipCardSubChannelEntry 13}

cipCardSubChannelCMDRetry
                    OBJECT-TYPE
                    SYNTAX      TruthValue
                    MAX-ACCESS  read-only
                    STATUS      current
                    DESCRIPTION
                        "A state that a device can get into if the mainframe
                         tries to write data to the CMCC when the CMCC has no 
                         buffers for it or if the mainframe performs a read 
                         operation and the CMCC doesn't have any data to send."
                    ::= {cipCardSubChannelEntry 14}

cipCardSubChannelBufferWait
                    OBJECT-TYPE
                    SYNTAX      TruthValue
                    MAX-ACCESS  read-only
                    STATUS      current
                    DESCRIPTION
                        "A state that a device can get into when the mainframe
                         tries to write data to the CMCC and the CMCC has no 
                         buffers for all of the write operation."
                    ::= {cipCardSubChannelEntry 15}

cipCardSubChannelStatPending
                    OBJECT-TYPE
                    SYNTAX      TruthValue
                    MAX-ACCESS  read-only
                    STATUS      current
                    DESCRIPTION
                        "Indicates that the CMCC has status to present for a 
                         particular device.  The indication is cleared when the 
                         mainframe excepts the status."
                    ::= {cipCardSubChannelEntry 16}

cipCardSubChannelSuspend
                    OBJECT-TYPE
                    SYNTAX      TruthValue
                    MAX-ACCESS  read-only
                    STATUS      current
                    DESCRIPTION
                        "Indicates that the device task has decided to suspend data 
                         transfer for a particular device."
                    ::= {cipCardSubChannelEntry 17}

cipCardSubChannelFBLWait
                    OBJECT-TYPE
                    SYNTAX      TruthValue
                    MAX-ACCESS  read-only
                    STATUS      current
                    DESCRIPTION
                        "A state that a device can get into when the mainframe
                         tries to write data to the CMCC and the CMCC has no buffers
                         for all of the write operation."
                    ::= {cipCardSubChannelEntry 18}

-- ;;;;;;;;;;;;;;;;;;;;; Claw Related objects ;;;;;;;;;;;;;;;;;;;;;;;;;;;

cipCardClaw   OBJECT IDENTIFIER ::= {cipCard 4}

-- ;;;;;;;;;;;;;;;;;;;;; cipCardClawTable ;;;;;;;;;;;;;;;;;;;;;;;;;;;

cipCardClawTable    OBJECT-TYPE 
                    SYNTAX      SEQUENCE OF CipCardClawEntry
                    MAX-ACCESS  not-accessible
                    STATUS      current
                    DESCRIPTION
                        "This table contains status and other information 
                         not covered in the following tables for the Common 
                         Link Access to Workstation (CLAW) protocol."
                    ::= {cipCardClaw 1}

cipCardClawEntry    OBJECT-TYPE
                    SYNTAX      CipCardClawEntry
                    MAX-ACCESS  not-accessible
                    STATUS      current
                    DESCRIPTION
                        "A list of CLAW values."
                    INDEX   { cipCardEntryIndex,
                              cipCardDtrBrdIndex,
                              cipCardSubChannelIndex,
                              cipCardClawIndex }
                    ::= { cipCardClawTable 1 }

CipCardClawEntry ::= SEQUENCE
{
        cipCardClawIndex                  Integer32 (0..2147483647),
        cipCardClawConnected              TruthValue
}

cipCardClawIndex    OBJECT-TYPE
                    SYNTAX      Integer32 (0..2147483647)
                    MAX-ACCESS  read-only
                    STATUS      current
                    DESCRIPTION
                        "This indicates which CLAW link is being referenced
                         for a particular subchannel on a daughter board on a
                         CMCC card."
                    ::= {cipCardClawEntry 1}

cipCardClawConnected
                    OBJECT-TYPE
                    SYNTAX     TruthValue
                    MAX-ACCESS read-only
                    STATUS     current
                    DESCRIPTION
                        "Indicates CLAW connection status."
                    ::= {cipCardClawEntry 2}

-- ;;;;;;;;;;;;;;;;;;;;; cipCardClawConfigTable ;;;;;;;;;;;;;;;;;;;;;;;;;;;

cipCardClawConfigTable
                    OBJECT-TYPE 
                    SYNTAX      SEQUENCE OF CipCardClawConfigEntry
                    MAX-ACCESS  not-accessible
                    STATUS      current
                    DESCRIPTION
                        "This table contains configuration information for
                         the Common Link Access to Workstation (CLAW)
                         protocol."
                    ::= {cipCardClaw 2}

cipCardClawConfigEntry
                    OBJECT-TYPE
                    SYNTAX      CipCardClawConfigEntry
                    MAX-ACCESS  not-accessible
                    STATUS      current
                    DESCRIPTION
                        "A list of CLAW configuration values."
                    INDEX   { cipCardEntryIndex,
                              cipCardDtrBrdIndex,
                              cipCardSubChannelIndex,
                              cipCardClawIndex }
                    ::= { cipCardClawConfigTable 1 }

CipCardClawConfigEntry ::= SEQUENCE
{
        cipCardClawConfigPath             OCTET STRING (SIZE(2)),
        cipCardClawConfigDevice           OCTET STRING (SIZE(2)),
        cipCardClawConfigIpAddr           IpAddress,
        cipCardClawConfigHostName         DisplayString (SIZE (1..10)),
        cipCardClawConfigRouterName       DisplayString (SIZE (1..10)),
        cipCardClawConfigHostAppl         DisplayString (SIZE (1..10)),
        cipCardClawConfigRouterAppl       DisplayString (SIZE (1..10)),
        cipCardClawConfigBroadcastEnable  TruthValue,
        cipCardClawConfigRowStatus        RowStatus
}

cipCardClawConfigPath
                    OBJECT-TYPE
                    SYNTAX      OCTET STRING (SIZE(2))
                    MAX-ACCESS  read-create
                    STATUS      current
                    DESCRIPTION
                        "Hex path identifier for the escon director 
                         switch port containing the fiber from the 
                         channel on the host to which this CMCC CLAW 
                         task connects. 

                         This is a concatenation of the switch port number, 
                         the channel logical address (used by the host to
                         associate an logical partition (LPAR) with the
                         control unit), and the control unit logical
                         address (address of a logical control
                         unit used by the host to associate a group of 
                         physical devices). 

                         For a directly connected channel, the switch 
                         port number is usually 01."
                    ::= {cipCardClawConfigEntry 1}

cipCardClawConfigDevice
                    OBJECT-TYPE
                    SYNTAX      OCTET STRING (SIZE(2))
                    MAX-ACCESS  read-create
                    STATUS      current
                    DESCRIPTION
                      "Two digit hex device address for the device 
                       the SNA host will use to communicate with the
                       CLAW task on the CMCC card. The address must 
                       be even."
                    ::= {cipCardClawConfigEntry 2}

cipCardClawConfigIpAddr
                    OBJECT-TYPE
                    SYNTAX      IpAddress
                    MAX-ACCESS  read-create
                    STATUS      current
                    DESCRIPTION
                        "IP address of the host application for the CMCC
                         CLAW task as specified in the HOME statement 
                         of the PROFILE TCPIP."
                    ::= {cipCardClawConfigEntry 3}

cipCardClawConfigHostName
                    OBJECT-TYPE
                    SYNTAX      DisplayString(SIZE (1..10))
                    MAX-ACCESS  read-create
                    STATUS      current
                    DESCRIPTION
                        "CLAW host name for this CLAW device."
                    ::= {cipCardClawConfigEntry 4}

cipCardClawConfigRouterName
                    OBJECT-TYPE
                    SYNTAX      DisplayString(SIZE (1..10))
                    MAX-ACCESS  read-create
                    STATUS      current
                    DESCRIPTION
                        "CLAW router name for this CLAW device."
                    ::= {cipCardClawConfigEntry 5}

cipCardClawConfigHostAppl
                    OBJECT-TYPE
                    SYNTAX      DisplayString(SIZE (1..10))
                    MAX-ACCESS  read-create
                    STATUS      current
                    DESCRIPTION
                        "CLAW host application name for this CLAW connection."
                    ::= {cipCardClawConfigEntry 6}

cipCardClawConfigRouterAppl
                    OBJECT-TYPE
                    SYNTAX      DisplayString(SIZE (1..10))
                    MAX-ACCESS  read-create
                    STATUS      current
                    DESCRIPTION
                        "CLAW router application name for this CLAW
                         connection."
                    ::= {cipCardClawConfigEntry 7}

cipCardClawConfigBroadcastEnable OBJECT-TYPE
                    SYNTAX      TruthValue
                    MAX-ACCESS  read-create
                    STATUS      current
                    DESCRIPTION
                        "Control processing of broadcast frames for the 
                         path/device.
                         Enable turns broadcast processing on."
                    ::= {cipCardClawConfigEntry 8}

cipCardClawConfigRowStatus OBJECT-TYPE
                    SYNTAX      RowStatus
                    MAX-ACCESS  read-create
                    STATUS      current
                    DESCRIPTION
                        "This object is used by a management station to
                         create or delete the row entry in
                         cipCardClawConfigTable following the RowStatus
                         textual convention."
  ::= {cipCardClawConfigEntry 9}

-- ;;;;;;;;;;;;;;;;;;;;;;;;;;; cipCardClawDataXferStatsTable ;;;;;;;;;;;;;;;;;

cipCardClawDataXferStatsTable
                    OBJECT-TYPE 
                    SYNTAX      SEQUENCE OF CipCardClawDataXferStatsEntry
                    MAX-ACCESS  not-accessible
                    STATUS      current
                    DESCRIPTION
                        "This table contains a list of objects pertaining to
                         data transfer statistics per CLAW Logical Link."
                    ::= {cipCardClaw 3}

cipCardClawDataXferStatsEntry
                    OBJECT-TYPE
                    SYNTAX      CipCardClawDataXferStatsEntry
                    MAX-ACCESS  not-accessible
                    STATUS      current
                    DESCRIPTION
                        "A list of daughter board statistics."
                    INDEX   { cipCardEntryIndex,
                              cipCardDtrBrdIndex,
                              cipCardSubChannelIndex,
                              cipCardClawIndex }
                    ::= { cipCardClawDataXferStatsTable 1 }

CipCardClawDataXferStatsEntry ::= SEQUENCE
{
        cipCardClawDataXferStatsBlocksRead         Counter32,
        cipCardClawDataXferStatsBlocksWritten      Counter32,
        cipCardClawDataXferStatsBytesRead          Counter32,
        cipCardClawDataXferStatsHCBytesRead        Counter64,
        cipCardClawDataXferStatsBytesWritten       Counter32,
        cipCardClawDataXferStatsHCBytesWritten     Counter64,
        cipCardClawDataXferStatsReadBlocksDropped  Counter32,
        cipCardClawDataXferStatsWriteBlocksDropped Counter32,
        cipCardClawDataXferStatsBufferGetRetryCount Counter32
}

cipCardClawDataXferStatsBlocksRead
                    OBJECT-TYPE
                    SYNTAX      Counter32
                    MAX-ACCESS  read-only
                    STATUS      current
                    DESCRIPTION
                        "Number of successful read data transfer channel
                         command words (CCWs) from the channel perspective."
                    ::= {cipCardClawDataXferStatsEntry 1}

cipCardClawDataXferStatsBlocksWritten
                    OBJECT-TYPE
                    SYNTAX      Counter32
                    MAX-ACCESS  read-only
                    STATUS      current
                    DESCRIPTION
                        "Number of successful write data transfer CCWs
                         from the channel perspective."
                    ::= {cipCardClawDataXferStatsEntry 2}

cipCardClawDataXferStatsBytesRead
                    OBJECT-TYPE
                    SYNTAX      Counter32
                    MAX-ACCESS  read-only
                    STATUS      current
                    DESCRIPTION
                        "Number of bytes successfully read from the 
                         channel perspective."
                    ::= {cipCardClawDataXferStatsEntry 3}

cipCardClawDataXferStatsHCBytesRead
                    OBJECT-TYPE
                    SYNTAX      Counter64
                    MAX-ACCESS  read-only
                    STATUS      current
                    DESCRIPTION
                        "Number of bytes successfully read from the channel
                         perspective. This is the 64-bit (High Capacity)
                         version of clawDataXferStatsBytesRead."
                    ::= {cipCardClawDataXferStatsEntry 4}

cipCardClawDataXferStatsBytesWritten
                    OBJECT-TYPE
                    SYNTAX      Counter32
                    MAX-ACCESS  read-only
                    STATUS      current
                    DESCRIPTION
                        "Number of bytes successfully written from the 
                         channel perspective."
                    ::= {cipCardClawDataXferStatsEntry 5}

cipCardClawDataXferStatsHCBytesWritten
                    OBJECT-TYPE
                    SYNTAX      Counter64
                    MAX-ACCESS  read-only
                    STATUS      current
                    DESCRIPTION
                        "Number of bytes successfully written from the 
                         channel perspective. This is the 64-bit version
                         version of clawDataXferStatsBytesWritten."
                    ::= {cipCardClawDataXferStatsEntry 6}

cipCardClawDataXferStatsReadBlocksDropped
                    OBJECT-TYPE
                    SYNTAX      Counter32
                    MAX-ACCESS  read-only
                    STATUS      current
                    DESCRIPTION
                        "Number of read blocks dropped."
                    ::= {cipCardClawDataXferStatsEntry 7}

cipCardClawDataXferStatsWriteBlocksDropped
                    OBJECT-TYPE
                    SYNTAX      Counter32
                    MAX-ACCESS  read-only
                    STATUS      current
                    DESCRIPTION
                        "Number of write blocks dropped."
                    ::= {cipCardClawDataXferStatsEntry 8}

cipCardClawDataXferStatsBufferGetRetryCount
                    OBJECT-TYPE
                    SYNTAX      Counter32
                    MAX-ACCESS  read-only
                    STATUS      current
                    DESCRIPTION
                        "Number of times a buffer was requested and none were
                         available."
                    ::= {cipCardClawDataXferStatsEntry 9}

-- ;;;;;;;;;;;;;;;;;;;;;;; End Of CLAW Objects ;;;;;;;;;;;;;;;;;;;;;;;;;;;;;

-- ;;;;;;;;;;;;;;;;;;;;;;;;;;;;;;;;;;;;;;;;;;;;;;;;;;;;;;;;;;;;;;;;;;;;;;;;;;;
--
--  TRAP DEFINITIONS
--

--
--  Notifications
--

cipCardTraps  OBJECT IDENTIFIER ::= { cipCard 5}

cipCardLinkFailure NOTIFICATION-TYPE
  OBJECTS {
    cipCardDtrBrdIndex,
    cipCardDtrBrdStatus,
    cipCardDtrBrdSignal,
    linkIncidentTrapCause,
    implicitIncidents,
    codeViolationErrors,
    linkFailureSignalOrSyncLoss,
    linkFailureNOSs,
    linkFailureSequenceTimeouts,
    linkFailureInvalidSequences
  }
  STATUS  deprecated
  DESCRIPTION
    "This trap indicates that a significant link event has been recognized
     resulting in the degradation of the interface line quality.
     (This trap was deactivated 6/97, below trap is now sent on link failures)"
  ::= { cipCardTraps 1 }

cipCardDtrBrdLinkFailure NOTIFICATION-TYPE
  OBJECTS {
    cipCardDtrBrdStatus,
    cipCardDtrBrdSignal,
    linkIncidentTrapCause
  }  STATUS  current
  DESCRIPTION
    "This trap indicates that a significant link event has been recognized
     resulting in the degradation of the interface line quality."
  ::= { cipCardTraps 2 }

--
-- Conformance Information
--

ciscoChannelMibConformance OBJECT IDENTIFIER ::= { channel 2 }
ciscoChannelMibCompliances OBJECT IDENTIFIER ::= 
  { ciscoChannelMibConformance 1 }
ciscoChannelMibGroups OBJECT IDENTIFIER ::= 
  { ciscoChannelMibConformance 2 }

--
-- Compliance Statements
--

ciscoChannelMibCompliance MODULE-COMPLIANCE
  STATUS current
  DESCRIPTION
    "The compliance statement for the TcpIP Offload feature."
  MODULE
    MANDATORY-GROUPS {
      ciscoChannelGroup
    }
  ::= { ciscoChannelMibCompliances 1 }

ciscoChannelMibComplianceRev1 MODULE-COMPLIANCE
  STATUS current
  DESCRIPTION
    "The compliance statement for the TcpIP Offload feature."
  MODULE
    MANDATORY-GROUPS {
      ciscoChannelGroupRev1
    }
  ::= { ciscoChannelMibCompliances 2 }

ciscoChannelMibComplianceRev2 MODULE-COMPLIANCE
  STATUS current
  DESCRIPTION
    "The compliance statement for the TcpIP Offload & CSNA features."
  MODULE
    MANDATORY-GROUPS {
      ciscoChannelGroupRev1, ciscoChannelGroupRev2
    }
  ::= { ciscoChannelMibCompliances 3 }

ciscoChannelGroup OBJECT-GROUP
  OBJECTS {
    -- cipCardTable
    -- cipCardEntryIndex,
    cipCardEntryName,
    cipCardEntryTotalMemory,
    cipCardEntryFreeMemory,
    cipCardEntryCpuUtilization,
    cipCardEntryTimeSinceLastReset,
    cipCardEntryMajorSwRevisionNr,
    cipCardEntryMinorSwRevisionNr,
    cipCardEntryMajorHwRevisionNr,
    cipCardEntryMinorHwRevisionNr,
    -- cipCardApplicationTable
    -- cipCardApplicationNameIndex,
    cipCardApplicationRevision,
    cipCardApplicationCompileInfo,
    -- cipCardDaughterBoardTable
    -- cipCardDtrBrdIndex,
    cipCardDtrBrdType,
    cipCardDtrBrdStatus,
    cipCardDtrBrdSignal,
    cipCardDtrBrdOnline,
    implicitIncidents,
    codeViolationErrors,
    linkFailureSignalOrSyncLoss,
    linkFailureNOSs,
    linkFailureSequenceTimeouts,
    linkFailureInvalidSequences,
    linkIncidentTrapCause,
    -- cipCardSubChannelTable
    cipCardSubChannelIndex,
    cipCardSubChannelConnections,
    cipCardSubChannelCancels,
    cipCardSubChannelSelectiveResets,
    cipCardSubChannelSystemResets,
    cipCardSubChannelDeviceErrors,
    cipCardSubChannelWriteBlocksDropped,
    cipCardSubChannelLastSenseData,
    cipCardSubChannelLastSenseDataTime,
    cipCardSubChannelCuBusies,
    -- cipCardClawTable
    cipCardClawIndex,
    cipCardClawConnected,
    -- cipCardClawConfigTable
    cipCardClawConfigPath,
    cipCardClawConfigDevice,
    cipCardClawConfigIpAddr,
    cipCardClawConfigHostName,
    cipCardClawConfigRouterName,
    cipCardClawConfigHostAppl,
    cipCardClawConfigRouterAppl,
    -- cipCardClawDataXferStatsTable
    cipCardClawDataXferStatsBlocksRead,
    cipCardClawDataXferStatsBlocksWritten,
    cipCardClawDataXferStatsBytesRead,
    cipCardClawDataXferStatsHCBytesRead,
    cipCardClawDataXferStatsBytesWritten,
    cipCardClawDataXferStatsHCBytesWritten,
    cipCardClawDataXferStatsReadBlocksDropped,
    cipCardClawDataXferStatsWriteBlocksDropped,
    cipCardClawDataXferStatsBufferGetRetryCount
  }
  STATUS current
  DESCRIPTION
    "A collection of objects providing configuration capability."
  ::= { ciscoChannelMibGroups 1}

ciscoChannelGroupRev1 OBJECT-GROUP
  OBJECTS {
    -- cipCardTable
    -- cipCardEntryIndex,
    cipCardEntryName,
    cipCardEntryTotalMemory,
    cipCardEntryFreeMemory,
    cipCardEntryCpuUtilization,
    cipCardEntryTimeSinceLastReset,
    cipCardEntryMajorSwRevisionNr,
    cipCardEntryMinorSwRevisionNr,
    cipCardEntryMajorHwRevisionNr,
    cipCardEntryMinorHwRevisionNr,
    -- cipCardApplicationTable
    -- cipCardApplicationNameIndex,
    cipCardApplicationRevision,
    cipCardApplicationCompileInfo,
    -- cipCardDaughterBoardTable
    -- cipCardDtrBrdIndex,
    cipCardDtrBrdType,
    cipCardDtrBrdStatus,
    cipCardDtrBrdSignal,
    cipCardDtrBrdOnline,
    implicitIncidents,
    codeViolationErrors,
    linkFailureSignalOrSyncLoss,
    linkFailureNOSs,
    linkFailureSequenceTimeouts,
    linkFailureInvalidSequences,
    linkIncidentTrapCause,
    cipCardDtrBrdLastStat,
    cipCardDtrBrdNextStat,
    -- cipCardSubChannelTable
    cipCardSubChannelIndex,
    cipCardSubChannelConnections,
    cipCardSubChannelCancels,
    cipCardSubChannelSelectiveResets,
    cipCardSubChannelSystemResets,
    cipCardSubChannelDeviceErrors,
    cipCardSubChannelWriteBlocksDropped,
    cipCardSubChannelLastSenseData,
    cipCardSubChannelLastSenseDataTime,
    cipCardSubChannelCuBusies,
    cipCardSubChannelCmdRetries,
    -- cipCardClawTable
    cipCardClawIndex,
    cipCardClawConnected,
    -- cipCardClawConfigTable
    cipCardClawConfigPath,
    cipCardClawConfigDevice,
    cipCardClawConfigIpAddr,
    cipCardClawConfigHostName,
    cipCardClawConfigRouterName,
    cipCardClawConfigHostAppl,
    cipCardClawConfigRouterAppl,
    -- cipCardClawDataXferStatsTable
    cipCardClawDataXferStatsBlocksRead,
    cipCardClawDataXferStatsBlocksWritten,
    cipCardClawDataXferStatsBytesRead,
    cipCardClawDataXferStatsHCBytesRead,
    cipCardClawDataXferStatsBytesWritten,
    cipCardClawDataXferStatsHCBytesWritten,
    cipCardClawDataXferStatsReadBlocksDropped,
    cipCardClawDataXferStatsWriteBlocksDropped,
    cipCardClawDataXferStatsBufferGetRetryCount
  }
  STATUS current
  DESCRIPTION
    "A collection of objects providing configuration capability."
  ::= { ciscoChannelMibGroups 2}

ciscoChannelGroupRev2 OBJECT-GROUP
  OBJECTS {
    -- cipCardTable
    -- cipCardEntryIndex
    cipCardEntryCpuLoad1m,
    cipCardEntryCpuLoad5m,
    cipCardEntryCpuLoad60m,
    cipCardEntryDmaLoad1m,
    cipCardEntryDmaLoad5m,
    cipCardEntryDmaLoad60m,
    -- cipCardDaughterBoardTable
    -- cipCardDtrBrdIndex
    cipCardDtrBrdChannelLoad1m,
    cipCardDtrBrdChannelLoad5m,
    cipCardDtrBrdChannelLoad60m,
    -- cipCardClawConfigTable
    cipCardClawConfigBroadcastEnable,
    cipCardClawConfigRowStatus
  }
  STATUS current
  DESCRIPTION
    "A collection of objects providing configuration capability."
  ::= { ciscoChannelMibGroups 3}

ciscoChannelGroupRev3 OBJECT-GROUP
  OBJECTS {
    -- cipCardSubChannelTable
    cipCardSubChannelResetEvent,
    cipCardSubChannelShortBusy,
    cipCardSubChannelCMDRetry,
    cipCardSubChannelBufferWait,
    cipCardSubChannelStatPending,
    cipCardSubChannelSuspend,
    cipCardSubChannelFBLWait
  }
  STATUS current
  DESCRIPTION
    "A collection of Subchannel device status objects."
  ::= { ciscoChannelMibGroups 4}

END
