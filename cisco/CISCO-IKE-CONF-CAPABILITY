CISCO-IKE-CONF-CAPABILITY DEFINITIONS ::= BEGIN

IMPORTS
        MODULE-IDENTITY
                FROM SNMPv2-SMI
        AGENT-CAPABILITIES
                FROM SNMPv2-CONF
        ciscoAgentCapability
                FROM CISCO-SMI;

ciscoCicIkeCfgCapability MODULE-IDENTITY
        LAST-UPDATED    "200602020000Z"
        ORGANIZATION    "Cisco Systems, Inc."
        CONTACT-INFO
                "       Cisco Systems
                        Customer Service

                Postal: 170 W Tasman Drive
                        San Jose, CA  95134
                        USA

                   Tel: +1 800 553-NETS

                E-mail: cs-san@cisco.com"
        DESCRIPTION
                "Agent capabilities for
                 CISCO-IKE-CONFIGURATION-MIB"

        REVISION  "200602020000Z"
        DESCRIPTION
                "Initial version of this MIB."
        ::= { ciscoAgentCapability 489 }

--
-- Agent capability for SanOS 3.0 (on MDS 9000 Platform)
--
cCicIkeCfgCapSanOSV30R1MDS9000 AGENT-CAPABILITIES
    PRODUCT-RELEASE "Cisco SanOS 3.0(1) on Cisco MDS 9000
                     series devices." 
    STATUS          current
    DESCRIPTION     "Cisco IKE Configuration 
                     MIB capabilities"

    SUPPORTS        CISCO-IKE-CONFIGURATION-MIB
    INCLUDES        {
                        cicIkeCfgOperGroup,
                        cicIkeCfgIdentitiesGroup,
                        cicIkeCfgPskAuthGroup,
                        cicIkeCfgPolicyGroup,
                        cicIkeCfgOptionalPolicyGroup,
                        cicIkeCfgFailureRecoveryGroup
                    }
    ::= { ciscoCicIkeCfgCapability 1 }

END
