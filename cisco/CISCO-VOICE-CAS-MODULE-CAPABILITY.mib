CISCO-VOICE-CAS-MODULE-CAPABILITY DEFINITIONS ::= BEGIN

IMPORTS
        MODULE-IDENTITY
                FROM SNMPv2-SMI
        AGENT-CAPABILITIES
                FROM SNMPv2-CONF
        ciscoAgentCapability
                FROM CISCO-SMI;

ciscoVoiceCasModuleCapability MODULE-IDENTITY
        LAST-UPDATED    "200403290000Z"
        ORGANIZATION    "Cisco Systems, Inc."
        CONTACT-INFO
                "       Cisco Systems
                        Customer Service

                Postal: 170 West Tasman Drive
                        San Jose, CA  95134
                        USA

                   Tel: +1 800 553-NETS

                E-mail: cs-voice-gateway@cisco.com"
        DESCRIPTION
                "The capabilities description of 
                 CISCO-VOICE-CAS-MODULE-MIB."

        REVISION        "200403290000Z"
        DESCRIPTION
                "Initial version of this MIB module."
        ::= { ciscoAgentCapability 401 }

cvcmCapabilityV321 AGENT-CAPABILITIES
    PRODUCT-RELEASE      "Cisco VISM Release 3.2.1"
    STATUS               current
    DESCRIPTION          "CISCO-VOICE-CAS-MODULE-MIB capabilities."

    SUPPORTS             CISCO-VOICE-CAS-MODULE-MIB
        INCLUDES         { cvcmCasBitGroup }

        VARIATION        cvcmABCDIncomingPattern
            ACCESS       read-only
            DESCRIPTION  "Set not supported."
    ::= { ciscoVoiceCasModuleCapability 1 }

END
