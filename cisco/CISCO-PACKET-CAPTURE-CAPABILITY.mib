CISCO-PACKET-CAPTURE-CAPABILITY DEFINITIONS ::= BEGIN

IMPORTS
    MODULE-IDENTITY,
    Unsigned32
        FROM SNMPv2-SMI
    AGENT-CAPABILITIES
        FROM SNMPv2-CONF
    SnmpAdminString
        FROM SNMP-FRAMEWORK-MIB
    InetAddressType
        FROM INET-ADDRESS-MIB
    ciscoAgentCapability
        FROM CISCO-SMI;

ciscoPacketCaptureCapability MODULE-IDENTITY
    LAST-UPDATED    "200810230000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        CISCO-PACKET-CAPTURE-MIB."
    REVISION        "200810230000Z"
    DESCRIPTION
        "Added capability statement cpcCapV12R0233SXIPCat6K."
    REVISION        "200701050000Z"
    DESCRIPTION
        "Initial version of this MIB module."
          ::= { ciscoAgentCapability 527 }

ciscoPacketCaptureCatOSV08R0601 AGENT-CAPABILITIES
    PRODUCT-RELEASE "Cisco CatOS 8.6(1) on devices with
                    Supervisor 720 or Supervisor 32 present."
    STATUS          current
    DESCRIPTION     "CISCO-PACKET-CAPTURE-MIB capabilities."

    SUPPORTS        CISCO-PACKET-CAPTURE-MIB
    INCLUDES        {
                        cpcGenericConfigGroup,
                        cpcFilterConfigGroup,
                        cpcMacFilterConfigGroup,
                        cpcIpFilterConfigGroup,
                        cpcDestFileNameConfigGroup
                    }
    VARIATION       cpcSessionDestFileName
    SYNTAX          SnmpAdminString (SIZE (7..40))
    DESCRIPTION
        "Only limited set of values are supported.
        Value of this object must be specified in the format
        of <device>:<filename>. Maximum length allowed
        for <filename> is 28 characters."

    VARIATION       cpcSessionPacketLength
    SYNTAX          Unsigned32 (0..10258 )
    DESCRIPTION     "Only limited set of values are supported."

    VARIATION       cpcSessionPacketLimits
    SYNTAX          Unsigned32 (0..32000 )
    DESCRIPTION     "Only limited set of values are supported."

    VARIATION       cpcSessionConfigStatus
    ACCESS          read-only
    DESCRIPTION
        "Implementation only supports read operation
        for this object."

    VARIATION       cpcCaptureSourceIfStatus
    SYNTAX          INTEGER  {
                        active(1),
                        createAndGo(4),
                        destroy(6)
                    }
    DESCRIPTION     "Only limited set of values are supported."

    VARIATION       cpcMacFilterRowStatus
    SYNTAX          INTEGER  {
                        active(1),
                        createAndGo(4),
                        destroy(6)
                    }
    DESCRIPTION     "Only limited set of values are supported."

    VARIATION       cpcIpFilterAddressType
    SYNTAX          InetAddressType {
                        ipv4(1)
                    }
    DESCRIPTION     "Only limited set of values are supported."

    VARIATION       cpcIpFilterRowStatus
    SYNTAX          INTEGER  {
                        active(1),
                        createAndGo(4),
                        destroy(6)
                    }
    DESCRIPTION     "Only limited set of values are supported."
    ::= { ciscoPacketCaptureCapability 1 }

cpcCapV12R0233SXIPCat6K AGENT-CAPABILITIES
    PRODUCT-RELEASE "Cisco IOS 12.2(33)SXI on Catalyst 6000/6500
                        series devices."
    STATUS          current
    DESCRIPTION     "CISCO-PACKET-CAPTURE-MIB capabilities."

    SUPPORTS        CISCO-PACKET-CAPTURE-MIB
    INCLUDES        {
                        cpcGenericConfigGroup,
                        cpcFilterConfigGroup,
                        cpcMacFilterConfigGroup,
                        cpcDestFileNameConfigGroup,
                        cpcPacketLengthFilterConfigGroup,
                        cpcEthertypeFilterConfigGroup,
                        cpcVlanFilterConfigGroup,
                        cpcAccessGroupFilterConfigGroup,
                        cpcBufferConfigGroup,
                        cpcScheduleConfigGroup,
                        cpcSessionStatsGroup,
                        cpcMaxMacFilterConfigGroup,
                        cpcMaxIpFilterConfigGroup,
                        cpcSessionPacketRateLimitGroup,
                        cpcSessionDescrGroup 
                    }
    VARIATION       cpcSessionPacketLength
    SYNTAX          Unsigned32 (0..9216 )
    DESCRIPTION     "Only limited set of values is supported."

    VARIATION       cpcSessionConfigStatus
    SYNTAX          INTEGER  {
                        active(1),
                        createAndGo(4),
                        destroy(6)
                    }
    DESCRIPTION     "Only limited set of enumerated values is
                    supported."

    VARIATION       cpcCaptureSourceIfStatus
    SYNTAX          INTEGER  {
                        active(1),
                        createAndGo(4),
                        destroy(6)
                    }
    DESCRIPTION     "Only limited set of enumerated values is
                    supported."

    VARIATION       cpcMacFilterRowStatus
    SYNTAX          INTEGER  {
                        active(1),
                        createAndGo(4),
                        destroy(6)
                    }
    DESCRIPTION     "Only limited set of enumerated values is
                    supported."

    VARIATION       cpcIpFilterAddressType
    SYNTAX          InetAddressType {
                        ipv4(1)
                    }
    DESCRIPTION     "Only limited set of enumerated values is
                    supported."

    VARIATION       cpcPacketLengthFilterMin 
    SYNTAX          Unsigned32 (0..9216 )
    DESCRIPTION     "Only limited set of values is supported."

    VARIATION       cpcPacketLengthFilterMax 
    SYNTAX          Unsigned32 (0..9216 )
    DESCRIPTION     "Only limited set of values is supported and the
                    value of cpcPacketLengthFilterMax must be equal or
                    greater than that of cpcPacketLengthFilterMin."

    VARIATION       cpcEthertypeFilterStatus 
    SYNTAX          INTEGER  {
                        active(1),
                        createAndGo(4),
                        destroy(6)
                    }
    DESCRIPTION     "Only limited set of enumerated values is
                    supported."

    VARIATION       cpcVlanFilterRowStatus 
    SYNTAX          INTEGER  {
                        active(1),
                        createAndGo(4),
                        destroy(6)
                    }
    DESCRIPTION     "Only limited set of enumerated values is
                    supported."

    VARIATION       cpcAccessGroupFilterStatus 
    SYNTAX          INTEGER  {
                        active(1),
                        createAndGo(4),
                        destroy(6)
                    }
    DESCRIPTION     "Only limited set of enumerated values is
                    supported."

    VARIATION       cpcBufferSize 
    SYNTAX          Unsigned32 (0 | 32..65535 )
    DESCRIPTION     "Only limited set of values is supported."

    VARIATION       cpcSessionPacketRateLimit 
    SYNTAX          Unsigned32 (10..100000 )
    DESCRIPTION     "Only limited set of values is supported."
    ::= { ciscoPacketCaptureCapability 2 }

END
