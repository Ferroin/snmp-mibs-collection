CISCO-ITP-ACL-MIB DEFINITIONS ::= BEGIN

IMPORTS
        MODULE-IDENTITY,
        OBJECT-TYPE, 
        Unsigned32
                FROM SNMPv2-SMI

        SnmpAdminString
                FROM SNMP-FRAMEWORK-MIB

        RowStatus,
        TimeStamp,
        TEXTUAL-CONVENTION
                FROM SNMPv2-TC

        MODULE-COMPLIANCE,
        OBJECT-GROUP
                FROM SNMPv2-CONF

        CItpTcAclId,
        CItpTcEncodingSchemeValue,
        CItpTcGlobalTitleSelector,
        CItpTcNAI,
        CItpTcNumberingPlan, 
        CItpTcPointCode,
        CItpTcPointCodeMask,
        CItpTcServiceIndicator, 
        CItpTcSubSystemNumber,
        CItpTcSubSystemNumberMask,
        CItpTcTranslationType
                FROM CISCO-ITP-TC-MIB

        ciscoMgmt
             FROM CISCO-SMI;        

ciscoItpAclMIB MODULE-IDENTITY
        LAST-UPDATED    "200108290000Z"
        ORGANIZATION    "Cisco Systems, Inc."
        CONTACT-INFO
                "       Cisco Systems, Inc
                        Customer Service

                Postal: 170 W. Tasman Drive
                        San Jose, CA  95134
                        USA

                   Tel: +1 800 553-NETS

                E-mail: cs-ss7@cisco.com"
        DESCRIPTION
               "The MIB for managing access lists that control
                messages transported over Signalling System 
                No. 7 (SS7) Network via Cisco IP Transfer
                Point.  

                The Cisco IP Transfer Point (ITP) is a hardware 
                and software solution that transports SS7 traffic 
                using IP. Each ITP node provides function similar
                to SS7 signaling point.   

                The relevant ITU documents describing this technology
                is the ITU Q series, including ITU Q.700: Introduction
                to CCITT Signalling System No. 7 and ITU Q.701 
                Functional description of the message transfer part
                (MTP) of Signalling System No. 7."

        REVISION        "200108290000Z"
        DESCRIPTION
                "Initial version of this MIB module."
        ::= {  ciscoMgmt 227  }

-- Top-level structure of the MIB

cItpAclMIBNotifs          OBJECT IDENTIFIER ::= { ciscoItpAclMIB 0 }
cItpAclMIBObjects         OBJECT IDENTIFIER ::= { ciscoItpAclMIB 1 }
cItpAclMIBConformance     OBJECT IDENTIFIER ::= { ciscoItpAclMIB 2 }

cItpAclScalars            OBJECT IDENTIFIER ::= { cItpAclMIBObjects 1 }
cItpAclConfig             OBJECT IDENTIFIER ::= { cItpAclMIBObjects 2 }

--  *************************************************************
--  *                                                           *
--  * Textual Conventions                                       *
--  *                                                           *
--  *************************************************************
CItpAclAction ::= TEXTUAL-CONVENTION
    STATUS          current
    DESCRIPTION
           "The list of possible actions to be performed on a
            packet when information in message matches an access
            control entry .

            'accept'  : The matching packet is accepted for
                        further processing.
            'discard' : The matching packet is to be discarded
                        without any further processing on this 
                        packet."
    SYNTAX INTEGER {
            accept(1),
            discard(2)
    }

--  *************************************************************
--  *                                                           *
--  * SP - Scalars                                              *
--  *                                                           *
--  *************************************************************
cItpAclConfigLastChanged          OBJECT-TYPE
    SYNTAX                        TimeStamp 
    MAX-ACCESS                    read-only
    STATUS                        current
    DESCRIPTION
            "The value of sysUpTime at the time of the last
             creation or deletion of an entry in the cItpAclTable.
             If the local network management subsystem is 
             re-initialization, then this object contains the 
             sysUpTime at the time when this occurred. This value 
             can be used to prevent unnecessary walks of the
             cItpAclTable."
    ::= { cItpAclScalars 1 }

--  *************************************************************
--  *                                                           *
--  * SP - Access Control List Table                            *
--  *                                                           *
--  *************************************************************

cItpAclTable                      OBJECT-TYPE
    SYNTAX                        SEQUENCE OF CItpAclTableEntry 
    MAX-ACCESS                    not-accessible
    STATUS                        current
    DESCRIPTION
           "A table of SP access controls. The access control
            definition controls which packets are accepted or
            rejected. The access control may be applied before
            sending the packet to the routing table or may be
            applied after the packet is processed by the routing
            table. Entries are added to this table via
            cItpAclRowStatus in accordance with the RowStatus
            convention."
    ::= { cItpAclConfig  1 }

cItpAclTableEntry                 OBJECT-TYPE
    SYNTAX                        CItpAclTableEntry 
    MAX-ACCESS                    not-accessible
    STATUS                        current
    DESCRIPTION
            "A list of Signalling Point access control attributes."
    INDEX   {
            cItpAclId,                  
            cItpAclEntryType,                  
            cItpAclEntryNumber 
    }
    ::= { cItpAclTable  1 }

CItpAclTableEntry  ::= SEQUENCE {
    cItpAclId                        CItpTcAclId,
    cItpAclEntryType                 INTEGER,
    cItpAclEntryNumber               Unsigned32,
    cItpAclAction                    CItpAclAction,
    cItpAclParameters                BITS, 
    cItpAclDpc                       CItpTcPointCode,
    cItpAclDpcMask                   CItpTcPointCodeMask,
    cItpAclOpc                       CItpTcPointCode,
    cItpAclOpcMask                   CItpTcPointCodeMask,
    cItpAclSi                        CItpTcServiceIndicator, 
    cItpAclPattern                   SnmpAdminString,
    cItpAclOffset                    Unsigned32,
    cItpAclComment                   SnmpAdminString, 
    cItpAclCgpa                      CItpTcPointCode, 
    cItpAclCgpaMask                  CItpTcPointCodeMask,
    cItpAclCgpaSsn                   CItpTcSubSystemNumber, 
    cItpAclCgpaSsnMask               CItpTcSubSystemNumberMask, 
    cItpAclCdpa                      CItpTcPointCode, 
    cItpAclCdpaMask                  CItpTcPointCodeMask,
    cItpAclCdpaSsn                   CItpTcSubSystemNumber, 
    cItpAclCdpaSsnMask               CItpTcSubSystemNumberMask, 
    cItpAclGtiSelector               CItpTcGlobalTitleSelector,
    cItpAclGtiTranslateType          CItpTcTranslationType,
    cItpAclGtiNumberingPlan          CItpTcNumberingPlan,
    cItpAclGtiNai                    CItpTcNAI, 
    cItpAclGtiEsv                    CItpTcEncodingSchemeValue, 
    cItpAclAft                       CItpTcPointCode, 
    cItpAclAftMask                   CItpTcPointCodeMask,
    cItpAclAftSsn                    CItpTcSubSystemNumber, 
    cItpAclAftSsnMask                CItpTcSubSystemNumberMask, 
    cItpAclRowStatus                 RowStatus

}

cItpAclId                         OBJECT-TYPE
    SYNTAX                        CItpTcAclId 
    MAX-ACCESS                    not-accessible
    STATUS                        current
    DESCRIPTION
            "The identifier used to select a list of access list
             entries. The administrator will select an valid 
             identifier within the specified range defined for 
             SS7 access lists."
    ::= { cItpAclTableEntry  1 }

cItpAclEntryType                  OBJECT-TYPE
    SYNTAX                        INTEGER {
                                    comment(1),
                                    entry(2)
    }
    MAX-ACCESS                    not-accessible
    STATUS                        current
    DESCRIPTION
           "The list of possible entry types.
            'comments'  : A statement used to describe and document
                          access list entries.
            'entry'     : A access list entry."
    ::= { cItpAclTableEntry  2 }

cItpAclEntryNumber                OBJECT-TYPE
    SYNTAX                        Unsigned32 (1..65535)
    MAX-ACCESS                    not-accessible
    STATUS                        current
    DESCRIPTION
            "An numeric value assigned to each access list entry.
             The entries of the same type must be unique. Entries 
             will be tested in ascending order."
    ::= { cItpAclTableEntry  3 }

cItpAclAction                     OBJECT-TYPE
    SYNTAX                        CItpAclAction 
    MAX-ACCESS                    read-create
    STATUS                        current
    DESCRIPTION
           "The action to be performed on the packet that matched
            this access control."
    DEFVAL { accept } 
    ::= { cItpAclTableEntry  4 }

cItpAclParameters                 OBJECT-TYPE
    SYNTAX                        BITS { 
                                         si(0),
                                         dpc(1),
                                         dpcMask(2),
                                         opc(3),
                                         opcMask(4),
                                         pattern(5),
                                         comment(6),
                                         cgpa(7),
                                         cgpaMask(8),
                                         cdpa(9),
                                         cdpaMask(10),
                                         selector(11),
                                         aft(12),
                                         aftMask(13),
                                         all(14)
                                  }
    MAX-ACCESS                    read-create
    STATUS                        current
    DESCRIPTION
       "The cItpAclType object indicates which types of tests 
        will be processed on the each access list entry.
        Each may contain one or more filters. The filter will
        be processed ascending order(si,dpc...all). Each test 
        is evaluated and if true the packet is processed
        according to cItpAclAction. 

       'si'      : The cItpAclSi is the relevant column. The packet
                   is compared to cItpAclSi to determine if the 
                   packet matches this filter.

       'dpc'     : The cItpAclDpc and cItpAclDpcMask are the relevant
                   columns. The packet is compared to cItpAclDpc
                   in conjunction with cItpAclDpcMask to determine
                   if the packet matches this access control.
                   The mask is first negated (~mask) and bitwise
                   AND is perform with mask and dpc.

       'dpcMask' : Indicates that a mask is to be applied when the
                   dpc filter is specified. If the mask is not 
                   specified then the mask is assumed to be all 
                   zeros.

       'opc'     : cItpAclOpc and cItpAclOpcMask are the relevant
                   columns. The packet is compared to cItpAclOpc
                   in conjunction with cItpAclOpcMask to determine
                   if the packet matches this access control.
                   The mask is first negated (~mask) and bitwise
                   AND is perform with mask and opc.

       'opcMask' : Indicates that a mask is to be applied when the
                   opc filter is specified. If the mask is not 
                   specified then the mask is assumed to be all 
                   zeros.

       'pattern' : cItpAclPattern and cItpAclOffset are the 
                   relevant columns. The matching criteria is 
                   based on matching the pattern specified by 
                   cItpAclPattern at offset cItpAclOffset from 
                   the start of the packet.

       'comment' : The cItpAclComment object provides an entry 
                   that can be used to describe filters.

       'cgpa'    : The cItpAclCgpa, cItpAclCgpaMask, 
                   cItpAclCgpaSsn and cItpAclCgpaSsnMask are the
                   relevant columns.  The Calling Party Point code
                   is compare with cItpAclCgpaPC using the 
                   ItpAclCgpaMask. Also, the cItpAclCgpaSsn 
                   and cItpAclCgpaSsnMask are compared if specified.

       'cgpaMask': Indicates that a mask is to be applied when the
                   cgpa filter is specified. If the mask is not 
                   specified then the mask is assumed to be all 
                   zeros.

       'cgpaSsn' : Indicates that a Subsystem Number(SSN) is to
                   be checked when the cgpa filter is specified. 

       'cgpaSsnMask': Indicates that SSN mask is to be applied 
                   when checking the SSN number for the cgpa 
                   filter is specified. If the mask is not 
                   specified then the mask is assumed to be all 
                   zeros.

       'cdpa'    : The cItpAclCdpa, cItpAclCdpaMask, 
                   cItpAclCdpaSsn and cItpAclCdpaSsnMask are the
                   relevant columns.  The Called Party Point code
                   is compared with cItpAclCcpa using the 
                   ItpAclCcpaMask. Also, the cItpAclCcpaSsn 
                   and cItpAclCcpaSsnMask are compared if specified.

       'cdpaMask': Indicates that a mask is to be applied when the
                   cdpa filter is specified. If the mask is not 
                   specified then the mask is assumed to be all 
                   zeros.

       'cdpaSsn' : Indicates that a SSN is to be checked when the
                   cdpa filter is specified. 

       'cdpaSsnMask': Indicates that SSN mask is to be applied 
                   when checking the SSN number for the cdpa 
                   filter is specified. If the mask is not 
                   specified then the mask is assumed to be all 
                   zeros.

       'selector': The Global Title Selector is used to select 
                   which objects will be tested and in what order
                   the tests will be applied as follows.
                                                                     x
                   The types of translations are different based on 
                   the variant. In both, variants the translation 
                   type and other parameters are used to provide the 
                   following types of translations.

                   - Intermediate GTT resulting in MSUs routed to a 
                     solitary point code

                   - Intermediate GTT resulting in MSUs load 
                     balanced across two or more point codes

                   - Final GTT routed to a solitary point code

                   - Final GTT routed to a primary and backup 
                     point-code and SSN (dominant mode)

                   - Final GTT load balanced across a group of 
                     point-codes and subsystems

                   For ANSI the translation types are defined in 
                   TABLE B.1/T1.112.3 of TR-NWT-000246.  The ANSI 
                   selector table may be a simple flat table/array of 
                   256 Translation Types(0-255).  In this method of 
                   translation tables can be directly accessed using 
                   the translation type from the Called Party Point 
                   Code.  

                   For ITU section 2.4.5 of ITU-T Q.714, defines the 
                   use of the Global Tile Indicator(GTI), along with 
                   Translation Type(TT), Network Plan(NP), and Nature 
                   of Address Indicator(NAI), as selectors for the 
                   table to perform the Global Title 
                   Translation(GTT).  In this cae the selector table 
                   must be searched using a combination oF GTI, TT, 
                   NP and NAI.  

                   The objects cItpAclGtiSelector, 
                   cItpAclGtiTranslateType, cItpAclGtiNumberingPlan, 
                   cItpAclGtiNai, and cItpAclGtiEsv are the relevant 
                   columns.  These object will be used in the 
                   following order based on variant and translation 
                   type.  

                   1 => cItpAclGtiNai
                   2 => cItpAclGtiTranslateType
                   3 => cItpAclGtiTranslateType
                            cItpAclGtiNumberingPlan
                                cItpAclGtiEsv
                   4 => cItpAclGtiTranslateType
                            cItpAclGtiNumberingPlan
                                cItpAclGtiNai
                                     cItpAclGtiEsv

       'aft'    :  The cItpAclAft, cItpAclAftMask, 
                   cItpAclAftSsn and cItpAclAftSsnMask are the
                   relevant columns.  The affected point code is 
                   compared with cItpAclAftPC using the 
                   ItpAclAftMask. Also, the cItpAclAftSsn 
                   and cItpAclAftSsnMask are compared if 
                   specified.

       'aftMask':  Indicates that a mask is to be applied when the
                   aft filter is specified. If the mask is not 
                   specified then the mask is assumed to be all 
                   zeros.

       'all'    :  Used in conjunction with cItpAclAction to specify
                   defaults for packet that did not match any 
                   specified access list entry."
    ::= { cItpAclTableEntry  5 }

cItpAclDpc                        OBJECT-TYPE
    SYNTAX                        CItpTcPointCode 
    MAX-ACCESS                    read-create
    STATUS                        current
    DESCRIPTION
            "The destination point code specified for this ACL. The 
             'dpc' bit in the cItpAclParameters object is used 
             indicate whether this object has been specified."
    ::= { cItpAclTableEntry  6 }

cItpAclDpcMask                    OBJECT-TYPE
    SYNTAX                        CItpTcPointCodeMask
    MAX-ACCESS                    read-create
    STATUS                        current
    DESCRIPTION
            "The mask used to define which part of the point code
             in the packet is significant when comparing the  
             destination point code with cItpAclDpc. The 
             'dpcMask' bit in the cItpAclParameters object is used 
             indicate whether this object has been specified."
    ::= { cItpAclTableEntry  7 }

cItpAclOpc                        OBJECT-TYPE
    SYNTAX                        CItpTcPointCode 
    MAX-ACCESS                    read-create
    STATUS                        current
    DESCRIPTION
            "The origin point code specified in this ACL. The 
             'opc' bit in the cItpAclParameters object is used 
             indicate whether this object has been specified."
    ::= { cItpAclTableEntry  8 }

cItpAclOpcMask                    OBJECT-TYPE
    SYNTAX                        CItpTcPointCodeMask
    MAX-ACCESS                    read-create
    STATUS                        current
    DESCRIPTION
            "The mask used to define which part of the origin
             point code in the packet is significant when comparing
             the origin point code with cItpAclDpc.  The 
             'opcMask' bit in the cItpAclParameters object is used 
             indicate whether this object has been specified."
    ::= { cItpAclTableEntry  9 }

cItpAclSi                         OBJECT-TYPE
    SYNTAX                        CItpTcServiceIndicator 
    MAX-ACCESS                    read-create
    STATUS                        current
    DESCRIPTION
            "The Service Indicator Octet. The 'si' bit in the 
             cItpAclParameters object is used indicate whether 
             this object has been specified."
    ::= { cItpAclTableEntry 10 }

cItpAclPattern                    OBJECT-TYPE
    SYNTAX                        SnmpAdminString (SIZE (0..40) ) 
    MAX-ACCESS                    read-create
    STATUS                        current
    DESCRIPTION
            "The pattern used to match a packet at offset
             cItpAclOffset.  The 'pattern' bit in the 
             cItpAclParameters object is used indicate whether
             this object has been specified."
    ::= { cItpAclTableEntry 11 }

cItpAclOffset                     OBJECT-TYPE
    SYNTAX                        Unsigned32 (0..255) 
    MAX-ACCESS                    read-create
    STATUS                        current
    DESCRIPTION
            "The offset into the packet were we begin matching the
             pattern specified by cItpAclPattern is to start.  The 
             'pattern' bit in the cItpAclParameters object is used
             indicate whether this object has been specified."
    ::= { cItpAclTableEntry 12 }

cItpAclComment                    OBJECT-TYPE
    SYNTAX                        SnmpAdminString (SIZE (0..100) ) 
    MAX-ACCESS                    read-create
    STATUS                        current
    DESCRIPTION
            "A brief description used to document access list 
             entries.  The 'comment' bit in the cItpAclParameters 
             object is used indicate whether this object has been 
             specified."
    ::= { cItpAclTableEntry 13 }

cItpAclCgpa                       OBJECT-TYPE
    SYNTAX                        CItpTcPointCode 
    MAX-ACCESS                    read-create
    STATUS                        current
    DESCRIPTION
            "The Calling Party Point Code.  The 'cgpa' bit in the 
             cItpAclParameters object is used indicate whether this 
             object has been specified."
    ::= { cItpAclTableEntry 14 }

cItpAclCgpaMask                   OBJECT-TYPE
    SYNTAX                        CItpTcPointCodeMask
    MAX-ACCESS                    read-create
    STATUS                        current
    DESCRIPTION
            "The Calling Party Point Code mask.  The 'cgpaMask' bit
             in the cItpAclParameters object is used indicate 
             whether this object has been specified."
    ::= { cItpAclTableEntry 15 }

cItpAclCgpaSsn                    OBJECT-TYPE
    SYNTAX                        CItpTcSubSystemNumber 
    MAX-ACCESS                    read-create
    STATUS                        current
    DESCRIPTION
            "The Calling Party Point Code subsystem number. The
             'cgpa' bit in the cItpAclParameters object is used 
             indicate whether this object has been specified."
    ::= { cItpAclTableEntry 16 }

cItpAclCgpaSsnMask                OBJECT-TYPE
    SYNTAX                        CItpTcSubSystemNumberMask 
    MAX-ACCESS                    read-create
    STATUS                        current
    DESCRIPTION
            "The Calling Party Point Code subsystem number Mask.  
             The 'cgpa' bit in the cItpAclParameters object is used 
             indicate whether this object has been specified."
    ::= { cItpAclTableEntry 17 }

cItpAclCdpa                       OBJECT-TYPE
    SYNTAX                        CItpTcPointCode 
    MAX-ACCESS                    read-create
    STATUS                        current
    DESCRIPTION
            "The Called Party Point Code.  The 'cdpa' bit in the
             cItpAclParameters object is used indicate whether this
             object has been specified."
    ::= { cItpAclTableEntry 18 }

cItpAclCdpaMask                   OBJECT-TYPE
    SYNTAX                        CItpTcPointCodeMask
    MAX-ACCESS                    read-create
    STATUS                        current
    DESCRIPTION
            "The Called Party Point Code mask.  The 'cdpaMask' bit
             in the cItpAclParameters object is used indicate 
             whether this object has been specified."
    ::= { cItpAclTableEntry 19 }

cItpAclCdpaSsn                    OBJECT-TYPE
    SYNTAX                        CItpTcSubSystemNumber 
    MAX-ACCESS                    read-create
    STATUS                        current
    DESCRIPTION
            "The Called Party Point Code subsystem number.  The 
             'cdpa' bit in the cItpAclParameters object is used 
             indicate whether this object has been specified."
    ::= { cItpAclTableEntry 20 }

cItpAclCdpaSsnMask                OBJECT-TYPE
    SYNTAX                        CItpTcSubSystemNumberMask 
    MAX-ACCESS                    read-create
    STATUS                        current
    DESCRIPTION
            "The Called Party Point Code subsystem number Mask.  The
             'cdpa' bit in the cItpAclParameters object is used 
             indicate whether this object has been specified."
    ::= { cItpAclTableEntry 21 }

cItpAclGtiSelector                OBJECT-TYPE
    SYNTAX                        CItpTcGlobalTitleSelector
    MAX-ACCESS                    read-create
    STATUS                        current
    DESCRIPTION
            "The Global Title Selector.  The 'selector' bit in the
             cItpAclParameters object is used indicate whether this
             object has been specified."
    ::= { cItpAclTableEntry 22 }

cItpAclGtiTranslateType           OBJECT-TYPE
    SYNTAX                        CItpTcTranslationType
    MAX-ACCESS                    read-create
    STATUS                        current
    DESCRIPTION
            "The Global Title Translate Type. The 'selector' bit in
             the cItpAclParameters object is used indicate whether 
             this object has been specified."
    ::= { cItpAclTableEntry 23 }

cItpAclGtiNumberingPlan           OBJECT-TYPE
    SYNTAX                        CItpTcNumberingPlan
    MAX-ACCESS                    read-create
    STATUS                        current
    DESCRIPTION
            "The Global Title Numbering Plan.  The 'selector' bit in
             the cItpAclParameters object is used indicate whether 
             this object has been specified."
    ::= { cItpAclTableEntry 24 }

cItpAclGtiNai                     OBJECT-TYPE
    SYNTAX                        CItpTcNAI 
    MAX-ACCESS                    read-create
    STATUS                        current
    DESCRIPTION
            "The Global Title nature of address indicator.  The 
             'selector' bit in the cItpAclParameters object is 
             used indicate whether this object has been 
             specified."
    ::= { cItpAclTableEntry 25 }

cItpAclGtiEsv                     OBJECT-TYPE
    SYNTAX                        CItpTcEncodingSchemeValue 
    MAX-ACCESS                    read-create
    STATUS                        current
    DESCRIPTION
            "The Global Title encoding scheme value.  The 
             'selector' bit in the cItpAclParameters object is
             used indicate whether this object has been 
             specified."
    ::= { cItpAclTableEntry 26 }

cItpAclAft                        OBJECT-TYPE
    SYNTAX                        CItpTcPointCode 
    MAX-ACCESS                    read-create
    STATUS                        current
    DESCRIPTION
            "The Affected Point Code.  The 'aft' bit in the 
             cItpAclParameters object is used indicate whether 
             this object has been specified."
    ::= { cItpAclTableEntry 27 }

cItpAclAftMask                    OBJECT-TYPE
    SYNTAX                        CItpTcPointCodeMask
    MAX-ACCESS                    read-create
    STATUS                        current
    DESCRIPTION
            "The Affected Point Code mask.  The 'aftMask' bit in the
             cItpAclParameters object is used indicate whether 
             this object has been specified."
    ::= { cItpAclTableEntry 28 }

cItpAclAftSsn                    OBJECT-TYPE
    SYNTAX                        CItpTcSubSystemNumber 
    MAX-ACCESS                    read-create
    STATUS                        current
    DESCRIPTION
            "The Affected Point Code subsystem number.  The 'aft' 
             bit in the cItpAclParameters object is used indicate 
             whether this object has been specified."
    ::= { cItpAclTableEntry 29 }

cItpAclAftSsnMask                OBJECT-TYPE
    SYNTAX                        CItpTcSubSystemNumberMask 
    MAX-ACCESS                    read-create
    STATUS                        current
    DESCRIPTION
            "The Affected Point Code subsystem number Mask.  The 
             'aft' bit in the cItpAclParameters object is used 
             indicate whether this object has been specified."
    ::= { cItpAclTableEntry 30 }

cItpAclRowStatus                  OBJECT-TYPE
    SYNTAX                        RowStatus
    MAX-ACCESS                    read-create
    STATUS                        current
    DESCRIPTION                   
         "The object is used by a management station to 
          create or delete the row entry in cItpAcl  
          following the RowStatus textual convention."
    ::= { cItpAclTableEntry 31 }

-- *************************************************************
-- *                                                           *
-- * Conformance Information                                   *
-- *                                                           *
-- *************************************************************
cItpAclMIBCompliances OBJECT IDENTIFIER ::=
        { cItpAclMIBConformance 1 }
cItpAclMIBGroups      OBJECT IDENTIFIER ::=
        { cItpAclMIBConformance 2 }

-- Compliance

cItpAclMIBCompliance MODULE-COMPLIANCE
    STATUS current
    DESCRIPTION
            "The compliance statement for entities which implement
            the Cisco SP MIB"
    MODULE -- this module
            MANDATORY-GROUPS {
                    cItpAclScalarGroup,
                    cItpAclAccessListGroup 
            }

    OBJECT           cItpAclAction                 
    MIN-ACCESS       read-only
    DESCRIPTION      "Create/Write access is not required."

    OBJECT           cItpAclParameters             
    MIN-ACCESS       read-only
    DESCRIPTION      "Create/Write access is not required."

    OBJECT           cItpAclDpc                    
    MIN-ACCESS       read-only
    DESCRIPTION      "Create/Write access is not required."

    OBJECT           cItpAclDpcMask                
    MIN-ACCESS       read-only
    DESCRIPTION      "Create/Write access is not required."

    OBJECT           cItpAclOpc                    
    MIN-ACCESS       read-only
    DESCRIPTION      "Create/Write access is not required."

    OBJECT           cItpAclOpcMask                
    MIN-ACCESS       read-only
    DESCRIPTION      "Create/Write access is not required."

    OBJECT           cItpAclSi                     
    MIN-ACCESS       read-only
    DESCRIPTION      "Create/Write access is not required."

    OBJECT           cItpAclPattern                
    MIN-ACCESS       read-only
    DESCRIPTION      "Create/Write access is not required."

    OBJECT           cItpAclOffset                 
    MIN-ACCESS       read-only
    DESCRIPTION      "Create/Write access is not required."

    OBJECT           cItpAclComment                
    MIN-ACCESS       read-only
    DESCRIPTION      "Create/Write access is not required."

    OBJECT           cItpAclCgpa                   
    MIN-ACCESS       read-only
    DESCRIPTION      "Create/Write access is not required."

    OBJECT           cItpAclCgpaMask               
    MIN-ACCESS       read-only
    DESCRIPTION      "Create/Write access is not required."

    OBJECT           cItpAclCgpaSsn                
    MIN-ACCESS       read-only
    DESCRIPTION      "Create/Write access is not required."

    OBJECT           cItpAclCgpaSsnMask            
    MIN-ACCESS       read-only
    DESCRIPTION      "Create/Write access is not required."

    OBJECT           cItpAclCdpa                   
    MIN-ACCESS       read-only
    DESCRIPTION      "Create/Write access is not required."

    OBJECT           cItpAclCdpaMask               
    MIN-ACCESS       read-only
    DESCRIPTION      "Create/Write access is not required."

    OBJECT           cItpAclCdpaSsn                
    MIN-ACCESS       read-only
    DESCRIPTION      "Create/Write access is not required."

    OBJECT           cItpAclCdpaSsnMask            
    MIN-ACCESS       read-only
    DESCRIPTION      "Create/Write access is not required."

    OBJECT           cItpAclGtiSelector            
    MIN-ACCESS       read-only
    DESCRIPTION      "Create/Write access is not required."

    OBJECT           cItpAclGtiTranslateType       
    MIN-ACCESS       read-only
    DESCRIPTION      "Create/Write access is not required."

    OBJECT           cItpAclGtiNumberingPlan       
    MIN-ACCESS       read-only
    DESCRIPTION      "Create/Write access is not required."

    OBJECT           cItpAclGtiNai                 
    MIN-ACCESS       read-only
    DESCRIPTION      "Create/Write access is not required."

    OBJECT           cItpAclGtiEsv                 
    MIN-ACCESS       read-only
    DESCRIPTION      "Create/Write access is not required."

    OBJECT           cItpAclAft                    
    MIN-ACCESS       read-only
    DESCRIPTION      "Create/Write access is not required."

    OBJECT           cItpAclAftMask                
    MIN-ACCESS       read-only
    DESCRIPTION      "Create/Write access is not required."

    OBJECT           cItpAclAftSsn                 
    MIN-ACCESS       read-only
    DESCRIPTION      "Create/Write access is not required."

    OBJECT           cItpAclAftSsnMask             
    MIN-ACCESS       read-only
    DESCRIPTION      "Create/Write access is not required."

    OBJECT           cItpAclRowStatus              
    MIN-ACCESS       read-only
    DESCRIPTION      "Create/Write access is not required."
    ::= { cItpAclMIBCompliances 1 }

-- Units of Conformance

cItpAclScalarGroup OBJECT-GROUP
    OBJECTS {
             cItpAclConfigLastChanged 
    }
    STATUS current
    DESCRIPTION
            "SP main objects."
    ::= { cItpAclMIBGroups 1 }

cItpAclAccessListGroup OBJECT-GROUP
    OBJECTS {
            cItpAclAction,
            cItpAclParameters,
            cItpAclDpc,
            cItpAclDpcMask,
            cItpAclOpc,
            cItpAclOpcMask,
            cItpAclSi,
            cItpAclPattern,
            cItpAclOffset,
            cItpAclComment,
            cItpAclCgpa,
            cItpAclCgpaMask,
            cItpAclCgpaSsn,
            cItpAclCgpaSsnMask,
            cItpAclCdpa,
            cItpAclCdpaMask,
            cItpAclCdpaSsn,
            cItpAclCdpaSsnMask,
            cItpAclGtiSelector,
            cItpAclGtiTranslateType,
            cItpAclGtiNumberingPlan,
            cItpAclGtiNai,
            cItpAclGtiEsv,
            cItpAclAft,
            cItpAclAftMask,
            cItpAclAftSsn,
            cItpAclAftSsnMask,
            cItpAclRowStatus
    }
    STATUS current
    DESCRIPTION
            "Signaling Point access control list objects."
    ::= { cItpAclMIBGroups 2 }

END
