CISCO-IP-NW-DISCOVERY-CAPABILITY DEFINITIONS ::= BEGIN

IMPORTS
    MODULE-IDENTITY
        FROM SNMPv2-SMI
    AGENT-CAPABILITIES
        FROM SNMPv2-CONF
    ciscoAgentCapability
        FROM CISCO-SMI;

ciscoIpNwDiscoveryCapability MODULE-IDENTITY
    LAST-UPDATED    "200611070000Z"
    ORGANIZATION    "Cisco Systems, Inc."
    CONTACT-INFO
            "Cisco Systems
            Customer Service

            Postal: 170 West Tasman Drive
            San Jose, CA  95134
            USA

            Tel: +1 800 553-NETS

            E-mail: cs-san@cisco.com"
    DESCRIPTION
        "The capabilities description of
        CISCO-IP-NW-DISCOVERY-MIB."
    REVISION        "200611070000Z"
    DESCRIPTION
        "Initial version of this MIB module."
          ::= { ciscoAgentCapability 523 }

cIpNwDiscoverCapSanOSV30R1MDS9000 AGENT-CAPABILITIES
    PRODUCT-RELEASE "Cisco SanOS 3.0 on Cisco MDS 9000                          series devices."
    STATUS          current
    DESCRIPTION     "Cisco IP NW Discovery MIB capabilities"

    SUPPORTS        CISCO-IP-NW-DISCOVERY-MIB
    INCLUDES        {
                        cIpNetworkDiscoveryInfoGroup,
                        cIpNetworkDiscoveryCfgGroup
                    }
    ::= { ciscoIpNwDiscoveryCapability 1 }

END
