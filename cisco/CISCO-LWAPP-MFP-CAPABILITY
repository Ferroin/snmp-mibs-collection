CISCO-LWAPP-MFP-CAPABILITY DEFINITIONS ::= BEGIN

IMPORTS
        MODULE-IDENTITY
                FROM SNMPv2-SMI
        AGENT-CAPABILITIES
                FROM SNMPv2-CONF
        ciscoAgentCapability
                FROM CISCO-SMI;

ciscoLwappMfpCapability MODULE-IDENTITY  
        LAST-UPDATED         "200605160000Z"
        ORGANIZATION         "Cisco Systems, Inc."
        CONTACT-INFO
                "             Cisco Systems
                              Customer Service

                      Postal: 170 W Tasman Drive
                              San Jose, CA  95134
                              USA

                         Tel: +1 800 553-NETS

                      E-mail: cs-wnbu-snmp@cisco.com"
        DESCRIPTION
                "Agent capabilities for CISCO-LWAPP-MFP-MIB. "
        REVISION      "200605160000Z"
        DESCRIPTION
                "Initial version of this MIB module. "
        ::= { ciscoAgentCapability 504 }

ciscoLwappMfpCapabilityCUWNSV4R0 AGENT-CAPABILITIES

PRODUCT-RELEASE         "Cisco Unified Wireless Network Software
                        Release 4.0 for Cisco WLAN Controllers"
        STATUS          current
        DESCRIPTION     "CISCO-LWAPP-MFP-MIB capabilities"

        SUPPORTS        CISCO-LWAPP-MFP-MIB
        INCLUDES        {
                        ciscoLwappMfpConfigGroup,
                        ciscoLwappMfpStatusGroup,
                        ciscoLwappMfpNotifObjsGroup,
                        ciscoLwappMfpNotifsGroup
                        }   

        VARIATION       cLMfpCtrlNotifEnable
        ACCESS          read-only
        DESCRIPTION
                        "This object is implemented as
                        read-only. "

        VARIATION       cLMfpVersionRequired
        ACCESS          read-only
        DESCRIPTION
                        "This object is implemented as
                        read-only. "
        ::= { ciscoLwappMfpCapability 1 }
END
