CISCO-RFC1406-CAPABILITY DEFINITIONS ::= BEGIN

IMPORTS
	MODULE-IDENTITY
		FROM SNMPv2-SMI
	AGENT-CAPABILITIES
		FROM SNMPv2-CONF
	ciscoAgentCapability
		FROM CISCO-SMI;

ciscoRFC1406Capability MODULE-IDENTITY
		LAST-UPDATED	"200210220000Z"
		ORGANIZATION    "Cisco Systems, Inc."
		CONTACT-INFO
			"	Cisco Systems
				Customer Service

			Postal:	170 West Tasman Drive
				San Jose, CA  95134
				USA

			   Tel:	+1 800 553-NETS

			E-mail:	cs-snmp@cisco.com"
		DESCRIPTION
			"Agent capabilities for RFC1406-MIB (DS1 MIB)"
		REVISION	"200210220000Z"
		DESCRIPTION
			"Support SET operation for dsx1LineCoding and
			dsx1LineType"
		REVISION	"200108170000Z"
		DESCRIPTION
			"Support SET operation for dsx1LoopbackConfig object."
		REVISION	"9408180000Z"
		DESCRIPTION
			"Initial version of this MIB module."
		::= { ciscoAgentCapability 102 }

ciscoRFC1406CapabilityV10R02 AGENT-CAPABILITIES

PRODUCT-RELEASE "Cisco IOS 10.2"
STATUS		current
DESCRIPTION	"ds1 capabilities"

SUPPORTS	RFC1406-MIB
INCLUDES	{ ds1Group }

VARIATION	dsx1LineType
ACCESS		read-only
DESCRIPTION	"Unable to create or modify"

VARIATION	dsx1LineCoding
ACCESS		read-only
DESCRIPTION	"Unable to create or modify"

VARIATION	dsx1SendCode
ACCESS		read-only
DESCRIPTION	"Unable to create or modify"

VARIATION	dsx1CircuitIdentifier
ACCESS		read-only
DESCRIPTION	"Unable to create or modify"

VARIATION	dsx1LoopbackConfig
ACCESS		read-only
DESCRIPTION	"Unable to create or modify"

VARIATION	dsx1SignalMode
ACCESS		read-only
DESCRIPTION	"Unable to create or modify"

VARIATION	dsx1TransmitClockSource
ACCESS		read-only
DESCRIPTION	"Unable to create or modify"

VARIATION	dsx1Fdl
ACCESS		read-only
DESCRIPTION	"Unable to create or modify"

VARIATION	dsx1FarEndCurrentIndex
ACCESS		not-implemented
DESCRIPTION	"Table for dsx1FarEndCurrentEntry not supported"

VARIATION	dsx1FarEndTimeElapsed
ACCESS		not-implemented
DESCRIPTION	"Table for dsx1FarEndCurrentEntry not supported"

VARIATION	dsx1FarEndValidIntervals
ACCESS		not-implemented
DESCRIPTION	"Table for dsx1FarEndCurrentEntry not supported"

VARIATION	dsx1FarEndCurrentESs
ACCESS		not-implemented
DESCRIPTION	"Table for dsx1FarEndCurrentEntry not supported"

VARIATION	dsx1FarEndCurrentSESs
ACCESS		not-implemented
DESCRIPTION	"Table for dsx1FarEndCurrentEntry not supported"

VARIATION	dsx1FarEndCurrentSEFSs
ACCESS		not-implemented
DESCRIPTION	"Table for dsx1FarEndCurrentEntry not supported"

VARIATION	dsx1FarEndCurrentUASs
ACCESS		not-implemented
DESCRIPTION	"Table for dsx1FarEndCurrentEntry not supported"

VARIATION	dsx1FarEndCurrentCSSs
ACCESS		not-implemented
DESCRIPTION	"Table for dsx1FarEndCurrentEntry not supported"

VARIATION	dsx1FarEndCurrentLESs
ACCESS		not-implemented
DESCRIPTION	"Table for dsx1FarEndCurrentEntry not supported"

VARIATION	dsx1FarEndCurrentPCVs
ACCESS		not-implemented
DESCRIPTION	"Table for dsx1FarEndCurrentEntry not supported"

VARIATION	dsx1FarEndCurrentBESs
ACCESS		not-implemented
DESCRIPTION	"Table for dsx1FarEndCurrentEntry not supported"

VARIATION	dsx1FarEndCurrentDMs
ACCESS		not-implemented
DESCRIPTION	"Table for dsx1FarEndCurrentEntry not supported"

VARIATION	dsx1FarEndIntervalIndex
ACCESS		not-implemented
DESCRIPTION	"Table for dsx1FarEndIntervalEntry not supported"

VARIATION	dsx1FarEndIntervalNumber
ACCESS		not-implemented
DESCRIPTION	"Table for dsx1FarEndIntervalEntry not supported"

VARIATION	dsx1FarEndIntervalESs
ACCESS		not-implemented
DESCRIPTION	"Table for dsx1FarEndIntervalEntry not supported"

VARIATION	dsx1FarEndIntervalSESs
ACCESS		not-implemented
DESCRIPTION	"Table for dsx1FarEndIntervalEntry not supported"

VARIATION	dsx1FarEndIntervalSEFSs
ACCESS		not-implemented
DESCRIPTION	"Table for dsx1FarEndIntervalEntry not supported"

VARIATION	dsx1FarEndIntervalUASs
ACCESS		not-implemented
DESCRIPTION	"Table for dsx1FarEndIntervalEntry not supported"

VARIATION	dsx1FarEndIntervalCSSs
ACCESS		not-implemented
DESCRIPTION	"Table for dsx1FarEndIntervalEntry not supported"

VARIATION	dsx1FarEndIntervalLESs
ACCESS		not-implemented
DESCRIPTION	"Table for dsx1FarEndIntervalEntry not supported"

VARIATION	dsx1FarEndIntervalPCVs
ACCESS		not-implemented
DESCRIPTION	"Table for dsx1FarEndIntervalEntry not supported"

VARIATION	dsx1FarEndIntervalBESs
ACCESS		not-implemented
DESCRIPTION	"Table for dsx1FarEndIntervalEntry not supported"

VARIATION	dsx1FarEndIntervalDMs
ACCESS		not-implemented
DESCRIPTION	"Table for dsx1FarEndIntervalEntry not supported"

VARIATION	dsx1FarEndTotalIndex
ACCESS		not-implemented
DESCRIPTION	"Table for dsx1FarEndTotalEntry not supported"

VARIATION	dsx1FarEndTotalESs
ACCESS		not-implemented
DESCRIPTION	"Table for dsx1FarEndTotalEntry not supported"

VARIATION	dsx1FarEndTotalSESs
ACCESS		not-implemented
DESCRIPTION	"Table for dsx1FarEndTotalEntry not supported"

VARIATION	dsx1FarEndTotalSEFSs
ACCESS		not-implemented
DESCRIPTION	"Table for dsx1FarEndTotalEntry not supported"

VARIATION	dsx1FarEndTotalUASs
ACCESS		not-implemented
DESCRIPTION	"Table for dsx1FarEndTotalEntry not supported"

VARIATION	dsx1FarEndTotalCSSs
ACCESS		not-implemented
DESCRIPTION	"Table for dsx1FarEndTotalEntry not supported"

VARIATION	dsx1FarEndTotalLESs
ACCESS		not-implemented
DESCRIPTION	"Table for dsx1FarEndTotalEntry not supported"

VARIATION	dsx1FarEndTotalPCVs
ACCESS		not-implemented
DESCRIPTION	"Table for dsx1FarEndTotalEntry not supported"

VARIATION	dsx1FarEndTotalBESs
ACCESS		not-implemented
DESCRIPTION	"Table for dsx1FarEndTotalEntry not supported"

VARIATION	dsx1FarEndTotalDMs
ACCESS		not-implemented
DESCRIPTION	"Table for dsx1FarEndTotalEntry not supported"

VARIATION	dsx1FracIfIndex
ACCESS		read-only
DESCRIPTION	"Unable to create or modify"
	::= { ciscoRFC1406Capability 1 }

ciscoRFC1406CapabilityV122R12T AGENT-CAPABILITIES

PRODUCT-RELEASE "Cisco IOS 12.2(12)T"
STATUS          obsolete -- superseded by 
                         -- ciscoRFC1406CapabilityV122R12TRev2
DESCRIPTION     "ds1 capabilities"

SUPPORTS        RFC1406-MIB
INCLUDES        { ds1Group }

VARIATION       dsx1LineType
ACCESS          read-only
DESCRIPTION     "Unable to create or modify"

VARIATION       dsx1LineCoding
ACCESS          read-only
DESCRIPTION     "Unable to create or modify"

VARIATION       dsx1SendCode
ACCESS          read-only
DESCRIPTION     "Unable to create or modify"

VARIATION       dsx1CircuitIdentifier
ACCESS          read-only
DESCRIPTION     "Unable to create or modify"

VARIATION       dsx1SignalMode
ACCESS          read-only
DESCRIPTION     "Unable to create or modify"

VARIATION       dsx1TransmitClockSource
ACCESS          read-only
DESCRIPTION     "Unable to create or modify"

VARIATION       dsx1Fdl
ACCESS          read-only
DESCRIPTION     "Unable to create or modify"

VARIATION       dsx1FarEndCurrentIndex
ACCESS          not-implemented
DESCRIPTION     "Table for dsx1FarEndCurrentEntry not supported"

VARIATION       dsx1FarEndTimeElapsed
ACCESS          not-implemented
DESCRIPTION     "Table for dsx1FarEndCurrentEntry not supported"

VARIATION       dsx1FarEndValidIntervals
ACCESS          not-implemented
DESCRIPTION     "Table for dsx1FarEndCurrentEntry not supported"

VARIATION       dsx1FarEndCurrentESs
ACCESS          not-implemented
DESCRIPTION     "Table for dsx1FarEndCurrentEntry not supported"

VARIATION       dsx1FarEndCurrentSESs
ACCESS          not-implemented
DESCRIPTION     "Table for dsx1FarEndCurrentEntry not supported"

VARIATION       dsx1FarEndCurrentSEFSs
ACCESS          not-implemented
DESCRIPTION     "Table for dsx1FarEndCurrentEntry not supported"

VARIATION       dsx1FarEndCurrentUASs
ACCESS          not-implemented
DESCRIPTION     "Table for dsx1FarEndCurrentEntry not supported"

VARIATION       dsx1FarEndCurrentCSSs
ACCESS          not-implemented
DESCRIPTION     "Table for dsx1FarEndCurrentEntry not supported"

VARIATION       dsx1FarEndCurrentLESs
ACCESS          not-implemented
DESCRIPTION     "Table for dsx1FarEndCurrentEntry not supported"

VARIATION       dsx1FarEndCurrentPCVs
ACCESS          not-implemented
DESCRIPTION     "Table for dsx1FarEndCurrentEntry not supported"

VARIATION       dsx1FarEndCurrentBESs
ACCESS          not-implemented
DESCRIPTION     "Table for dsx1FarEndCurrentEntry not supported"

VARIATION       dsx1FarEndCurrentDMs
ACCESS          not-implemented
DESCRIPTION     "Table for dsx1FarEndCurrentEntry not supported"

VARIATION       dsx1FarEndIntervalIndex
ACCESS          not-implemented
DESCRIPTION     "Table for dsx1FarEndIntervalEntry not supported"

VARIATION       dsx1FarEndIntervalNumber
ACCESS          not-implemented
DESCRIPTION     "Table for dsx1FarEndIntervalEntry not supported"

VARIATION       dsx1FarEndIntervalESs
ACCESS          not-implemented
DESCRIPTION     "Table for dsx1FarEndIntervalEntry not supported"

VARIATION       dsx1FarEndIntervalSESs
ACCESS          not-implemented
DESCRIPTION     "Table for dsx1FarEndIntervalEntry not supported"

VARIATION       dsx1FarEndIntervalSEFSs
ACCESS          not-implemented
DESCRIPTION     "Table for dsx1FarEndIntervalEntry not supported"

VARIATION       dsx1FarEndIntervalUASs
ACCESS          not-implemented
DESCRIPTION     "Table for dsx1FarEndIntervalEntry not supported"

VARIATION       dsx1FarEndIntervalCSSs
ACCESS          not-implemented
DESCRIPTION     "Table for dsx1FarEndIntervalEntry not supported"

VARIATION       dsx1FarEndIntervalLESs
ACCESS          not-implemented
DESCRIPTION     "Table for dsx1FarEndIntervalEntry not supported"

VARIATION       dsx1FarEndIntervalPCVs
ACCESS          not-implemented
DESCRIPTION     "Table for dsx1FarEndIntervalEntry not supported"

VARIATION       dsx1FarEndIntervalBESs
ACCESS          not-implemented
DESCRIPTION     "Table for dsx1FarEndIntervalEntry not supported"

VARIATION       dsx1FarEndIntervalDMs
ACCESS          not-implemented
DESCRIPTION     "Table for dsx1FarEndIntervalEntry not supported"

VARIATION       dsx1FarEndTotalIndex
ACCESS          not-implemented
DESCRIPTION     "Table for dsx1FarEndTotalEntry not supported"

VARIATION       dsx1FarEndTotalESs
ACCESS          not-implemented
DESCRIPTION     "Table for dsx1FarEndTotalEntry not supported"

VARIATION       dsx1FarEndTotalSESs
ACCESS          not-implemented
DESCRIPTION     "Table for dsx1FarEndTotalEntry not supported"

VARIATION       dsx1FarEndTotalSEFSs
ACCESS          not-implemented
DESCRIPTION     "Table for dsx1FarEndTotalEntry not supported"

VARIATION       dsx1FarEndTotalUASs
ACCESS          not-implemented
DESCRIPTION     "Table for dsx1FarEndTotalEntry not supported"

VARIATION       dsx1FarEndTotalCSSs
ACCESS          not-implemented
DESCRIPTION     "Table for dsx1FarEndTotalEntry not supported"

VARIATION       dsx1FarEndTotalLESs
ACCESS          not-implemented
DESCRIPTION     "Table for dsx1FarEndTotalEntry not supported"

VARIATION       dsx1FarEndTotalPCVs
ACCESS          not-implemented
DESCRIPTION     "Table for dsx1FarEndTotalEntry not supported"

VARIATION       dsx1FarEndTotalBESs
ACCESS          not-implemented
DESCRIPTION     "Table for dsx1FarEndTotalEntry not supported"

VARIATION       dsx1FarEndTotalDMs
ACCESS          not-implemented
DESCRIPTION     "Table for dsx1FarEndTotalEntry not supported"

VARIATION       dsx1FracIfIndex
ACCESS          read-only
DESCRIPTION     "Unable to create or modify"
	::= { ciscoRFC1406Capability 2 }

ciscoRFC1406CapabilityV122R12TRev2 AGENT-CAPABILITIES

PRODUCT-RELEASE "Cisco IOS 12.2(12)T"
STATUS          current
DESCRIPTION     "ds1 capabilities"

SUPPORTS        RFC1406-MIB
INCLUDES        { ds1Group }

VARIATION       dsx1SendCode
ACCESS          read-only
DESCRIPTION     "Unable to create or modify"

VARIATION       dsx1CircuitIdentifier
ACCESS          read-only
DESCRIPTION     "Unable to create or modify"

VARIATION       dsx1SignalMode
ACCESS          read-only
DESCRIPTION     "Unable to create or modify"

VARIATION       dsx1TransmitClockSource
ACCESS          read-only
DESCRIPTION     "Unable to create or modify"

VARIATION       dsx1Fdl
ACCESS          read-only
DESCRIPTION     "Unable to create or modify"

VARIATION       dsx1FarEndCurrentEntry
ACCESS          not-implemented
DESCRIPTION     "Table not supported"

VARIATION       dsx1FarEndIntervalEntry
ACCESS          not-implemented
DESCRIPTION     "Table not supported"

VARIATION       dsx1FarEndTotalEntry
ACCESS          not-implemented
DESCRIPTION     "Table not supported"

VARIATION       dsx1FracIfIndex
ACCESS          read-only
DESCRIPTION     "Unable to create or modify"
        ::= { ciscoRFC1406Capability 3 }

END
