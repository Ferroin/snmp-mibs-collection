CISCO-CAS-IF-EXT-CAPABILITY DEFINITIONS ::= BEGIN
IMPORTS
        MODULE-IDENTITY,
        Unsigned32, Integer32
                FROM SNMPv2-SMI
        AGENT-CAPABILITIES
                FROM SNMPv2-CONF
        ciscoAgentCapability
                FROM CISCO-SMI;

ciscoCasIfExtCapability MODULE-IDENTITY
    LAST-UPDATED "200401190000Z"
    ORGANIZATION "Cisco Systems, Inc."
    CONTACT-INFO
        "        Cisco Systems
                 Customer Service
        Postal: 170 W Tasman Drive
                San Jose, CA 95134
                USA
           Tel: +1 800 553-NETS
        E-mail: cs-voice-gateway@cisco.com"
    DESCRIPTION
            "The agent capabilities for CISCO-CAS-IF-EXT-MIB." 

        REVISION "200401190000Z"
        DESCRIPTION
            "Initial version of this MIB module."
        ::= { ciscoAgentCapability 349 }

    ciscoCasIfExtCapabilityV5R00 AGENT-CAPABILITIES

        PRODUCT-RELEASE "MGX8850 Release 5.0.0"
        STATUS          current
        DESCRIPTION     "CISCO-CAS-IF-EXT-MIB capabilities for Voice 
                         Switch Service Module(VXSM) in 
                         Release 5.0.0." 

        SUPPORTS        CISCO-CAS-IF-EXT-MIB
        INCLUDES        { 
			    ccasIfExtVoiceCfgGroup,
                            ccasIfExtBulkGroup
                        }

        VARIATION       ccasIfExtVoiceCfgLifNumber
        SYNTAX          Unsigned32 (0..1)
        DESCRIPTION     "Either no LIF associated or 
                         associated with LIF number 1."

        VARIATION       ccasIfExtVoiceCfgCcntrlProfile
        SYNTAX          Unsigned32 (0..25)
        DESCRIPTION     "Either default profile 0, or H.248 profile.
                         VXSM supports only 25 H.248 profiles." 

        VARIATION       ccasIfExtVoiceCfgVadEnabled
        DEFVAL          { true } 
        DESCRIPTION     "Add default value 'true' since MIB doesn't 
                         define default value" 

        VARIATION       ccasIfExtVoiceCfgVadTimer
        SYNTAX          Integer32(250..500)
        DESCRIPTION     "Limited data range of values are supported."

        VARIATION       ccasIfExtVoiceCfgModemPassThru
        SYNTAX          INTEGER { 
                                 passThruDisabled (1), 
                                 passThruNseCA (8) 
                        }
        DEFVAL          { passThruDisabled } 
        DESCRIPTION     "Limited range of values are supported." 

        VARIATION       ccasIfExtVoiceCfgUpspeedCodec
        SYNTAX          INTEGER {
                            other            (1),
                            g726r32000       (14),
                            g711ulawr64000   (15),
                            g711Alawr64000   (16),
                            clearChannel     (27),
                            g726r40000       (28)
                        }
        DEFVAL          { g711ulawr64000 } 
        DESCRIPTION     "Limited range of values are supported." 

        VARIATION       ccasIfExtVoiceCfgT38MaxFaxTxRate
        ACCESS          not-implemented
        DESCRIPTION     "Not supported."

        VARIATION       ccasIfExtVoiceCfgT38HsPktPeriod
        ACCESS          not-implemented
        DESCRIPTION     "Not supported."

        VARIATION       ccasIfExtVoiceCfgT38HsRedundancy
        ACCESS          not-implemented
        DESCRIPTION     "Not supported."

        VARIATION       ccasIfExtVoiceCfgRepetition
        SYNTAX          Unsigned32 (1..31)
        DESCRIPTION     "Valid range is 1 to 31.
                         The order of operation is iterated through
                         the ccasGrpCfgIndex."

        VARIATION       ccasIfExtVoiceCfgBulkCfgOwner
        ACCESS          not-implemented
        DESCRIPTION     "Not supported."

        VARIATION       ccasIfExtVoiceCfgBulkCfgResult
        ACCESS          not-implemented
        DESCRIPTION     "Not supported."

        VARIATION       ccasIfExtVoiceCfgTonePlan
        DEFVAL          { 0 } 
        DESCRIPTION     "Default to default tone plan ID in 
                         the gateway."

        VARIATION       ccasIfExtVoiceCfgGwyLinkId
        SYNTAX          Integer32 (0..1)  
        DESCRIPTION     "Limited range is supported."

        VARIATION       ccasIfExtVoiceCfgH248PkgIds
        SYNTAX          BITS {
                                pkgG    (0),
                                pkgDG   (4),
                                pkgDD   (5),
                                pkgCG   (6),
                                pkgCT   (8),
                                pkgTDMC (11),
                                pkgAN   (12),
                                pkgSrvTn (15)
                        }
        DESCRIPTION     "Limited range is supported."

        VARIATION       ccasIfExtDs0GrpRepetition
        SYNTAX          Unsigned32 (1..336)
        DESCRIPTION     "Valid range is 1 to 336."

        VARIATION       ccasIfExtDs0GrpRepeatOwner
        ACCESS          not-implemented
        DESCRIPTION     "Not supported."

        VARIATION       ccasIfExtDs0GrpRepeatResult
        ACCESS          not-implemented
        DESCRIPTION     "Not supported."
    ::= { ciscoCasIfExtCapability 1 }

END
