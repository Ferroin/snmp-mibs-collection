CISCO-SVI-AUTOSTATE-CAPABILITY DEFINITIONS ::= BEGIN

IMPORTS
        MODULE-IDENTITY
                FROM SNMPv2-SMI

        AGENT-CAPABILITIES
                FROM SNMPv2-CONF

        TruthValue
                FROM SNMPv2-TC

        ciscoAgentCapability
                FROM CISCO-SMI;

ciscoSVIAutostateCapability MODULE-IDENTITY
        LAST-UPDATED    "200404080000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 CISCO-SVI-AUTOSTATE-MIB."

        REVISION        "200404080000Z"
        DESCRIPTION
                "Initial version of this MIB module."
        ::= { ciscoAgentCapability 384 }

csaCapabilityCatOSV08R0301Cat6k AGENT-CAPABILITIES
    PRODUCT-RELEASE      "Cisco CatOS 8.3(1) on Catalyst 6000/6500
                          and Cisco 7600 series devices."
    STATUS               current
    DESCRIPTION          "CISCO-SVI-AUTOSTATE-MIB capabilities."

    SUPPORTS             CISCO-SVI-AUTOSTATE-MIB
        INCLUDES         { ciscoSVIAutostateGroup,
                           ciscoSVITrackedVlanGroup
                         }
    ::= { ciscoSVIAutostateCapability 1 }

csaCapabilityV12R0218SXDCat6k AGENT-CAPABILITIES
    PRODUCT-RELEASE      "Cisco IOS 12.2(18)SXD on Catalyst 6000/6500
                          and Cisco 7600 series devices."
    STATUS               current
    DESCRIPTION          "CISCO-SVI-AUTOSTATE-MIB capabilities."

    SUPPORTS             CISCO-SVI-AUTOSTATE-MIB
        INCLUDES         { 
                           ciscoSVIAutostateGroup 
                         }
        VARIATION        csaFeatureEnable
            SYNTAX       TruthValue { true(1) } 
            DESCRIPTION  "Only true(1) is supported."

        VARIATION        csaInterfaceMode
            SYNTAX       INTEGER { normal(1),
                                   exclude(2) }
            DESCRIPTION  "Only limited set of enumerated 
                          values are supported."
    ::= { ciscoSVIAutostateCapability 2 }
END
