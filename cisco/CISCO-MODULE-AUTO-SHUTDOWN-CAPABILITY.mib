CISCO-MODULE-AUTO-SHUTDOWN-CAPABILITY DEFINITIONS ::= BEGIN

IMPORTS
    MODULE-IDENTITY,
    Unsigned32
        FROM SNMPv2-SMI
    AGENT-CAPABILITIES
        FROM SNMPv2-CONF
    ciscoAgentCapability
        FROM CISCO-SMI;

cmAutoShutdownCapability MODULE-IDENTITY
    LAST-UPDATED    "200810290000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com"
    DESCRIPTION
        "The capabilities description of
        CISCO-MODULE-AUTO-SHUTDOWN-MIB."
    REVISION        "200810290000Z"
    DESCRIPTION
        "Add the capability statements
        cmAutoShutdownCapV12R0233SXH3PCat6K and
        cmAutoShutdownCapV12R0233SXIPCat6K."
    REVISION        "200401190000Z"
    DESCRIPTION
        "Initial version of this MIB module."
    ::= { ciscoAgentCapability 386 }

cmAutoShutdownCapCatOSV08R0301 AGENT-CAPABILITIES
    PRODUCT-RELEASE "Cisco CatOS 8.3(1) on Catalyst 6000/6500
                    and Cisco 7600 series devices."
    STATUS          current
    DESCRIPTION
        "CISCO-MODULE-AUTO-SHUTDOWN-MIB capabilities."

    SUPPORTS        CISCO-MODULE-AUTO-SHUTDOWN-MIB
    INCLUDES        {
                        cmasModuleGroup,
                        cmasNotificationEnableGroup,
                        cmasNotificationsGroup
                    }
    ::= { cmAutoShutdownCapability 1 }

cmAutoShutdownCapV12R0233SXH3PCat6K AGENT-CAPABILITIES
    PRODUCT-RELEASE "Cisco IOS 12.2(33)SXH3 on Catalyst 6000/6500
                        series devices."
    STATUS          current
    DESCRIPTION
        "CISCO-MODULE-AUTO-SHUTDOWN-MIB capabilities."

    SUPPORTS        CISCO-MODULE-AUTO-SHUTDOWN-MIB
    INCLUDES        {
                        cmasModuleSysActionGroup,
                        cmasNotificationsGroup2
                    }
    ::= { cmAutoShutdownCapability 2 }

cmAutoShutdownCapV12R0233SXIPCat6K AGENT-CAPABILITIES
    PRODUCT-RELEASE "Cisco IOS 12.2(33)SXI on Catalyst 6000/6500
                        series devices."
    STATUS          current
    DESCRIPTION
        "CISCO-MODULE-AUTO-SHUTDOWN-MIB capabilities."

    SUPPORTS        CISCO-MODULE-AUTO-SHUTDOWN-MIB
    INCLUDES        {
                        cmasModuleSysActionGroup,
                        cmasNotificationsGroup2,
                        cmasModuleGroup,
                        cmasNotificationEnableGroup,
                        cmasNotificationsGroup
                    }
    VARIATION       cmasFrequency
    SYNTAX          Unsigned32 (2..255)
    DESCRIPTION
        "Only a limited set of values is supported."

    VARIATION       cmasPeriod
    SYNTAX          Unsigned32 (1..255)
    DESCRIPTION
        "Only a limited set of values is supported."
    ::= { cmAutoShutdownCapability 3 }

END
