CISCO-IPV6-MLD-CAPABILITY DEFINITIONS ::= BEGIN

IMPORTS
        MODULE-IDENTITY
                FROM SNMPv2-SMI
        AGENT-CAPABILITIES
                FROM SNMPv2-CONF
        ciscoAgentCapability
                FROM CISCO-SMI;

cipv6mldCapability MODULE-IDENTITY
        LAST-UPDATED    "200601070000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com
                        cs-snmp@cisco.com"
        DESCRIPTION
                "The capabilities description of
                 IPV6-MLD-MIB."

        REVISION        "200601070000Z"
        DESCRIPTION
                "Initial version of this MIB module."
        ::= { ciscoAgentCapability 470 }

ciscoIpv6MldCapCRS1V3R02 AGENT-CAPABILITIES
    PRODUCT-RELEASE     "Cisco IOS XR 3.2.0 for CRS-1"
    STATUS              current
    DESCRIPTION         "IPV6-MLD-MIB capabilities for
                        IOS XR release 3.2.0"

    SUPPORTS            IPV6-MLD-MIB
        INCLUDES        { mldBaseMIBGroup,
                          mldRouterMIBGroup,
                          mldHostMIBGroup,
                          mldProxyMIBGroup }
    ::= { cipv6mldCapability 1 }

END
