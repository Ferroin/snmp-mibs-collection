CISCO-QOS-TC-MIB DEFINITIONS ::= BEGIN

IMPORTS
     MODULE-IDENTITY,
     Unsigned32           
         FROM SNMPv2-SMI
     TEXTUAL-CONVENTION         
         FROM SNMPv2-TC
     ciscoMgmt                  
         FROM CISCO-SMI;

ciscoQosTcMIB MODULE-IDENTITY
    LAST-UPDATED    "200703050000Z"
    ORGANIZATION    "Cisco Systems, Inc."
    CONTACT-INFO
        "       Cisco Systems
                Customer Service

        Postal: 170 W Tasman Drive
                San Jose, CA 95134

           Tel: +1 800 553-NETS

        E-mail: cs-snmp@cisco.com"
    DESCRIPTION
        "This module defines the textual conventions used within
         Cisco Qos MIBs."
    REVISION      "200703050000Z"
    DESCRIPTION
         "Add QosPolicerType textual convention."
    REVISION      "200609181200Z"
    DESCRIPTION
         "The initial version of this MIB module."
    ::= { ciscoMgmt 573 } 

--
--  Definitions of textual convention
--

QosIpPrecedence ::= TEXTUAL-CONVENTION
    STATUS  current
    DESCRIPTION
        "Indicates the IP precedence."
    REFERENCE
        "RFC791 INTERNET PROTOCOL, Chapter 3.1"
    SYNTAX  Unsigned32 (0..7)

QosQueueNumber ::= TEXTUAL-CONVENTION
    STATUS  current
    DESCRIPTION
        "An integer indicates a queue number."
    SYNTAX  Unsigned32 

QosThresholdNumber ::= TEXTUAL-CONVENTION
    STATUS  current
    DESCRIPTION
        "An integer indicates a threshold number."
    SYNTAX  Unsigned32 

QosMplsExpValue ::= TEXTUAL-CONVENTION
    STATUS  current
    DESCRIPTION
        "An integer indicates a MPLS-EXP (experimental) value." 
    SYNTAX  Unsigned32 (0..7)

QosMutationMapName ::= TEXTUAL-CONVENTION
    DISPLAY-HINT "99a"
    STATUS  current
    DESCRIPTION
        "An octet string, preferably in human-readable form,
        describes the name of a mutation map."
    SYNTAX  OCTET STRING (SIZE (1..99))

QosMutationMapNameOrEmpty ::= TEXTUAL-CONVENTION
    DISPLAY-HINT "99a"
    STATUS  current
    DESCRIPTION
        "This textual convention is an extension of the
        QosMutationMapName convention. The latter defines a
        non-empty mutation map name. This extension permits
        the addtional value of empty string."
    SYNTAX  OCTET STRING (SIZE (0..99))

QosPolicerType ::= TEXTUAL-CONVENTION
    STATUS  current
    DESCRIPTION
        "An integer indicating the type of a QoS policer.

         microflow(1):     a microflow policer.
         aggregate(2):     an aggregate policer."
    SYNTAX INTEGER { microflow(1), aggregate(2) } 

END
