CISCO-RHINO-MIB DEFINITIONS ::= BEGIN

IMPORTS
                MODULE-IDENTITY,
                OBJECT-TYPE,
                NOTIFICATION-TYPE,
                Counter32,
                Gauge32,
                Integer32
                        FROM SNMPv2-SMI
                TEXTUAL-CONVENTION,
                TimeStamp,
                DisplayString,
                TruthValue
                        FROM SNMPv2-TC
                InterfaceIndex
                        FROM IF-MIB
                MODULE-COMPLIANCE, 
                OBJECT-GROUP,
                NOTIFICATION-GROUP
                        FROM SNMPv2-CONF
                ifIndex
                        FROM RFC1213-MIB
                workgroup
                        FROM CISCO-SMI
                Unsigned32
                        FROM CISCO-TC;

ciscoLS1010ChassisMIB MODULE-IDENTITY
        LAST-UPDATED    "200103290000Z"
        ORGANIZATION    "Cisco Systems, Inc."
        CONTACT-INFO
                "       Cisco Systems
                        Customer Service

                Postal: 170 W Tasman Drive
                        San Jose, CA  95134
                        USA

                   Tel: +1 800 553-NETS

                E-mail: cs-atm@cisco.com"
        DESCRIPTION
                "-Added enum sixPortDS3 for ciscoLS1010SubModuleType.
                 -Added enum nodeSwitchProcessor2ndGeneration for
                  ciscoLS1010ModuleType. 
                 -Added enum ac175W for psType.
                 -Added Group object for Notification objects." 
        REVISION        "200103290000Z" 
        DESCRIPTION
                "-Added enum ACL Daughter card SubModuleType for
                  Cat8540.
                 -Added enum for TS Carrier Module.
                 -Added enum for medium SingleModeLRFiber for
                  OC3 and OC12 ATM pams."
        REVISION        "200102150000Z"
        DESCRIPTION
                "-Added object for module hardware minor version.
                 -Added objects for module and submodule serial
                  number in string format.
                 -Deprecated integer serial number objects for module
                  and submodule.
                 -Added enumeration to submodule type for 
                  NRP2 for 6400.
                 -Reduce to single Module Compliance for clarity."
        REVISION        "200007200000Z"
        DESCRIPTION
                "Added enums XPIF GE, ATM, and POS SubModuleTypes for 
                 Cat8540c. Added enums cmpmCarrier ModuleType for 
                 Cat8540c."
        REVISION        "200004110000Z"
        DESCRIPTION
                "Added enums in ChassisSysType & ChassisBkplType for 
                 Cat4908g"
        REVISION        "200002070000Z"
        DESCRIPTION
                "Added enums for OC48c LR, and Dual Slot modules."
        REVISION        "9911300000Z"
        DESCRIPTION
                "Added enums for OC48c and ARM modules."
        REVISION        "9910040000Z"
        DESCRIPTION
                "Added enums in ChassisSysType & ChassisBkplType for
                 C2948."
        REVISION        "9906290000Z"
        DESCRIPTION
                "Added enums in subModuleType for the IMA & ATM25M4P 
                 PAMs."
        REVISION        "9906170000Z"
        DESCRIPTION
                "Added enumerations for Cat6k"
        REVISION        "9903120000Z"
        DESCRIPTION
                "Added enumerations for TGX8750."
        REVISION        "9812020000Z"
        DESCRIPTION
                "Consolidate changes from C6400, C8500, FR-PAM, 
                 new modules."
        REVISION        "9810260000Z"
        DESCRIPTION
                "Added new enum c8510. Also new tables for enet 
                 ports and  LEDs."
        REVISION        "9807130000Z"
        DESCRIPTION
                "Rhino ATM Switch Chassis MIB"
        REVISION        "9711200000Z"
        DESCRIPTION
                "Added ciscoAtmInterceptEndToEndOamFlow. Editorial changes."
        REVISION        "9707220000Z"
        DESCRIPTION
                "Added  clocking objects "
        REVISION        "9702040000Z"
        DESCRIPTION
                "Added object ciscoLS1010SubModuleHwVersionMinor."
        REVISION        "9610020000Z"
        DESCRIPTION
                "Added a new PsType for -48 VDC."
        REVISION        "9510020000Z"
        DESCRIPTION
                "Initial version of this MIB module."
        ::= { workgroup 11 }

ciscoLS1010ChassisMIBObjects OBJECT IDENTIFIER ::= { ciscoLS1010ChassisMIB 1 }
ciscoLS1010ChassisGroup OBJECT IDENTIFIER ::= { ciscoLS1010ChassisMIBObjects 1 }
ciscoLS1010ModuleGroup OBJECT IDENTIFIER ::= { ciscoLS1010ChassisMIBObjects 2 }
ciscoLS1010SubModuleGroup OBJECT IDENTIFIER ::= { ciscoLS1010ChassisMIBObjects 3 }
ciscoLS1010PortGroup OBJECT IDENTIFIER ::= { ciscoLS1010ChassisMIBObjects 4 }

ciscoLS1010CpuSwitchGroup OBJECT IDENTIFIER ::= { ciscoLS1010ChassisMIBObjects 5 }

clsEnetPortGroup OBJECT IDENTIFIER ::= { ciscoLS1010ChassisMIBObjects 6 }
clsPortLedGroup OBJECT IDENTIFIER ::= { ciscoLS1010ChassisMIBObjects 7 }

    PsType ::= TEXTUAL-CONVENTION
        STATUS    current
        DESCRIPTION
        "Power Supply type"
        SYNTAX     INTEGER {    powerone(0),            -- vendor 
                                astec(1),
                                minus48VDC(2),
                                empty(3),               -- not present
                                ac1100W(4),             -- C5500
                                ac1200W(5),             -- C5500
                                dc1200W(6),             -- C5500
                                pem(7),  -- C6400, DC Power entry module
                                ac1360W(8),
                                dc1360W(9),
                                ac2000W(10),
                                dc2000W(11), 
                                acpem(12), --C6400,AC Power entry module
                                ac175W(13)              -- Domino
                                }

    OperStatus ::= TEXTUAL-CONVENTION
        STATUS    current
        DESCRIPTION
        "Operational status of a chassis component. 

         fanAlarm(4) is only applicable to the C5500 power supply. 
         A fault(3) supercedes a fanAlarm(4).

         partialFault(5) & empty(6) are used by the Cisco6400 for the
         fan status to indicate partial fans failure & fan not present.
         A fault(3) value indicates total fans failure in the C6400."
        SYNTAX     INTEGER {    unknown(1),      -- none of the following
                                ok(2),           -- status ok
                                fault(3),        -- major problem
                                fanAlarm(4),   -- for C5500 power supply
                                partialFault(5), -- partial failure
                                empty(6)         -- not present
                                }

    AdminStatus ::= TEXTUAL-CONVENTION
        STATUS    current
        DESCRIPTION
        "Admin status of a chassis component."
        SYNTAX     INTEGER {    enable(1),     
                                disable(2),
                                reset(3)
                                }

    Led ::= TEXTUAL-CONVENTION
        STATUS    current
        DESCRIPTION
        "LED status"
        SYNTAX     INTEGER {    off(1),     
                                green(2),
                                red(3),
                                yellow(4),
                                blinkgreen(5), 
                                blinkyellow(6),
                                blinkred(7),
                                unknown(8)
                                }

    PcmciaType ::= TEXTUAL-CONVENTION
        STATUS    current
        DESCRIPTION
        "PCMCIA card type"
        SYNTAX     INTEGER {    unknown(1),             -- vendor 
                                empty(2),               -- not present
                                flash(3),
                                disk(4)
                                }

-- the chassis group

ciscoLS1010ChassisSysType OBJECT-TYPE
        SYNTAX        INTEGER {
                                other(1),        -- none of the following
                                ls1010(2),
                                c8510(3),        
                                cisco6400(4),
                                c8540(5),
                                tgx8750(6),
                                wsx6302(7),    -- C6K Multilayer Switch
                                c2948g(8),
                                c4908g(9)       
                                }
        MAX-ACCESS    read-only
        STATUS        current
        DESCRIPTION   "The chassis system type."
        ::= { ciscoLS1010ChassisGroup 1 }

ciscoLS1010ChassisBkplType OBJECT-TYPE
        SYNTAX        INTEGER {
                                other(1),        -- none of the following
                                atm(2),          -- LS1010 chassis
                                c5500(3),        -- Catalyst5500 chassis
                                cisco6400(4),    
                                c8510(5),        
                                c8540(6),
                                tgx8750(7), 
                                cat6000(8),    -- C6K Multilayer Switch
                                c2948g(9),
                                c4908g(10)
                                }
        MAX-ACCESS    read-only
        STATUS        current
        DESCRIPTION   "The chassis backplane type."
        ::= { ciscoLS1010ChassisGroup 2 }

ciscoLS1010ChassisPs0Type OBJECT-TYPE
        SYNTAX        PsType
        MAX-ACCESS    read-only
        STATUS        current
        DESCRIPTION   "Type of power supply number 1."
        ::= { ciscoLS1010ChassisGroup 3 }

ciscoLS1010ChassisPs0AdminStatus OBJECT-TYPE
        SYNTAX        AdminStatus
        MAX-ACCESS    read-write
        STATUS        current
        DESCRIPTION   "Enable or disable power supply 1."
        ::= { ciscoLS1010ChassisGroup 4 }

ciscoLS1010ChassisPs0Status OBJECT-TYPE
        SYNTAX        OperStatus
        MAX-ACCESS    read-only
        STATUS        current
        DESCRIPTION   "Status of power supply number 1."
        ::= { ciscoLS1010ChassisGroup 5 }

ciscoLS1010ChassisPs0Led OBJECT-TYPE
        SYNTAX        Led
        MAX-ACCESS    read-only
        STATUS        current
        DESCRIPTION   "LED Status of power supply number 1."
        ::= { ciscoLS1010ChassisGroup 6 }

ciscoLS1010ChassisPs1Type OBJECT-TYPE
        SYNTAX        PsType
        MAX-ACCESS    read-only
        STATUS        current
        DESCRIPTION   "Type of power supply number 2."
        ::= { ciscoLS1010ChassisGroup 7 }

ciscoLS1010ChassisPs1AdminStatus OBJECT-TYPE
        SYNTAX        AdminStatus
        MAX-ACCESS    read-write
        STATUS        current
        DESCRIPTION   "Enable or disable power supply 2."
        ::= { ciscoLS1010ChassisGroup 8 }

ciscoLS1010ChassisPs1Status OBJECT-TYPE
        SYNTAX        OperStatus
        MAX-ACCESS    read-only
        STATUS        current
        DESCRIPTION   "Status of power supply number 2."
        ::= { ciscoLS1010ChassisGroup 9 }

ciscoLS1010ChassisPs1Led OBJECT-TYPE
        SYNTAX        Led
        MAX-ACCESS    read-only
        STATUS        current
        DESCRIPTION   "LED Status of power supply number 2."
        ::= { ciscoLS1010ChassisGroup 10 }

ciscoLS1010ChassisFanStatus OBJECT-TYPE
        SYNTAX        OperStatus
        MAX-ACCESS    read-only
        STATUS        current
        DESCRIPTION   "Status of the chassis fan."
        ::= { ciscoLS1010ChassisGroup 11 }

ciscoLS1010ChassisFanLed OBJECT-TYPE
        SYNTAX        Led
        MAX-ACCESS    read-only
        STATUS        current
        DESCRIPTION   "LED Status of fan."
        ::= { ciscoLS1010ChassisGroup 12 }

ciscoLS1010ChassisCardStatusLed OBJECT-TYPE
        SYNTAX        Led
        MAX-ACCESS    read-only
        STATUS        current
        DESCRIPTION   "LED Status of CPU card."
        ::= { ciscoLS1010ChassisGroup 13 }

ciscoLS1010ChassisEnetLinkLed OBJECT-TYPE
        SYNTAX        Led
        MAX-ACCESS    read-only
        STATUS        current
        DESCRIPTION   "Ethernet link status LED of CPU card."
        ::= { ciscoLS1010ChassisGroup 14 }

ciscoLS1010Chassis12VoltStatus OBJECT-TYPE
        SYNTAX        INTEGER { 
                                ok(1), 
                                outOfTolerance(2),
                                unknown(3) 
                                }
        MAX-ACCESS    read-only
        STATUS        current
        DESCRIPTION   "The chassis 12V status."
        ::= { ciscoLS1010ChassisGroup 15 }

ciscoLS1010ChassisTempStatus OBJECT-TYPE
        SYNTAX        INTEGER { 
                                ok(1), 
                                overTemperature(2),
                                minorWarning(3),  -- Used by C6400
                                majorWarning(4),  -- Used by C6400
                                criticalWarning(5)-- Used by C6400
                                }
        MAX-ACCESS    read-only
        STATUS        current
        DESCRIPTION   "The chassis temperature status.

                     The values of minorWarning(3), majorWarning(4) and
                     criticalWarning(5) will be primarily used by C6400
                     to indicate the core temperature. C6400 will never
                     report overTemperature(2) status.

                     In C6400 there are two temperature sensors: core 
                     and inlet. C6400 use this object to represent the 
                     core temperature and the other object
                     ciscoLS1010ChassisInletTempStatus to represent the
                     inlet temperature."
       ::= { ciscoLS1010ChassisGroup 16 }

ciscoLS1010ChassisPcmciaSlot0Type OBJECT-TYPE
        SYNTAX        PcmciaType
        MAX-ACCESS    read-only
        STATUS        current
        DESCRIPTION   "Type of PCMCIA slot 0 type."
        ::= { ciscoLS1010ChassisGroup 17 }

ciscoLS1010ChassisPcmciaSlot1Type OBJECT-TYPE
        SYNTAX        PcmciaType
        MAX-ACCESS    read-only
        STATUS        current
        DESCRIPTION   "Type of PCMCIA slot 1 type."
        ::= { ciscoLS1010ChassisGroup 18 }

ciscoLS1010ChassisNumSlots OBJECT-TYPE
        SYNTAX        INTEGER (1..16)
        MAX-ACCESS    read-only
        STATUS        current
        DESCRIPTION   "The number of slots in the chassis for plug-in modules."
        ::= { ciscoLS1010ChassisGroup 19 }

ciscoLS1010ChassisLastChange OBJECT-TYPE
        SYNTAX        TimeStamp
        MAX-ACCESS    read-only
        STATUS        current
        DESCRIPTION   "The last time chassis physical content get changed."
        ::= { ciscoLS1010ChassisGroup 20 }

ciscoLS1010ChassisFailureAction OBJECT-TYPE
        SYNTAX        INTEGER {
                                nothing(1),
                                sendTrap(2),
                                shutdown(3),
                                sendTrapAndShutdown(4)
                                }
        MAX-ACCESS    read-write
        STATUS        current
        DESCRIPTION   "The action to take when there is any chassis failure,
                        which includes either power supply, voltage, 
                        temperature and fan failure."
        DEFVAL { sendTrapAndShutdown }
        ::= { ciscoLS1010ChassisGroup 21 }

ciscoLS1010ChassisChangeAction OBJECT-TYPE
        SYNTAX        INTEGER {
                                nothing(1),
                                sendTrap(2)
                                }
        MAX-ACCESS    read-write
        STATUS        current
        DESCRIPTION   "The action to take when there is any chassis change,
                        which includes either power supply, fan and boards."
        DEFVAL { sendTrap }
        ::= { ciscoLS1010ChassisGroup 22 }

ciscoLS1010ChassisClockingMode OBJECT-TYPE
        SYNTAX        INTEGER { revertive(1), nonRevertive(2) }
        MAX-ACCESS    read-write
        STATUS        current
        DESCRIPTION   "The clocking mode of the ls1010 system. By default,
                        the mode is non-revertive, which means that the clock
                        will stick to the current priority, even though higher
                        priority clock is available."
        ::= { ciscoLS1010ChassisGroup 23 }

ciscols1010SystemClockSourceStatus OBJECT-TYPE
    SYNTAX        INTEGER { notSelected(1),
                            selected(2) }
    MAX-ACCESS    read-only
    STATUS        current
    DESCRIPTION
              "The network clock source status of 'system' source:

               'notSelected' indicates 'system' not selected as the
              network clock source.

               'selected' indicates  ASP freerunning(system) is selected as 
              network clock source.  "
    ::= { ciscoLS1010ChassisGroup 24 }

ciscols1010SystemClockSourcePriority OBJECT-TYPE
    SYNTAX        INTEGER { priority1(1),
                            priority2(2),
                            priority3(3),
                            priority4(4), 
                            priority5(5) }
    MAX-ACCESS    read-write
    STATUS        current
    DESCRIPTION
              "The highest priority at which 'system' is configured as
              a network clock source. "
    ::= { ciscoLS1010ChassisGroup 25 }

ciscoLS1010ChassisInletTempStatus OBJECT-TYPE
        SYNTAX        INTEGER { ok(1),
                                overTemperature(2),
                                minorWarning(3),
                                majorWarning(4),
                                criticalWarning(5),
                                unknown(6)
                      }
        MAX-ACCESS    read-only
        STATUS        current
        DESCRIPTION   "C6400 has two temperature sensors: core and 
                       inlet. C6400 use this object to represent the 
                       inlet temperature and use the object
                       ciscoLS1010ChassisTempStatus to represent the
                       core temperature."
        ::= { ciscoLS1010ChassisGroup 26 }

-- the module group

ciscoLS1010ModuleTable OBJECT-TYPE
        SYNTAX        SEQUENCE OF CiscoLS1010ModuleEntry
        MAX-ACCESS    not-accessible
        STATUS        current
        DESCRIPTION   "A list of module entries.  The number of entries is 
                      given by the value of ciscoLS1010ChassisNumSlots."
        ::= { ciscoLS1010ModuleGroup 1 }

ciscoLS1010ModuleEntry OBJECT-TYPE
        SYNTAX        CiscoLS1010ModuleEntry
        MAX-ACCESS    not-accessible
        STATUS        current
        DESCRIPTION   "Entry containing information about one module in a 
                      slot of the chassis."
        INDEX         { ciscoLS1010ModuleIndex }
        ::= { ciscoLS1010ModuleTable 1 }

CiscoLS1010ModuleEntry ::=
        SEQUENCE {
                ciscoLS1010ModuleIndex
                        INTEGER,
                ciscoLS1010ModuleType
                        INTEGER,
                ciscoLS1010ModuleSerialNumber
                        Integer32,
                ciscoLS1010ModuleHwVersion
                        Integer32,
                ciscoLS1010ModuleSwVersion
                        Integer32,
                ciscoLS1010ModuleDescr
                        DisplayString,
                ciscoLS1010ModuleNumSubModules
                        INTEGER,
                ciscoLS1010ModuleAdminStatus
                        AdminStatus,
                ciscoLS1010ModuleOperStatus
                        OperStatus,
                ciscoLS1010ModuleHwVersionMinor
                        Unsigned32,
                ciscoLS1010ModuleSerialNumberString
                        DisplayString
                }

ciscoLS1010ModuleIndex OBJECT-TYPE
        SYNTAX        INTEGER (0..15)
        MAX-ACCESS    not-accessible
        STATUS        current
        DESCRIPTION   "A unique value for each module."
        ::= { ciscoLS1010ModuleEntry 1 }

ciscoLS1010ModuleType OBJECT-TYPE
        SYNTAX        INTEGER {
                        other(1),    -- none of the following
                        carrier(2),
                        cpuSwitchAndFeature(3),    -- FC1
                        cpuSwitchAndFeaturePFQ(4), -- FC-PFQ
                        superCarrier(5),
                        cpuRoute(6),       -- routing processor
                        switch10GAndFC(7), -- 10 gigabit switch fabric 
                                           -- with feature card option
                        switch10GNoFC(8),   -- 10 gigabit switch fabric 
                                             -- w/o feature card option
                        atmFabricIntegration(9),        -- on C5500
                        dualSlot(10),    -- Dual slot module for OC48c
                        cmpmCarrier(11),  -- CMPM module in 8540c
                        tsCarrier(12),   -- TS Carrier Module
                        nodeSwitchProcessor2ndGeneration(13) --NSP2
                               }
        MAX-ACCESS    read-only
        STATUS        current
        DESCRIPTION   "The type of module."
        ::= { ciscoLS1010ModuleEntry 2 }

ciscoLS1010ModuleSerialNumber OBJECT-TYPE
        SYNTAX        Integer32
        MAX-ACCESS    read-only
        STATUS        deprecated
        DESCRIPTION   "The serial number of the module.
                       Deprecated in favor of object 
                       ciscoLS1010ModuleSerialNumberString. This object
                       returns 0 for modules using an alphanumeric 
                       numbering scheme."
        ::= { ciscoLS1010ModuleEntry 3 }

ciscoLS1010ModuleHwVersion OBJECT-TYPE
        SYNTAX        Integer32
        MAX-ACCESS    read-only
        STATUS        current
        DESCRIPTION   "The hardware version of the module."  
        ::= { ciscoLS1010ModuleEntry 4 }

ciscoLS1010ModuleSwVersion OBJECT-TYPE
        SYNTAX        Integer32
        MAX-ACCESS    read-only
        STATUS        current
        DESCRIPTION   "The software version number."
        ::= { ciscoLS1010ModuleEntry 5 }

ciscoLS1010ModuleDescr OBJECT-TYPE
        SYNTAX        DisplayString
        MAX-ACCESS    read-only
        STATUS        current
        DESCRIPTION   "A descriptive string used by the agent 
                      to describe the module."
        ::= { ciscoLS1010ModuleEntry 6 }

ciscoLS1010ModuleNumSubModules OBJECT-TYPE
        SYNTAX        INTEGER (0..255)
        MAX-ACCESS    read-only
        STATUS        current
        DESCRIPTION   "The max number of sub-modules supported by this module."
        ::= { ciscoLS1010ModuleEntry 7 }

ciscoLS1010ModuleAdminStatus OBJECT-TYPE
        SYNTAX        AdminStatus
        MAX-ACCESS    read-write
        STATUS        current
        DESCRIPTION   "This object, when read, always returns a value of
                      ok(1).  Setting this object to one of the
                      acceptable values gives the following results:
                          reset:   reset the module's control logic
                          enable:  enable the module
                          disable: disable the module
                      Setting this object to any other values results in 
                      an error."
        ::= { ciscoLS1010ModuleEntry 8 }

 ciscoLS1010ModuleOperStatus OBJECT-TYPE
         SYNTAX        OperStatus
         MAX-ACCESS    read-only
         STATUS        current
         DESCRIPTION   "Operational status of the module."
         ::= { ciscoLS1010ModuleEntry 9 }

ciscoLS1010ModuleHwVersionMinor OBJECT-TYPE
        SYNTAX        Unsigned32
        MAX-ACCESS    read-only
        STATUS        current
        DESCRIPTION   "The minor hardware version of the module."
        ::= { ciscoLS1010ModuleEntry 10 }

ciscoLS1010ModuleSerialNumberString OBJECT-TYPE
        SYNTAX        DisplayString
        MAX-ACCESS    read-only
        STATUS        current
        DESCRIPTION   "The serial number of the module."
        ::= { ciscoLS1010ModuleEntry 11 }

-- the sub-module group

ciscoLS1010SubModuleTable OBJECT-TYPE
        SYNTAX        SEQUENCE OF CiscoLS1010SubModuleEntry
        MAX-ACCESS    not-accessible
        STATUS        current
        DESCRIPTION   "A list of sub-module entries.  The number of entries is 
                      given by the value of ciscoLS1010SlotNumSubModules."
        ::= { ciscoLS1010SubModuleGroup 1 }

ciscoLS1010SubModuleEntry OBJECT-TYPE
        SYNTAX        CiscoLS1010SubModuleEntry
        MAX-ACCESS    not-accessible
        STATUS        current
        DESCRIPTION   "Entry containing information about one sub-module in a 
                      sub-slot of the module."
        INDEX         { ciscoLS1010ModuleIndex, 
                        ciscoLS1010SubModuleIndex }
        ::= { ciscoLS1010SubModuleTable 1 }

CiscoLS1010SubModuleEntry ::=
        SEQUENCE {
                ciscoLS1010SubModuleIndex
                        INTEGER,
                ciscoLS1010SubModuleType
                        INTEGER,
                ciscoLS1010SubModuleSerialNumber
                        Integer32,
                ciscoLS1010SubModuleHwVersion
                        Integer32,
                ciscoLS1010SubModuleSwVersion
                        Integer32,
                ciscoLS1010SubModuleDescr
                        DisplayString,
                ciscoLS1010SubModuleNumPorts
                        INTEGER,
                ciscoLS1010SubModuleAdminStatus
                        INTEGER,
                ciscoLS1010SubModuleHwVersionMinor
                        Integer32,
                ciscoLS1010SubModuleOperStatus
                        OperStatus,
                ciscoLS1010SubModuleSerialNumberString
                        DisplayString
                }

ciscoLS1010SubModuleIndex OBJECT-TYPE
        SYNTAX        INTEGER (0..15)
        MAX-ACCESS    not-accessible
        STATUS        current
        DESCRIPTION   "A unique value for each sub-module within the module.
                      This value is determined by sub-slot number where the 
                      sub-module is inserted."
        ::= { ciscoLS1010SubModuleEntry 1 }

ciscoLS1010SubModuleType OBJECT-TYPE
        SYNTAX        INTEGER {
                               other(1),    -- none of the following
                               oc3Utp5(2),
                               oc3SingleModeFiber(3),
                               oc3MultiModeFiber(4),
                               oc12SingleModeFiber(5),
                               oc12MultiModeFiber(6),
                               ds3(7),
                               e3(8),
                               cpuSwitch(9),
                               featureFpga(10),
                               featureAsic(11),
                               t1(12),
                               e1(13),
                               e1bnc(14),
                               oc3Mixed(15),
                               cbrt1(16),
                               cbr120e1(17),
                               cbr75e1(18),
                               quadDs3(19),
                               quadE3(20),
                               dualDs3(21),
                               dualE3(22),
                               oc12Mixed(23),
                               atm25(24),
                               featurePVC(25),
                               routerProcessorAlpha(26), -- Cisco6400 NRP card
                               dualOC3SingleModeIRFiber(27), -- Cisco 6400 
                                                             -- Line card
                               dualOC3MultiModeIRFiber(28), 
                               routerProcessorBeta(29), -- Cisco6400 
                                                        -- NRP2 card

                               -- FR/FUNI Frame Port Adapters 
                               fratm1CT3(30),
                               fratm4CE1(31),
                               -- more ATM port adapters
                               oc3SingleModeLRFiber(35),
                               oc12SingleModeLRFiber(36),
                               sixPortDS3(37),
                               feUTP8p16k(40), -- 8 port fast ethernet UTP
                               feUTP8p64k(41),
                               feMMF8p16k(42), -- 8 port fast ethernet fiber
                               feMMF8p64k(43),
                               feUTP16p16k(44), -- 16 port fast ethernet UTP
                               feUTP16p64k(45),
                               feMMF16p16k(46), -- 16 port fast ethernet fiber
                               feMMF16p64k(47),
                               geF1p16k(48), -- 1 port gigabit ethernet fiber
                               geF1p64k(49),
                               geF2p16k(50), -- 2 port gigabit ethernet fiber
                               geF2p64k(51),
                               feBridge4p(52), -- fast ethernet bridge card
                               feUTP8p16kFullDup(53), -- 8 port UTP full duplex 
                               feUTP8p64kFullDup(54),
                               routeProc(55),     -- routing processor
                               switch10GProc(56), -- 10G switching processor
                               featureNetClock(57), -- network clock FC
                               featureABR(58),    -- ABR relative rate FC
                               geF8p64k(59), -- 8 port gig-ether fiber

                                -- cat8540
                                featureLite(60),
                                -- c8540MSR Port Adapters
                                s16pOC3MM(61),
                                s16pOC3SM(62),
                                s4pOC12MM(63),
                                s4pOC12SM(64),
                                atmIma8pT1(65),
                                atmIma8pE1(66),
                                atm25m4p(67),
                                s1pOC48cSM(68),
                                s1pOC48cSMLR(69),
                                -- cat5500 Bridge card
                                atmFIMBridge(70),
                                atmFIMoc12MM(71),
                                -- ATM Router Module card
                                arm1p64k(80),
                                arm2p64k(81),
                                -- 8540c XPIF Giga Ethernet Module (Barracuda)
                                xpif1pGE16k(82),
                                xpif1pGE64k(83),
                                xpif1pGE256k(84),
                                -- 8540c XPIF ATM OC12/3 Module card (Garfield)
                                xpifAtm1pOC12SMIR64k(85),
                                xpifAtm1pOC12SMIR256k(86),
                                xpifAtm1pOC12MM64k(87),
                                xpifAtm1pOC12MM256k(88),
                                xpifAtm1pOC3SMIR64k(89),
                                xpifAtm1pOC3SMIR256k(90),
                                xpifAtm1pOC3MM64k(91),
                                xpifAtm1pOC3MM256k(92),
                                -- 8540c XPIF POS OC12 Module card (POS)
                                xpifPos1pOC12SMIR64k(93),
                                xpifPos1pOC12SMIR256k(94),
                                xpifPos1pOC12SMLR64k(95),
                                xpifPos1pOC12SMLR256k(96),
                                -- ATM Router Module (XPIF) card
                                xpifArm2p256k(97),
                                -- ACL Daughter card for EPIF and GPIF
                                aclDaughter(98)
                              }
        MAX-ACCESS    read-only
        STATUS        current
         DESCRIPTION   "The type of sub-module."
        ::= { ciscoLS1010SubModuleEntry 2 }

ciscoLS1010SubModuleSerialNumber OBJECT-TYPE
        SYNTAX        Integer32
        MAX-ACCESS    read-only
        STATUS        deprecated
        DESCRIPTION   "The serial number of the sub-module.
                       Deprecated in favor of object
                       ciscoLS1010SubModuleSerialNumberString. This 
                       object returns 0 for submodules using
                       an alphanumeric numbering scheme."
        ::= { ciscoLS1010SubModuleEntry 3 }

ciscoLS1010SubModuleHwVersion OBJECT-TYPE
        SYNTAX        Integer32
        MAX-ACCESS    read-only
        STATUS        current
        DESCRIPTION   "The major hardware version of the sub-module.
                       Together with ciscoLS1010SubModuleHwVersionMinor,
                       this completely specifies the hardware version of
                       the sub-module."  
        ::= { ciscoLS1010SubModuleEntry 4 }

ciscoLS1010SubModuleSwVersion OBJECT-TYPE
        SYNTAX        Integer32
        MAX-ACCESS    read-only
        STATUS        current
        DESCRIPTION   "The software version number."
        ::= { ciscoLS1010SubModuleEntry 5 }

ciscoLS1010SubModuleDescr OBJECT-TYPE
        SYNTAX        DisplayString
        MAX-ACCESS    read-only
        STATUS        current
        DESCRIPTION   "A descriptive string used by the agent 
                      to describe the module."
        ::= { ciscoLS1010SubModuleEntry 6 }

ciscoLS1010SubModuleNumPorts OBJECT-TYPE
        SYNTAX        INTEGER (0..255)
        MAX-ACCESS    read-only
        STATUS        current
        DESCRIPTION   "The maximum number of ports supported by 
                       this sub-module."
        ::= { ciscoLS1010SubModuleEntry 7 }

ciscoLS1010SubModuleAdminStatus OBJECT-TYPE
        SYNTAX        INTEGER { reset(1), ok(2) }
        MAX-ACCESS    read-write
        STATUS        current
        DESCRIPTION   "This object can be read/written as reset or ok."
        ::= { ciscoLS1010SubModuleEntry 8 }

ciscoLS1010SubModuleHwVersionMinor OBJECT-TYPE
        SYNTAX        Integer32
        MAX-ACCESS    read-only
        STATUS        current
        DESCRIPTION   "The minor hardware version of the sub-module.
                       Together with ciscoLS1010SubModuleHwVersion,
                       this completely specifies the hardware version of
                       the sub-module."  
        ::= { ciscoLS1010SubModuleEntry 9 }

 ciscoLS1010SubModuleOperStatus OBJECT-TYPE
         SYNTAX          OperStatus
         MAX-ACCESS      read-only
         STATUS          current
         DESCRIPTION     "Operational status of the submodule."
         ::= { ciscoLS1010SubModuleEntry 10 }

ciscoLS1010SubModuleSerialNumberString OBJECT-TYPE
        SYNTAX        DisplayString
        MAX-ACCESS    read-only
        STATUS        current
        DESCRIPTION   "The serial number of the sub-module."
        ::= { ciscoLS1010SubModuleEntry 11 }

-- the port group

ciscoLS1010PortTable OBJECT-TYPE
        SYNTAX        SEQUENCE OF CiscoLS1010PortEntry
        MAX-ACCESS     not-accessible
        STATUS        current
        DESCRIPTION   "A list of port entries.  The number of entries is 
                      determined by the number of modules in the chassis,
                      the number of sub-module in the module 
                      and the number of ports on each sub-module."
        ::= { ciscoLS1010PortGroup 1 }

ciscoLS1010PortEntry OBJECT-TYPE
        SYNTAX        CiscoLS1010PortEntry
        MAX-ACCESS    not-accessible
        STATUS        current
        DESCRIPTION   "Entry containing information for a particular port on 
                      a sub-module."
        INDEX         { ciscoLS1010ModuleIndex,
                        ciscoLS1010SubModuleIndex, 
                        ciscoLS1010PortIndex }
        ::= { ciscoLS1010PortTable 1 }

CiscoLS1010PortEntry ::= SEQUENCE {
                ciscoLS1010PortIndex
                        INTEGER,
                ciscoLS1010PortIfIndex
                        InterfaceIndex
                }

ciscoLS1010PortIndex OBJECT-TYPE
        SYNTAX        INTEGER (0..255)
        MAX-ACCESS    not-accessible
        STATUS        current
        DESCRIPTION   "An index value that uniquely identifies this port within
                      a sub-module.  The value is determined by the location of
                      the port on the sub-module.  Valid entries are 1 to the 
                      value of subModuleNumPorts for this sub-module."
        ::= { ciscoLS1010PortEntry 1 }

ciscoLS1010PortIfIndex OBJECT-TYPE
        SYNTAX        InterfaceIndex
        MAX-ACCESS    read-only
        STATUS        current
        DESCRIPTION   "The ifIndex value assigned to this port."
        ::= { ciscoLS1010PortEntry 2 }

-- the ethernet port group

clsEnetPortTable OBJECT-TYPE
        SYNTAX        SEQUENCE OF ClsEnetPortEntry
        MAX-ACCESS     not-accessible
        STATUS        current
        DESCRIPTION   "A list of ethernet port entries.  This table
                       is mainly to support ethernet port only."
        ::= { clsEnetPortGroup 1 }

clsEnetPortEntry OBJECT-TYPE
        SYNTAX        ClsEnetPortEntry
        MAX-ACCESS    not-accessible
        STATUS        current
        DESCRIPTION   "Entry contains information of a particular 
                       ethernet port."
        INDEX         { ifIndex }
        ::= { clsEnetPortTable 1 }

ClsEnetPortEntry ::= SEQUENCE {
                clsEnetPortDuplex       INTEGER,
                clsEnetPortAdminSpeed   INTEGER,
                clsEnetPortType         INTEGER,
                clsEnetPortLinkStatus   INTEGER
                }

clsEnetPortDuplex OBJECT-TYPE     
         SYNTAX        INTEGER { 
                                unknown(1), -- not applicable or other
                                auto(2), -- auto negotiation
                                half(3), -- half duplex
                                full(4)  -- full duplex
                                }
         MAX-ACCESS    read-write
         STATUS        current
         DESCRIPTION   "Indicates whether the port is operating 
                       in half-duplex, full-duplex, or auto mode. 
                       If the port could not agree with the far end on 
                       port duplex, the port will be in auto(2) mode.
                       Unknown(1) indicates either the port does not 
                       support duplex mode, or the duplex mode is
                       none of the defined."
         ::= { clsEnetPortEntry  1 }

clsEnetPortAdminSpeed OBJECT-TYPE
         SYNTAX        INTEGER { 
                                unknown(1), -- not applicable or other
                                auto(2),      -- auto negotiation
                                e10Mbps(3),   -- 10 Mbps 
                                e100Mbps(4),  -- 100 Mbps
                                e1000Mbps(5)  -- 1000 Mbps
                                }
         MAX-ACCESS    read-write
         STATUS        current
         DESCRIPTION   "Indicates the desired speed of the port 
                        in bits per second. 
                        The current operational speed of the port 
                        is determined by ifSpeed.
                        If the port could not agree with the far end on 
                        port speed, the port will be in auto(2) mode,
                        which will force the port to transmit in speed
                        whichever is lower.
                        Unknown(1) indicates either the port does not 
                        support admin speed, or the admin speed is
                        none of the defined."
         ::= { clsEnetPortEntry  2 }

clsEnetPortType OBJECT-TYPE
         SYNTAX        INTEGER {
                            unknown(1),    -- empty or other
                            e100BaseTX(2), -- UTP fast Ethernet
                            e100BaseFX(3), -- Fiber fast Ethernet
                            e1000BaseLX(4), -- Long Wave SMF Giga Ethernet
                            e1000BaseSX(5), -- Short Wave MMF Giga Ethernet
                            empty(6)        -- port not present
                                }
         MAX-ACCESS    read-only
         STATUS        current
         DESCRIPTION   "The type of physical layer medium-dependent
                        interface on the port.
                        unknown(1) indicates that the port type is none of
                        those defined. empty(6) indicates that the port is 
                        not present." 
         ::= { clsEnetPortEntry  3 }

clsEnetPortLinkStatus OBJECT-TYPE
         SYNTAX        INTEGER {
                            unknown(1), -- not applicable or other
                            autoNegotiate(2),
                            forceUp(3)
                                }
         MAX-ACCESS    read-write
         STATUS        current
         DESCRIPTION   "This object indicates how the link status
                        of the port came up.

                        autoNegotiate(2) -- the port will try to
                        negotiate the link with the partner port.
                        If successful, the link will come up,
                        otherwise the link will remain down.

                        forceUp(3) -- the port will force the link
                        up irrespective of its partner port.  This
                        will bring up the link in full duplex only.

                        Default is autoNegotiate(2)."
         ::= { clsEnetPortEntry  4 }

-- the port LED group

clsPortLedTable OBJECT-TYPE
        SYNTAX        SEQUENCE OF ClsPortLedEntry
        MAX-ACCESS     not-accessible
        STATUS        current
        DESCRIPTION   "A list of LED entries associated with a port."
        ::= { clsPortLedGroup 1 }

clsPortLedEntry OBJECT-TYPE
        SYNTAX        ClsPortLedEntry
        MAX-ACCESS    not-accessible
        STATUS        current
        DESCRIPTION   "Entry contains information of a particular
                       LED associated with a particular port which
                       is identified by ifIndex."
        INDEX         { ifIndex, clsPortLedIndex }
        ::= { clsPortLedTable 1 }

ClsPortLedEntry ::= SEQUENCE {
                clsPortLedIndex         INTEGER,
                clsPortLedType          INTEGER,
                clsPortLedStatus        INTEGER
                }

clsPortLedIndex OBJECT-TYPE
         SYNTAX        INTEGER (1..255)
         MAX-ACCESS    not-accessible
         STATUS        current
         DESCRIPTION   "An index that uniquely identifies this LED
                        among all the LEDs associated with the port
                        identified by ifIndex.
                        This value is related to the physical location
                        of the LED, and is in ascending order from 
                        top to bottom, left to right."
         ::= { clsPortLedEntry  1 }

clsPortLedType OBJECT-TYPE
         SYNTAX        INTEGER {
                                ledTx(1), -- transmit
                                ledRx(2), -- receive
                                ledLink(3), -- link status
                                led100Mbps(4), -- port speed
                                ledRxLoss(5), -- Rx cell loss
                                ledRxFullOut(6), -- Rx cell full out
                                ledRxSync(7), -- Rx sync
                                ledFullDuplex(8), -- full duplex
                                ledOptDetect(9) -- optical detect
                                }
         MAX-ACCESS    read-only
         STATUS        current
         DESCRIPTION   "Indicates the type or label of the LED."
         ::= { clsPortLedEntry  2 }

clsPortLedStatus OBJECT-TYPE
         SYNTAX         INTEGER {    
                                unknown(1), -- not supported or other
                                on(2),
                                off(3)
                                }
         MAX-ACCESS    read-only
         STATUS        current
         DESCRIPTION   "Indicates the status of the LED.
                        Unknown(1) indicates either the LED status is 
                        not supported or the status is none of the
                        defined."
         ::= { clsPortLedEntry  3 }

-- the CPU/switch fabric group

ciscoAtmCpuAdminStatus OBJECT-TYPE
        SYNTAX        INTEGER { reset(1), ok(2) }
        MAX-ACCESS    read-write
        STATUS        current
        DESCRIPTION   "Reset will reload the CPU board."
        ::= { ciscoLS1010CpuSwitchGroup 1 }

ciscoAtmSwitchTotalBuffer OBJECT-TYPE
        SYNTAX        Integer32
        MAX-ACCESS    read-only
        STATUS        current
        DESCRIPTION   "The total cell buffer count in switch's shared memory."
        ::= { ciscoLS1010CpuSwitchGroup 2 }

ciscoAtmSwitchFreeBuffer OBJECT-TYPE
        SYNTAX        Gauge32
        MAX-ACCESS    read-only
        STATUS        current
        DESCRIPTION   "The free cell buffer count in switch's shared memory."
        ::= { ciscoLS1010CpuSwitchGroup 3 }

ciscoAtmSwitchDiscardCells OBJECT-TYPE
        SYNTAX        Counter32
        MAX-ACCESS    read-only
        STATUS        current
        DESCRIPTION   "The total discarded cells of the switch."
        ::= { ciscoLS1010CpuSwitchGroup 4 }

ciscoAtmSwitchInvalidCells OBJECT-TYPE
        SYNTAX        Counter32
        MAX-ACCESS    read-only
        STATUS        current
        DESCRIPTION   "The total invalid cells of the switch."
        ::= { ciscoLS1010CpuSwitchGroup 5 }

ciscoAtmSwitchInvalidCellHeaderTable OBJECT-TYPE
        SYNTAX        SEQUENCE OF CiscoAtmSwitchInvalidCellHeaderEntry
        MAX-ACCESS     not-accessible
        STATUS        current
        DESCRIPTION   "A list of invalid cell header entries."
        ::= { ciscoLS1010CpuSwitchGroup 6 }

ciscoAtmSwitchInvalidCellHeaderEntry OBJECT-TYPE
        SYNTAX        CiscoAtmSwitchInvalidCellHeaderEntry
        MAX-ACCESS    not-accessible
        STATUS        current
        DESCRIPTION   "a entry of invalid cell header."     
        INDEX         { ciscoAtmSwitchInvalidCellHeaderIndex }
        ::= { ciscoAtmSwitchInvalidCellHeaderTable 1 }

CiscoAtmSwitchInvalidCellHeaderEntry ::= SEQUENCE {
                ciscoAtmSwitchInvalidCellHeaderIndex
                        INTEGER,
                ciscoAtmSwitchInvalidCellHeader
                        OCTET STRING
                }

ciscoAtmSwitchInvalidCellHeaderIndex OBJECT-TYPE
        SYNTAX        INTEGER (1..64)
        MAX-ACCESS    not-accessible
        STATUS        current
        DESCRIPTION   "A sequence number that identifies a invalid cell header
                       entry in the table."
        ::= { ciscoAtmSwitchInvalidCellHeaderEntry 1 }

ciscoAtmSwitchInvalidCellHeader OBJECT-TYPE
        SYNTAX        OCTET STRING (SIZE(5))
        MAX-ACCESS    read-only
        STATUS        current
        DESCRIPTION   "The most recently received invalid cells header.
                       octet 0 is port number (0-32),
                       octet 1 bit 7-5 is PTI,
                       octet 1 bit 4 is CLP,
                       octet 1 bit 3-0 is GFC,
                       octet 2 is VPI,
                       octet 3 is high byte of VCI
                       octet 4 is low byte of VCI."
        ::= { ciscoAtmSwitchInvalidCellHeaderEntry 2 }

ciscoAtmCpuTerminateOamFlow OBJECT-TYPE
        SYNTAX        TruthValue
        MAX-ACCESS    read-write
        STATUS        obsolete    
                           -- superseded by ciscoAtmCpuTerminateVpOamFlow
        DESCRIPTION   "Terminate all the incoming OAM cells to the CPU port."
        DEFVAL { false }        -- no oam flow termination, by default
        ::= { ciscoLS1010CpuSwitchGroup 7 }

ciscoAtmInterceptEndToEndOamFlow OBJECT-TYPE
        SYNTAX        TruthValue
        MAX-ACCESS    read-write
        STATUS        current
        DESCRIPTION   "Indicates whether incoming end-to-end OAM flow
                       cells are sent to the switch CPU.

                       If the value is 'true', all incoming
                       end-to-end OAM flow cells, including those on
                       transit connections, are sent to the switch
                       CPU.

                       This value may be modified at any time. The
                       modified value will apply to all existing
                       connections.

                       Note that if the value is 'false', the switch
                       can not use the ATM PING application  for
                       end-to-end loopback on transit connections,
                       since the end-to-end OAM cells on such connections
                       will not be seen by the switch CPU."
        DEFVAL { true }
        ::= { ciscoLS1010CpuSwitchGroup 8 }

-- the following two OBJECT IDENTIFIERS are used to define SNMPv2 Notifications
-- that are backward compatible with SNMPv1 Traps.

ciscoLS1010ChassisMIBNotificationPrefix OBJECT IDENTIFIER ::= 
                                        { ciscoLS1010ChassisMIB 2 }
ciscoLS1010ChassisMIBNotifications OBJECT IDENTIFIER ::= 
                                { ciscoLS1010ChassisMIBNotificationPrefix 0 }

ciscoLS1010ChassisFailureNotification NOTIFICATION-TYPE
        OBJECTS {
                ciscoLS1010ChassisPs0Status,
                ciscoLS1010ChassisPs1Status,
                ciscoLS1010ChassisFanStatus,
                ciscoLS1010Chassis12VoltStatus,
                ciscoLS1010ChassisTempStatus
                }
        STATUS  current
        DESCRIPTION
                "Agent detects a change in the status of ps0, ps1, 
                fan, 12V line, and/or chassis temperature. 
                This notification will be generated when the status
                changes from no-fault to fault, and also when the status 
                changes from fault to no-fault."
        ::= { ciscoLS1010ChassisMIBNotifications 1 }

ciscoLS1010ChassisChangeNotification NOTIFICATION-TYPE
        -- no OBJECTS
        STATUS  current
        DESCRIPTION
                "Agent detects any hot-swap component change or changes
                in the chassis."
        ::= { ciscoLS1010ChassisMIBNotifications 2 }

        -- conformance information

ciscoLS1010ChassisMIBConformance OBJECT IDENTIFIER ::= { ciscoLS1010ChassisMIB 3 }
ciscoLS1010ChassisMIBCompliances OBJECT IDENTIFIER ::= { ciscoLS1010ChassisMIBConformance 1 }
ciscoLS1010ChassisMIBGroups      OBJECT IDENTIFIER ::= { ciscoLS1010ChassisMIBConformance 2 }

        -- compliance statements

ciscoLS1010ChassisMIBCompliance MODULE-COMPLIANCE
        STATUS obsolete 
        DESCRIPTION
                "The compliance statement for entities which implement
                the Cisco LS1010 Chassis MIB. This statement was
                obsoleted by ciscoLS1010ChassisMIBComplianceRev1."
        MODULE  -- this module
                MANDATORY-GROUPS { ciscoLS1010ChassisMIBGroup }
        ::= { ciscoLS1010ChassisMIBCompliances 1 }

ciscoLS1010ChassisMIBComplianceRev1 MODULE-COMPLIANCE
        STATUS obsolete
        DESCRIPTION
                "The compliance statement for entities which implement
                the Cisco LS1010 Chassis MIB.  This statement was
                obsoleted by ciscoLS1010ChassisMIBComplianceRev2."
        MODULE  -- this module
                MANDATORY-GROUPS { ciscoLS1010ChassisMIBGroup,
                                   ciscoLS1010ChassisMIBRev1Group }
        ::= { ciscoLS1010ChassisMIBCompliances 2 }

ciscoLS1010ChassisMIBComplianceRev2 MODULE-COMPLIANCE
        STATUS obsolete -- superseded by ciscoLS1010ChassisMIBComplianceRev3
        DESCRIPTION
                "The compliance statement for entities which implement
                the Cisco LS1010 Chassis MIB"
        MODULE  -- this module
                MANDATORY-GROUPS { ciscoLS1010ChassisMIBGroup,
                                   ciscoLS1010ChassisMIBRev1Group,
                                   ciscoLS1010ChassisMIBClockingGroup }
        ::= { ciscoLS1010ChassisMIBCompliances 3 }

-- ciscoLS1010ChassisMIBComplianceRev3 is superceded by 
-- ciscoLS1010ChassisMIBComplianceRev4

ciscoLS1010ChassisMIBComplianceRev3 MODULE-COMPLIANCE
        STATUS obsolete  
        DESCRIPTION
                "The compliance statement for entities which implement
                the Cisco LS1010 Chassis MIB."
        MODULE  -- this module
                MANDATORY-GROUPS { ciscoLS1010ChassisMIBGroup1,
                                   ciscoLS1010ChassisMIBClockingGroup }
        ::= { ciscoLS1010ChassisMIBCompliances 4 }

ciscoLS1010ChassisMIBComplianceRev4 MODULE-COMPLIANCE
        STATUS obsolete 
        DESCRIPTION
                "The compliance statement for entities which implement
                the Cisco LS1010 Chassis MIB."
        MODULE  -- this module
                MANDATORY-GROUPS { ciscoLS1010ChassisMIBGroup1,
                                   ciscoLS1010ChassisMIBClockingGroup,
                                   clsEnetPortGroup1,
                                   clsPortLedGroup1 }
        ::= { ciscoLS1010ChassisMIBCompliances 5 }

ciscoLS1010ChassisMIBComplianceRev5 MODULE-COMPLIANCE
        STATUS obsolete  
        DESCRIPTION
                "The compliance statement for the Cisco 6400 product."
        MODULE  -- this module
                MANDATORY-GROUPS { ciscoLS1010ChassisMIBGroup1,
                                   ciscoLS1010ChassisMIBClockingGroup,
                                   clsOperStatusGroup,
                                   clsInletTempGroup }
        ::= { ciscoLS1010ChassisMIBCompliances 6 }

ciscoLS1010ChassisMIBComplianceRev6 MODULE-COMPLIANCE
        STATUS current
        DESCRIPTION
                "The compliance statement for this MIB." 
        MODULE  -- this module
                MANDATORY-GROUPS { ciscoLS1010ChassisMIBGroup2,
                                   ciscoLS1010ChassisMIBClockingGroup }

                OBJECT   ciscoLS1010ModuleSerialNumberString
                SYNTAX   DisplayString (SIZE (1..32))
                DESCRIPTION
                  "Support for serial numbers longer than 32 characters 
                   is not required."

                OBJECT   ciscoLS1010SubModuleSerialNumberString
                SYNTAX   DisplayString (SIZE (1..32))
                DESCRIPTION
                  "Support for serial numbers longer than 32 characters 
                   is not required."
        ::= { ciscoLS1010ChassisMIBCompliances 7 }

        -- units of conformance

ciscoLS1010ChassisMIBGroup OBJECT-GROUP
        OBJECTS {
                ciscoLS1010ChassisSysType,
                ciscoLS1010ChassisBkplType,
                ciscoLS1010ChassisPs0Type,
                ciscoLS1010ChassisPs0AdminStatus,
                ciscoLS1010ChassisPs0Status,
                ciscoLS1010ChassisPs0Led,
                ciscoLS1010ChassisPs1Type,
                ciscoLS1010ChassisPs1AdminStatus,
                ciscoLS1010ChassisPs1Status,
                ciscoLS1010ChassisPs1Led,
                ciscoLS1010ChassisFanStatus,
                ciscoLS1010ChassisFanLed,
                ciscoLS1010ChassisCardStatusLed,
                ciscoLS1010ChassisEnetLinkLed,
                ciscoLS1010Chassis12VoltStatus,
                ciscoLS1010ChassisTempStatus,
                ciscoLS1010ChassisPcmciaSlot0Type,
                ciscoLS1010ChassisPcmciaSlot1Type,
                ciscoLS1010ChassisNumSlots,
                ciscoLS1010ChassisLastChange,
                ciscoLS1010ChassisFailureAction,
                ciscoLS1010ChassisChangeAction,
                ciscoLS1010ChassisInletTempStatus,
                ciscoLS1010ModuleType,
                ciscoLS1010ModuleSerialNumber,
                ciscoLS1010ModuleHwVersion,
                ciscoLS1010ModuleSwVersion,
                ciscoLS1010ModuleDescr,
                ciscoLS1010ModuleNumSubModules,
                ciscoLS1010ModuleAdminStatus,
                ciscoLS1010ModuleOperStatus,
                ciscoLS1010SubModuleType,
                ciscoLS1010SubModuleSerialNumber,
                ciscoLS1010SubModuleHwVersion,
                ciscoLS1010SubModuleSwVersion,
                ciscoLS1010SubModuleDescr,
                ciscoLS1010SubModuleNumPorts,
                ciscoLS1010SubModuleAdminStatus,
                ciscoLS1010PortIfIndex,
                ciscoAtmCpuAdminStatus,
                ciscoAtmSwitchTotalBuffer,
                ciscoAtmSwitchFreeBuffer,
                ciscoAtmSwitchDiscardCells,
                ciscoAtmSwitchInvalidCells,
                ciscoAtmSwitchInvalidCellHeader
        }
        STATUS obsolete
        DESCRIPTION
                "A collection of objects providing rhino chassis information"
        ::= { ciscoLS1010ChassisMIBGroups 1 }

ciscoLS1010ChassisMIBObsoleteGroup OBJECT-GROUP
        OBJECTS {
                ciscoAtmCpuTerminateOamFlow
        }
        STATUS obsolete
        DESCRIPTION
                "A collection of objects providing rhino chassis information
                 which are obsolete."
        ::= { ciscoLS1010ChassisMIBGroups 2 }

ciscoLS1010ChassisMIBRev1Group OBJECT-GROUP
        OBJECTS {
                ciscoLS1010SubModuleHwVersionMinor
        }
        STATUS current
        DESCRIPTION
                "A collection of objects useful for reporting the hardware
                 version of sub-modules in the chassis."
        ::= { ciscoLS1010ChassisMIBGroups 3 }

ciscoLS1010ChassisMIBClockingGroup OBJECT-GROUP
        OBJECTS {
                ciscoLS1010ChassisClockingMode,
                ciscols1010SystemClockSourceStatus,
                ciscols1010SystemClockSourcePriority
        }
        STATUS current
        DESCRIPTION
                "A collection of objects useful for managing clocking."
        ::= { ciscoLS1010ChassisMIBGroups 4 }

ciscoLS1010ChassisMIBGroup1 OBJECT-GROUP
        OBJECTS {
                ciscoLS1010ChassisSysType,
                ciscoLS1010ChassisBkplType,
                ciscoLS1010ChassisPs0Type,
                ciscoLS1010ChassisPs0AdminStatus,
                ciscoLS1010ChassisPs0Status,
                ciscoLS1010ChassisPs0Led,
                ciscoLS1010ChassisPs1Type,
                ciscoLS1010ChassisPs1AdminStatus,
                ciscoLS1010ChassisPs1Status,
                ciscoLS1010ChassisPs1Led,
                ciscoLS1010ChassisFanStatus,
                ciscoLS1010ChassisFanLed,
                ciscoLS1010ChassisCardStatusLed,
                ciscoLS1010ChassisEnetLinkLed,
                ciscoLS1010Chassis12VoltStatus,
                ciscoLS1010ChassisTempStatus,
                ciscoLS1010ChassisPcmciaSlot0Type,
                ciscoLS1010ChassisPcmciaSlot1Type,
                ciscoLS1010ChassisNumSlots,
                ciscoLS1010ChassisLastChange,
                ciscoLS1010ChassisFailureAction,
                ciscoLS1010ChassisChangeAction,
                ciscoLS1010ModuleType,
                ciscoLS1010ModuleSerialNumber,
                ciscoLS1010ModuleHwVersion,
                ciscoLS1010ModuleSwVersion,
                ciscoLS1010ModuleDescr,
                ciscoLS1010ModuleNumSubModules,
                ciscoLS1010ModuleAdminStatus,
                ciscoLS1010SubModuleType,
                ciscoLS1010SubModuleSerialNumber,
                ciscoLS1010SubModuleHwVersion,
                ciscoLS1010SubModuleSwVersion,
                ciscoLS1010SubModuleDescr,
                ciscoLS1010SubModuleNumPorts,
                ciscoLS1010SubModuleAdminStatus,
                ciscoLS1010SubModuleOperStatus,
                ciscoLS1010SubModuleHwVersionMinor,
                ciscoLS1010PortIfIndex,
                ciscoAtmCpuAdminStatus,
                ciscoAtmSwitchTotalBuffer,
                ciscoAtmSwitchFreeBuffer,
                ciscoAtmSwitchDiscardCells,
                ciscoAtmSwitchInvalidCells,
                ciscoAtmSwitchInvalidCellHeader,
                ciscoAtmInterceptEndToEndOamFlow
        }
        STATUS obsolete
        DESCRIPTION
                "A collection of objects for managing the LS1010 chassis."
        ::= { ciscoLS1010ChassisMIBGroups 5 }

clsEnetPortGroup1 OBJECT-GROUP
        OBJECTS {
                clsEnetPortDuplex,
                clsEnetPortAdminSpeed,
                clsEnetPortType,
                clsEnetPortLinkStatus
        }
        STATUS current
        DESCRIPTION
                "A collection of objects for managing ethernet ports."
        ::= { ciscoLS1010ChassisMIBGroups 6 }

clsPortLedGroup1 OBJECT-GROUP
        OBJECTS {
                clsPortLedType,
                clsPortLedStatus
        }
        STATUS current
        DESCRIPTION
                "A collection of objects for showing port LEDs." 
        ::= { ciscoLS1010ChassisMIBGroups 7 }

clsOperStatusGroup OBJECT-GROUP
        OBJECTS {
                ciscoLS1010ModuleOperStatus,
                ciscoLS1010SubModuleOperStatus
        }
        STATUS current
        DESCRIPTION
                "A collection of objects for displaying operational status of 
                 modules and sub-modules in the chassis."
        ::= { ciscoLS1010ChassisMIBGroups 8 }

clsInletTempGroup OBJECT-GROUP
        OBJECTS {
                ciscoLS1010ChassisInletTempStatus            
        }
        STATUS current
        DESCRIPTION
                "A collection of objects for reporting inlet temperature."
        ::= { ciscoLS1010ChassisMIBGroups 9 }

ciscoLS1010ChassisMIBGroup2 OBJECT-GROUP
        OBJECTS {
                ciscoLS1010ChassisSysType,
                ciscoLS1010ChassisBkplType,
                ciscoLS1010ChassisPs0Type,
                ciscoLS1010ChassisPs0AdminStatus,
                ciscoLS1010ChassisPs0Status,
                ciscoLS1010ChassisPs0Led,
                ciscoLS1010ChassisPs1Type,
                ciscoLS1010ChassisPs1AdminStatus,
                ciscoLS1010ChassisPs1Status,
                ciscoLS1010ChassisPs1Led,
                ciscoLS1010ChassisFanStatus,
                ciscoLS1010ChassisFanLed,
                ciscoLS1010ChassisCardStatusLed,
                ciscoLS1010ChassisEnetLinkLed,
                ciscoLS1010Chassis12VoltStatus,
                ciscoLS1010ChassisTempStatus,
                ciscoLS1010ChassisPcmciaSlot0Type,
                ciscoLS1010ChassisPcmciaSlot1Type,
                ciscoLS1010ChassisNumSlots,
                ciscoLS1010ChassisLastChange,
                ciscoLS1010ChassisFailureAction,
                ciscoLS1010ChassisChangeAction,
                ciscoLS1010ModuleType,
                ciscoLS1010ModuleHwVersion,
                ciscoLS1010ModuleSwVersion,
                ciscoLS1010ModuleDescr,
                ciscoLS1010ModuleNumSubModules,
                ciscoLS1010ModuleAdminStatus,
                ciscoLS1010SubModuleType,
                ciscoLS1010SubModuleHwVersion,
                ciscoLS1010SubModuleSwVersion,
                ciscoLS1010SubModuleDescr,
                ciscoLS1010SubModuleNumPorts,
                ciscoLS1010SubModuleAdminStatus,
                ciscoLS1010SubModuleOperStatus,
                ciscoLS1010SubModuleHwVersionMinor,
                ciscoLS1010PortIfIndex,
                ciscoAtmCpuAdminStatus,
                ciscoAtmSwitchTotalBuffer,
                ciscoAtmSwitchFreeBuffer,
                ciscoAtmSwitchDiscardCells,
                ciscoAtmSwitchInvalidCells,
                ciscoAtmSwitchInvalidCellHeader,
                ciscoAtmInterceptEndToEndOamFlow,
                ciscoLS1010ModuleHwVersionMinor,
                ciscoLS1010ModuleSerialNumberString,
                ciscoLS1010SubModuleSerialNumberString
        }
        STATUS current
        DESCRIPTION
                "A collection of objects for managing the 
                 LS1010 chassis."
        ::= { ciscoLS1010ChassisMIBGroups 10 }

ciscoLS1010ChassisMIBDeprecatedGroup OBJECT-GROUP
        OBJECTS {
                ciscoLS1010ModuleSerialNumber,
                ciscoLS1010SubModuleSerialNumber
        }
        STATUS deprecated
        DESCRIPTION
                "A collection of objects providing rhino 
                 chassis information which are obsolete."
        ::= { ciscoLS1010ChassisMIBGroups 11 }

ciscoLS1010ChassisMIBNotificationGroup NOTIFICATION-GROUP 
        NOTIFICATIONS {
                ciscoLS1010ChassisFailureNotification,
                ciscoLS1010ChassisChangeNotification
        }
        STATUS current
        DESCRIPTION
                "A collection of notifications supported
                 by LS1010 chassis."
        ::= { ciscoLS1010ChassisMIBGroups 12 } 

END
