CISCO-CIPCMPC-MIB DEFINITIONS ::= BEGIN

IMPORTS
	MODULE-IDENTITY, OBJECT-TYPE, NOTIFICATION-TYPE, 
	Counter32, Integer32
		FROM SNMPv2-SMI

	MODULE-COMPLIANCE, OBJECT-GROUP
		FROM SNMPv2-CONF

	RowStatus, TDomain, TimeStamp
		FROM SNMPv2-TC

	ifIndex
		FROM RFC1213-MIB

	ciscoMgmt
		FROM CISCO-SMI

	cipCardEntryIndex, cipCardDtrBrdIndex, cipCardSubChannelIndex
		FROM CISCO-CHANNEL-MIB

	ChannelPath, ChannelDevice
		FROM CISCO-CIPCSNA-MIB

	ChannelTgName
		FROM CISCO-CIPTG-MIB;

ciscoCipCmpcMIB MODULE-IDENTITY
	LAST-UPDATED	"9901250000Z"
	ORGANIZATION	"cisco IBU Engineering Working Group"
	CONTACT-INFO
		"	Cisco Systems
			Customer Service

		Postal: 170 W Tasman Drive
			San Jose, CA  95134
			USA

		   Tel: +1 800 553-NETS

		E-mail: cs-snmp@cisco.com"
	DESCRIPTION
	        "This is the Management Information Base (MIB) 
                module for objects used to manage the Cisco Multi-Path 
                Channel (MPC) support on Cisco Mainframe Channel
                Connection (CMCC) cards, also called the CMPC feature.

                -------------------------------------------------
                | Acronym Definitions:                          |
                | CIP      =   Channel Interface Processor      |
                | CMPC     =   Cisco Multi-Path Channel         |
                | HPR      =   High Performance Routing         |
                | HPDT     =   High Performance Data Transfer   |
                | ISR      =   Intermediate Session Routing     |
                | MPC      =   Multi-Path Channel                |
                | MPC+     =   HPDT MPC                         |
                | SNA      =   Systems Network Architecture     |
                | TG       =   Transmission Group               |
                -------------------------------------------------

                This MIB consists of the following tables:
                1) CMPC Subchannel Administration 
                2) CMPC Subchannel Operational
                3) CMPC TG Statistics

                Refer to the following MIBs for an understanding of Cisco 
                channel terminology and Cisco CMCC terminology:
                  CISCO-CHANNEL-MIB
                  CISCO-CIPCSNA-MIB
                  CISCO-CIPLAN-MIB
                  CISCO-CIPTG-MIB
                "
	REVISION        "9901250000Z"
	DESCRIPTION
		"Since the CMCC now supports MPC and MPC+,
		the new state, activePlus, was added to 
		cipCmpcSubChannelOperState to indicate the
		TG is active and using the MPC+ protocol." 

	REVISION        "9801060000Z"
	DESCRIPTION
		"With the addition of Cisco's new Channel Port
                 Adapter cards, all the references to CIP in the
                 MIB description and object descriptions are changed
                 to CMCC (Cisco Mainframe Channel Connection). The
                 object names in the form of cip... or cipCard...
                 will remain the same, but will be valid objects
                 for the Channel Port Adapter cards."

	REVISION "9702090000Z"
	DESCRIPTION
		"Initial version of this MIB module."
        ::= { ciscoMgmt 72 }

cipCmpcObjects OBJECT IDENTIFIER ::= { ciscoCipCmpcMIB 1 }

cipCmpcSubChannel OBJECT IDENTIFIER ::= { cipCmpcObjects 1 }
cipCmpcTg OBJECT IDENTIFIER ::= { cipCmpcObjects 2 }

-- ;;;;;;;;;;;;;;;;;;;;; cipCmpcSubChannelAdminTable ;;;;;;;;;;;;;;;;;;;;;;;;;;;

cipCmpcSubChannelAdminTable OBJECT-TYPE 
        SYNTAX SEQUENCE OF CipCmpcSubChannelAdminEntry
        MAX-ACCESS not-accessible
        STATUS current
        DESCRIPTION
                "This table contains configuration information used to 
                 define subchannels for the Cisco Multi-Path Channel 
                 (CMPC) feature on the CMCC card.

                 Each instance of this table is created when a CMPC
                 sub-channel is configured on the router. When the 
                 CMPC sub-channel configuration statement is deleted
                 from the router, the instance represented by this
                 table is removed."
        ::= { cipCmpcSubChannel 1 }

cipCmpcSubChannelAdminEntry OBJECT-TYPE
        SYNTAX CipCmpcSubChannelAdminEntry
        MAX-ACCESS not-accessible
        STATUS current
        DESCRIPTION
                "A list of CMPC configuration values."
        INDEX { cipCardEntryIndex,
                cipCardDtrBrdIndex,
                cipCardSubChannelIndex
        }
        ::= { cipCmpcSubChannelAdminTable 1 }

CipCmpcSubChannelAdminEntry ::= SEQUENCE
{
        cipCmpcSubChannelAdminPath                  ChannelPath,
        cipCmpcSubChannelAdminDevice                ChannelDevice,
        cipCmpcSubChannelAdminTgName                ChannelTgName,
        cipCmpcSubChannelAdminDirection             INTEGER,
        cipCmpcSubChannelAdminTgTransport           TDomain,
        cipCmpcSubChannelAdminRowStatus             RowStatus
}

cipCmpcSubChannelAdminPath OBJECT-TYPE
        SYNTAX ChannelPath
        MAX-ACCESS read-create
        STATUS current
        DESCRIPTION
                "Channel path for this CMPC instance."
        ::= { cipCmpcSubChannelAdminEntry 1 }

cipCmpcSubChannelAdminDevice OBJECT-TYPE
        SYNTAX ChannelDevice
        MAX-ACCESS read-create
        STATUS current
        DESCRIPTION
                "Device address of the subchannel the attached 
                host will use to communicate with this CMPC 
                instance."
        ::= { cipCmpcSubChannelAdminEntry 2 }

cipCmpcSubChannelAdminTgName OBJECT-TYPE
        SYNTAX ChannelTgName
        MAX-ACCESS read-create
        STATUS current
        DESCRIPTION
                "This is the name of the CMPC transmission group.
                Each CMPC subchannel in the same connection
                transmission group must have the same TG name"
        ::= { cipCmpcSubChannelAdminEntry 3 }

cipCmpcSubChannelAdminDirection OBJECT-TYPE
        SYNTAX INTEGER {
                read          (1),
                write         (2),
                readOrWrite   (3)
        }
        MAX-ACCESS  read-create
        STATUS current
        DESCRIPTION
                "Specifies whether the CMPC subchannel is for host 
                 reads or host writes."
        ::= { cipCmpcSubChannelAdminEntry 4 }

cipCmpcSubChannelAdminTgTransport  OBJECT-TYPE
          SYNTAX TDomain
          MAX-ACCESS read-only
          STATUS current
          DESCRIPTION
                 "This object specifies the Transmission Group 
                  transport type OID for which this CMPC Sub-Channel 
                  instance if configured.

                  When the Transmission Group for this CMPC Sub-Channel 
                  instance is not configured, this object will be set to 
                  the NULL TDomian { 0, 0 }."
          ::= { cipCmpcSubChannelAdminEntry 5 }

cipCmpcSubChannelAdminRowStatus OBJECT-TYPE
        SYNTAX RowStatus
        MAX-ACCESS read-create
        STATUS current
        DESCRIPTION
                "This object is used by a Management Station to create
                 or delete the row entry in the cipCmpcSubChannelAdminTable 
                 following the the RowStatus textual convention.

                 Upon successful creation of the row, an Agent
                 automatically creates a corresponding entry in
                 the cipCmpcSubChannelOperTable and 
                 cipCmpcSubChannelStatsTable.

                 The Management Station can initiate row deletion, by
                 setting this value to 'destroy (6)'.  The Agent will
                 then delete the rows corresponding to this CMPC 
                 instance from the cipCmpcSubChannelAdminTable,
                 cipCmpcSubChannelOperTable and cipCmpcSubChannelStatsTable."
        ::= { cipCmpcSubChannelAdminEntry 6 }

-- ;;;;;;;;;;;;;;;;;;;;; cipCmpcSubChannelOperTable ;;;;;;;;;;;;;;;;;;;;;;;;;;;

cipCmpcSubChannelOperTable OBJECT-TYPE 
        SYNTAX SEQUENCE OF CipCmpcSubChannelOperEntry
        MAX-ACCESS not-accessible
        STATUS current
        DESCRIPTION
                "This table contains operational information 
                 for the Cisco Multi-Path Channel (CMPC) 
                 feature on the CMCC card."
        ::= { cipCmpcSubChannel 2 }

cipCmpcSubChannelOperEntry OBJECT-TYPE
        SYNTAX CipCmpcSubChannelOperEntry
        MAX-ACCESS not-accessible
        STATUS current
        DESCRIPTION
                "A list of CMPC operational and status values. The 
                 entries are created by the Agent.  They have 
                 read-only access."
        AUGMENTS    { cipCmpcSubChannelAdminEntry }
        ::= { cipCmpcSubChannelOperTable 1 }

CipCmpcSubChannelOperEntry ::= SEQUENCE
{
        cipCmpcSubChannelOperState                INTEGER,
        cipCmpcSubChannelOperMaxbfru              Integer32
}

cipCmpcSubChannelOperState OBJECT-TYPE
        SYNTAX INTEGER {
                shutdown      (1),
                inactive      (2),
                xid2Pending   (3),
                active        (4),
                activePlus    (5)
        }
        MAX-ACCESS read-only
        STATUS current
        DESCRIPTION
                "Activation state of the CMPC subchannel.
                   shutdown    - CMCC interface with this CMPC
                                 subchannel configured is shutdown.
                   inactive    - CMCC physical channel up, CMPC 
                                 subchannel has not started to 
                                 activate yet.
                   xid2Pending - VTAM and CMCC CMPC have started
                                 negotiating channel connection.
                   active      - CMCC CMPC subchannel is active in
                                 MPC or non-HPDT mode.
                   activePlus  - CMCC CMPC subchannel is active in
                                 MPC+ or HPDT mode."
        ::= { cipCmpcSubChannelOperEntry 1 }

cipCmpcSubChannelOperMaxbfru OBJECT-TYPE
        SYNTAX Integer32
        MAX-ACCESS read-only
        STATUS current
        DESCRIPTION
                "Maximum number of 4096 byte buffers allowed per
                 channel block I/O on this CMPC subchannel. For host 
                 write subchannels, this is the maximum number of 
                 4096 byte buffers the host can write to the CMCC for 
                 each channel block I/O. Since the CMCC is capable of 
                 receiving 16 4096 byte buffers per channel block I/O, 
                 the value on host write subchannels will always be 16. 
                 For host read subchannels, this is the maximum number 
                 of 4096 byte buffers the host can read from the CMCC
                 for each channel block I/O."
        ::= { cipCmpcSubChannelOperEntry 2 }

-- ;;;;;;;;;;;;;;;;;; cipCmpcTgOperTable ;;;;;;;;;;;;;;;;;;;;;;;;

cipCmpcTgOperTable OBJECT-TYPE
        SYNTAX SEQUENCE OF CipCmpcTgOperEntry
        MAX-ACCESS not-accessible
        STATUS current
        DESCRIPTION
                "This table contains Operational information 
                 for each instance of a CMPC Transmission 
                 Group (TG).

                 Each instance of this table is created for every
                 CMPC TG with a unique tg-name configured on a 
                 CMCC card."
        ::= { cipCmpcTg 1 }

cipCmpcTgOperEntry OBJECT-TYPE
        SYNTAX CipCmpcTgOperEntry
        MAX-ACCESS not-accessible
        STATUS current
        DESCRIPTION
                "A list of CMPC TG Operational objects."
        INDEX   { ifIndex, 
            cipCmpcTgOperName }
        ::= { cipCmpcTgOperTable 1 }

CipCmpcTgOperEntry ::= SEQUENCE
{
        cipCmpcTgOperName                        ChannelTgName,
        cipCmpcTgOperLastSeqNumFailureCause      INTEGER,
        cipCmpcTgOperLastSeqNumFailureTime       TimeStamp,
        cipCmpcTgOperExpectedReceiveSeqNum       Integer32,
        cipCmpcTgOperLastSeqNumReceived          Integer32,
        cipCmpcTgOperLastSeqNumSent              Integer32
}

cipCmpcTgOperName OBJECT-TYPE
        SYNTAX ChannelTgName
        MAX-ACCESS not-accessible
        STATUS current
        DESCRIPTION
                "This is the name for this instance of a 
                 CMPC transmission group (TG)."
        ::= { cipCmpcTgOperEntry 1 }

cipCmpcTgOperLastSeqNumFailureCause OBJECT-TYPE
        SYNTAX INTEGER {
                none            (1),
                blockSeqError   (2),
                sweepSeqError   (3)
         }
        MAX-ACCESS read-only
        STATUS current
        DESCRIPTION
                "The last CMPC TG sequence number failure
                 cause.

                 none              - No sequence number errors
                                     have been detected.
                 blockSeqError     - Sequence number received
                                     in a cmpc I/O block did not
                                     match the expected sequence
                                     number.
                 sweepSeqError     - Sequence number received in
                                     a sweep message does not compare
                                     to the expected sequence number.
                                     for this CMPC TG."
        ::= { cipCmpcTgOperEntry 2 }

cipCmpcTgOperLastSeqNumFailureTime OBJECT-TYPE
        SYNTAX TimeStamp
        MAX-ACCESS read-only
        STATUS current
        DESCRIPTION
                "This object describes the value of sysUpTime
                when this CMPC TG last detected a sequence 
                number error.  If the CMPC TG has not failed,
                then this value shall be zero."
        ::= { cipCmpcTgOperEntry 3 }

cipCmpcTgOperExpectedReceiveSeqNum OBJECT-TYPE
        SYNTAX Integer32
        MAX-ACCESS read-only
        STATUS current
        DESCRIPTION
                "This is the sequence number expected from the 
                 host by this CMPC TG."
        ::= { cipCmpcTgOperEntry 4 }

cipCmpcTgOperLastSeqNumReceived OBJECT-TYPE
        SYNTAX Integer32
        MAX-ACCESS read-only
        STATUS current
        DESCRIPTION
                "This is the last sequence number received 
                 from the host by this CMPC TG."
        ::= { cipCmpcTgOperEntry 5 }

cipCmpcTgOperLastSeqNumSent OBJECT-TYPE
        SYNTAX Integer32
        MAX-ACCESS read-only
        STATUS current
        DESCRIPTION
                "This is the last sequence number sent
                 to the host by this CMPC TG."
        ::= { cipCmpcTgOperEntry 6 }

-- ;;;;;;;;;;;;;;;;;; cipCmpcTgStatsTable ;;;;;;;;;;;;;;;;;;;;;;;;

cipCmpcTgStatsTable OBJECT-TYPE
        SYNTAX SEQUENCE OF CipCmpcTgStatsEntry
        MAX-ACCESS not-accessible
        STATUS current
        DESCRIPTION
                "This table contains statistical information 
                 for each instance of a CMPC Transmission 
                 Group (TG).

                 Each instance of this table is created for every CMPC
                 TG with a unique tg-name configured on a CMCC card."
        ::= { cipCmpcTg 2 }

cipCmpcTgStatsEntry OBJECT-TYPE
        SYNTAX CipCmpcTgStatsEntry
        MAX-ACCESS not-accessible
        STATUS current
        DESCRIPTION
                "A list of CMPC TG statistical objects."
        AUGMENTS    { cipCmpcTgOperEntry }
        ::= { cipCmpcTgStatsTable 1 }

CipCmpcTgStatsEntry ::= SEQUENCE
{
        cipCmpcTgStatsConnectReqs                Counter32,
        cipCmpcTgStatsConnectInds                Counter32,
        cipCmpcTgStatsConnectRsps                Counter32,
        cipCmpcTgStatsConnectCnfms               Counter32,
        cipCmpcTgStatsDiscReqs                   Counter32,
        cipCmpcTgStatsDiscInds                   Counter32,
        cipCmpcTgStatsSweepReqsIn                Counter32,
        cipCmpcTgStatsSweepReqsOut               Counter32,
        cipCmpcTgStatsSweepRspsIn                Counter32,
        cipCmpcTgStatsSweepRspsOut               Counter32,
        cipCmpcTgStatsWraps                      Counter32
}

cipCmpcTgStatsConnectReqs OBJECT-TYPE
        SYNTAX Counter32
        MAX-ACCESS read-only
        STATUS current
        DESCRIPTION
                "Number of connect requests received from
                 the host by this CMPC TG."
        ::= { cipCmpcTgStatsEntry 1 }

cipCmpcTgStatsConnectInds OBJECT-TYPE
        SYNTAX Counter32
        MAX-ACCESS read-only
        STATUS current
        DESCRIPTION
                "Number of connect indications sent to the
                 host by this CMPC TG."
        ::= { cipCmpcTgStatsEntry 2 }

cipCmpcTgStatsConnectRsps OBJECT-TYPE
        SYNTAX Counter32
        MAX-ACCESS read-only
        STATUS current
        DESCRIPTION
                "Number of connect responses received from 
                 the host by this CMPC TG."
        ::= { cipCmpcTgStatsEntry 3 }

cipCmpcTgStatsConnectCnfms OBJECT-TYPE
        SYNTAX Counter32
        MAX-ACCESS read-only
        STATUS current
        DESCRIPTION
                "Number of connect confirms sent to the host 
                 by this CMPC TG."
        ::= { cipCmpcTgStatsEntry 4 }

cipCmpcTgStatsDiscReqs OBJECT-TYPE
        SYNTAX Counter32
        MAX-ACCESS read-only
        STATUS current
        DESCRIPTION
                "Number of disconnect requests received from 
                 the host by this CMPC TG."
        ::= { cipCmpcTgStatsEntry 5 }

cipCmpcTgStatsDiscInds OBJECT-TYPE
        SYNTAX Counter32
        MAX-ACCESS read-only
        STATUS current
        DESCRIPTION
                "Number of disconnect Indications sent to the
                 host by this CMPC TG."
        ::= { cipCmpcTgStatsEntry 6 }

cipCmpcTgStatsSweepReqsIn OBJECT-TYPE
        SYNTAX Counter32
        MAX-ACCESS read-only
        STATUS current
        DESCRIPTION
                "Number of sweep requests received 
                 from from the host by this CMPC TG."
        ::= { cipCmpcTgStatsEntry 7 }

cipCmpcTgStatsSweepReqsOut OBJECT-TYPE
        SYNTAX Counter32
        MAX-ACCESS read-only
        STATUS current
        DESCRIPTION
                "Number of CMPC sweep requests sent by 
                 this CMPC TG."
        ::= { cipCmpcTgStatsEntry 8 }

cipCmpcTgStatsSweepRspsIn OBJECT-TYPE
        SYNTAX Counter32
        MAX-ACCESS read-only
        STATUS current
        DESCRIPTION
                "Number of CMPC sweep responses received 
                 from VTAM by this CMPC TG."
        ::= { cipCmpcTgStatsEntry 9 }

cipCmpcTgStatsSweepRspsOut OBJECT-TYPE
        SYNTAX Counter32
        MAX-ACCESS read-only
        STATUS current
        DESCRIPTION
                "Number of CMPC sweep responses sent by 
                 this CMPC TG."
        ::= { cipCmpcTgStatsEntry 10 }

cipCmpcTgStatsWraps OBJECT-TYPE
        SYNTAX Counter32
        MAX-ACCESS read-only
        STATUS current
        DESCRIPTION
                "Number of times the CMPC sequence number 
                 for this TG has wrapped."
        ::= { cipCmpcTgStatsEntry 11 }

--
-- ;;;;;;;;;;;;;;;;;;;;;;;;;;;;;;;;;;;;;;;;;;;;;;;;;;;;;;;;;;;;;;;;;;;;;;;;;;
--
-- Notifications
--

cipCmpcNotificationPrefix OBJECT IDENTIFIER ::= { ciscoCipCmpcMIB 2 }
cipCmpcNotifications OBJECT IDENTIFIER ::= { cipCmpcNotificationPrefix 0 }

cipCmpcDirectionMismatch NOTIFICATION-TYPE
        OBJECTS {
                cipCmpcSubChannelAdminDirection
        }
        STATUS current
        DESCRIPTION
                "This trap indicates that the 
                 configured direction for the specified
                 CMPC subchannel does not match
                 the direction specified by the host.

                 The CMPC subchannel will not activate
                 as long as this mismatch exists."
        ::= { cipCmpcNotifications 1 }

cipCmpcSeqNumError NOTIFICATION-TYPE
        OBJECTS {
                cipCmpcTgOperLastSeqNumFailureCause,
                cipCmpcTgOperExpectedReceiveSeqNum,
                cipCmpcTgOperLastSeqNumReceived
        }
        STATUS current
        DESCRIPTION
                "This trap indicates that the CMPC 
                 TG has detected an MPC sequence 
                 number error.

                 This error will cause the CMPC TG
                 to disconnect."
        ::= { cipCmpcNotifications 2 }

--
-- ;;;;;;;;;;;;;;;;;;;;;;;;;;;;;;;;;;;;;;;;;;;;;;;;;;;;;;;;;;;;;;;;;;;;;;;;;;
--
-- Conformance Information
--

ciscoCipCmpcMibConformance OBJECT IDENTIFIER ::= { ciscoCipCmpcMIB 3 }
ciscoCipCmpcMibCompliances OBJECT IDENTIFIER ::= { ciscoCipCmpcMibConformance 1 }
ciscoCipCmpcMibGroups OBJECT IDENTIFIER ::= { ciscoCipCmpcMibConformance 2 }

--
-- Compliance Statements
--

ciscoCipCmpcMibCompliance MODULE-COMPLIANCE
        STATUS current
        DESCRIPTION
                "The compliance statement for the Cisco Multi-Path
                Channel (CMPC) feature."
        MODULE MANDATORY-GROUPS {
              ciscoCipCmpcSubChannelGroup,
              ciscoCipCmpcTgGroup
        }
        ::= { ciscoCipCmpcMibCompliances 1 }

ciscoCipCmpcSubChannelGroup OBJECT-GROUP
        OBJECTS {
                -- Table Header
                --  cipCmpcSubChannelAdminTable
                --  cipCmpcSubChannelAdminEntry
                -- Table Header
                --  cipCmpcSubChannelOperTable
                --  cipCmpcSubChannelOperEntry
                -- Table Indicies
                --  cipCardEntryIndex
                --  cipCardDtrBrdIndex
                --  cipCardSubChannelIndex

                cipCmpcSubChannelAdminPath,
                cipCmpcSubChannelAdminDevice,
                cipCmpcSubChannelAdminTgName,
                cipCmpcSubChannelAdminDirection,
                cipCmpcSubChannelAdminTgTransport,
                cipCmpcSubChannelAdminRowStatus,
                cipCmpcSubChannelOperState,
                cipCmpcSubChannelOperMaxbfru
        }
        STATUS current
        DESCRIPTION
                "A collection of objects providing Cisco 
                Multi-Path Channel (CMPC) Administration, 
                Operational status and Statistics."
        ::= { ciscoCipCmpcMibGroups 1 }

ciscoCipCmpcTgGroup OBJECT-GROUP
        OBJECTS {
                -- Table Header
                --  cipCmpcTgOperTable
                --  cipCmpcTgOperEntry
                -- Table Header
                --  cipCmpcTgStatsTable
                --  cipCmpcTgStatsEntry
                -- Table Indicies
                --  ifIndex
                --  cipCmpcTgOperName

                cipCmpcTgOperLastSeqNumFailureCause,
                cipCmpcTgOperLastSeqNumFailureTime,
                cipCmpcTgOperExpectedReceiveSeqNum,
                cipCmpcTgOperLastSeqNumReceived,
                cipCmpcTgOperLastSeqNumSent,
                cipCmpcTgStatsConnectReqs,
                cipCmpcTgStatsConnectInds,
                cipCmpcTgStatsConnectRsps,
                cipCmpcTgStatsConnectCnfms,
                cipCmpcTgStatsDiscReqs,
                cipCmpcTgStatsDiscInds,
                cipCmpcTgStatsSweepReqsIn,
                cipCmpcTgStatsSweepReqsOut,
                cipCmpcTgStatsSweepRspsIn,
                cipCmpcTgStatsSweepRspsOut,
                cipCmpcTgStatsWraps
        }
        STATUS current
        DESCRIPTION
                "A collection of objects providing CMPC
                 TG Operational and Statistical information."
        ::= { ciscoCipCmpcMibGroups 2 }

END
