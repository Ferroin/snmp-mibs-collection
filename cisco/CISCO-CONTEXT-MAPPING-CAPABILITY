CISCO-CONTEXT-MAPPING-CAPABILITY DEFINITIONS ::= BEGIN

IMPORTS
    MODULE-IDENTITY
        FROM SNMPv2-SMI
    AGENT-CAPABILITIES
        FROM SNMPv2-CONF
    ciscoAgentCapability
        FROM CISCO-SMI;

ciscoContextMappingCapability MODULE-IDENTITY
    LAST-UPDATED    "200808220000Z"
    ORGANIZATION    "Cisco Systems, Inc."
    CONTACT-INFO
            "Cisco Systems
            Customer Service

            Postal: 170 West Tasman Drive
            San Jose, CA  95134
            USA

            Tel: +1 800 553-NETS

            E-mail: cs-snmp@cisco.com"
    DESCRIPTION
        "Agent capabilities for the
        CISCO-CONTEXT-MAPPING-MIB."
    REVISION        "200808220000Z"
    DESCRIPTION
        "Added ciscoContextMappingIOSXRV3R7FCICRS1"
    REVISION        "200803240000Z"
    DESCRIPTION
        "Added ciscoContextMappingCapV12R02SG"
    REVISION        "200505200000Z"
    DESCRIPTION
        "Initial version of this MIB module."
    ::= { ciscoAgentCapability 564 }

ciscoContextMappingCapV12R02S AGENT-CAPABILITIES
    PRODUCT-RELEASE "Cisco IOS 12.2S"
    STATUS          current
    DESCRIPTION
        "CISCO-CONTEXT-MAPPING-MIB capabilities."

    SUPPORTS        CISCO-CONTEXT-MAPPING-MIB
    INCLUDES        { cContextMappingDataGroup }
    VARIATION       cContextMappingVrfName
    ACCESS          read-only
    DESCRIPTION
        "Write/create not implemented."

    VARIATION       cContextMappingTopologyName
    ACCESS          read-only
    DESCRIPTION
        "Write/create not implemented."

    VARIATION       cContextMappingProtoInstName
    ACCESS          read-only
    DESCRIPTION
        "Write/create not implemented."

    VARIATION       cContextMappingStorageType
    ACCESS          read-only
    DESCRIPTION
        "Write/create not implemented."

    VARIATION       cContextMappingRowStatus
    ACCESS          read-only
    DESCRIPTION
        "Write/create not implemented."
    ::= { ciscoContextMappingCapability 1 }

ciscoContextMappingCapV12R02SG AGENT-CAPABILITIES
    PRODUCT-RELEASE "Cisco IOS 12.2SG"
    STATUS          current
    DESCRIPTION
        "CISCO-CONTEXT-MAPPING-MIB capabilities."

    SUPPORTS        CISCO-CONTEXT-MAPPING-MIB
    INCLUDES        {
                        cContextMappingDataGroup,
                        cContextMappingBridgeDomainDataGroup
                    }
    VARIATION       cContextMappingVrfName
    ACCESS          read-only
    DESCRIPTION
        "Write/create not implemented."

    VARIATION       cContextMappingTopologyName
    ACCESS          read-only
    DESCRIPTION
        "Write/create not implemented."

    VARIATION       cContextMappingProtoInstName
    ACCESS          read-only
    DESCRIPTION
        "Write/create not implemented."

    VARIATION       cContextMappingStorageType
    ACCESS          read-only
    DESCRIPTION
        "Write/create not implemented."

    VARIATION       cContextMappingRowStatus
    ACCESS          read-only
    DESCRIPTION
        "Write/create not implemented."

    VARIATION       cContextMappingBridgeDomainIdentifier
    ACCESS          read-only
    DESCRIPTION
        "Write/create not implemented."

    VARIATION       cContextMappingBridgeDomainStorageType
    ACCESS          read-only
    DESCRIPTION
        "Write/create not implemented."

    VARIATION       cContextMappingBridgeDomainRowStatus
    ACCESS          read-only
    DESCRIPTION
        "Write/create not implemented."
    ::= { ciscoContextMappingCapability 2 }

ciscoContextMappingIOSXRV3R7FCICRS1 AGENT-CAPABILITIES
    PRODUCT-RELEASE "Cisco IOS XR 3.7FCI for CRS-1"
    STATUS          current
    DESCRIPTION
        "CISCO-CONTEXT-MAPPING-MIB capabilities."

    SUPPORTS        CISCO-CONTEXT-MAPPING-MIB
    INCLUDES        {
                        cContextMappingDataGroup,
                        cContextMappingBridgeDomainDataGroup,
                        cContextMappingBridgeInstanceDataGroup
                    }
    VARIATION       cContextMappingVrfName
    ACCESS          read-only
    DESCRIPTION
        "Write/create not implemented."

    VARIATION       cContextMappingTopologyName
    ACCESS          not-implemented
    DESCRIPTION     "Not supported."

    VARIATION       cContextMappingProtoInstName
    ACCESS          not-implemented
    DESCRIPTION     "Not supported."

    VARIATION       cContextMappingStorageType
    ACCESS          read-only
    DESCRIPTION
        "Write/create not implemented."

    VARIATION       cContextMappingRowStatus
    ACCESS          read-only
    DESCRIPTION
        "Write/create not implemented."

    VARIATION       cContextMappingBridgeDomainIdentifier
    ACCESS          not-implemented
    DESCRIPTION     "Not supported."

    VARIATION       cContextMappingBridgeDomainStorageType
    ACCESS          not-implemented
    DESCRIPTION     "Not supported."

    VARIATION       cContextMappingBridgeDomainRowStatus
    ACCESS          not-implemented
    DESCRIPTION     "Not supported."

    VARIATION       cContextMappingBridgeInstName
    ACCESS          read-only
    DESCRIPTION
        "Write access is not required."

    VARIATION       cContextMappingBridgeInstStorageType
    ACCESS          read-only
    DESCRIPTION
        "Write/create not implemented."

    VARIATION       cContextMappingBridgeInstRowStatus
    ACCESS          read-only
    DESCRIPTION
        "Write/create not implemented."
    ::= { ciscoContextMappingCapability 3 }

END
