CISCO-AAA-SERVER-EXT-CAPABILITY DEFINITIONS ::= BEGIN

IMPORTS
    MODULE-IDENTITY,
    Unsigned32
        FROM SNMPv2-SMI
    AGENT-CAPABILITIES
        FROM SNMPv2-CONF
    TimeIntervalSec
        FROM CISCO-TC
    ciscoAgentCapability
        FROM CISCO-SMI;

ciscoAAAServerExtCapability MODULE-IDENTITY
    LAST-UPDATED    "200806160000Z"
    ORGANIZATION    "Cisco Systems, Inc."
    CONTACT-INFO
            "Cisco Systems
            Customer Service

            Postal: 170 W Tasman Drive
            San Jose, CA  95134
            USA

            Tel: +1 800 553-NETS

            E-mail: cs-aaa@cisco.com"
    DESCRIPTION
        "Agent capabilities for CISCO-AAA-SERVER-EXT-MIB"
    REVISION        "200806160000Z"
    DESCRIPTION
        "Agent capabilities for Cisco ACE 4710 Application
        Control Engine Appliance."
    REVISION        "200602210000Z"
    DESCRIPTION
        "Agent capabilities for Cisco
        Application Control Engine (ACE)."
    REVISION        "200408240000Z"
    DESCRIPTION
        "Agent capabilities for Cisco MDS 2.0."
    REVISION        "200311220000Z"
    DESCRIPTION
        "Agent capabilities for Cisco MDS 1.3."
    ::= { ciscoAgentCapability 372 }

ciscoAAAServerExtCapMDS13R1 AGENT-CAPABILITIES
    PRODUCT-RELEASE "Cisco MDS 1.3(1)"
    STATUS          current
    DESCRIPTION
        "Cisco AAA Server MIB capabilities"

    SUPPORTS        CISCO-AAA-SERVER-EXT-MIB
    INCLUDES        {
                        cAAASvrExtGenericConfGroup,
                        cAAASvrExtSvrTableConfGroup,
                        cAAASvrExtProtoParamConfigGroup,
                        cAAASvrExtSvrGroupConfGroup,
                        cAAASvrExtAppSvrGroupConfGroup
                    }
    VARIATION       cAAASvrExtLocalAccLogMaxSize
    SYNTAX          Unsigned32 (0..35000)
    DESCRIPTION
        "Only the range 0-35000 is supported with
        default of 15000."

    VARIATION       cAAAServerDeadTime
    ACCESS          not-implemented
    DESCRIPTION
        "Not supported."

    VARIATION       cAAAServerTimeOut
    SYNTAX          TimeIntervalSec (0..60)
    DESCRIPTION
        "Only the range 0-60 is supported.
        The value of this object is not currently
        used for radius in the implementation and
        hence ignored for radius server entries."

    VARIATION       cAAAServerRetransmits
    ACCESS          not-implemented
    DESCRIPTION
        "Not supported."

    VARIATION       cAAAServerProtoDeadTime
    ACCESS          not-implemented
    DESCRIPTION
        "Not supported."

    VARIATION       cAAAServerProtoTimeOut
    SYNTAX          TimeIntervalSec (1..60)
    DESCRIPTION
        "Only the range 1-60 is supported."

    VARIATION       cAAAServerProtoRetransmits
    SYNTAX          Unsigned32 (0..5)
    DESCRIPTION
        "Only the range of 0-5 is supported. The object
        is  not relevant for tacacs+ servers and hence
        the value is ignored."

    VARIATION       cAAASvrExtSvrGrpConfigEntry
    DESCRIPTION
        "There is a special agent defined group with
        'cAAASvrGrpIndex' as 1, 'cAAASvrGrpName' as
        'radius' and 'cAAASvrGrpProtocol' as 'radius'.
        Whenever this group is used by any aplication
        in the system  for any of the AAA functions,
        then the value of corresponding instance of
        'cAAAServerList' is updated with all the AAA
        server entries in the agent. This group entry
        can not be deleted by the user."

    VARIATION       cAAAServerProtocol
    DESCRIPTION
        "The supported protcols are;
        - tacacsplus(1) - TACACS+
        - radius(2)     - RADIUS
        ."

    VARIATION       cAAASvrGrpConfigRowStatus
    DESCRIPTION
        "Only allowed values are :
        - createAndGo(4)
        - destroy(6)
        - active(1)
        ."

    VARIATION       cAAASvrGrpProtocol
    DESCRIPTION
        "The supported protcols are;
        - tacacsplus(1) - TACACS+
        - radius(2)     - RADIUS
        ."
    ::= { ciscoAAAServerExtCapability 1 }

ciscoAAAServerExtCapMDS20R1 AGENT-CAPABILITIES
    PRODUCT-RELEASE "Cisco MDS 2.0(1)"
    STATUS          current
    DESCRIPTION
        "Cisco AAA Server MIB capabilities"

    SUPPORTS        CISCO-AAA-SERVER-EXT-MIB
    INCLUDES        {
                        cAAASvrExtGenericConfGroup,
                        cAAASvrExtSvrTableConfGroup,
                        cAAASvrExtProtoParamConfigGroup,
                        cAAASvrExtSvrGroupConfGroup,
                        cAAASvrExtAppSvrGroupConfGroup
                    }
    VARIATION       cAAASvrExtLocalAccLogMaxSize
    ACCESS          not-implemented
    DESCRIPTION
        "Not supported."

    VARIATION       cAAAServerDeadTime
    ACCESS          not-implemented
    DESCRIPTION
        "Not supported."

    VARIATION       cAAAServerTimeOut
    SYNTAX          TimeIntervalSec (0..60)
    DESCRIPTION
        "Only the range 0-60 is supported."

    VARIATION       cAAAServerRetransmits
    SYNTAX          Unsigned32 (0..5)
    DESCRIPTION
        "Only the range of 0-5 is supported. The object
        is not relevant for tacacs+ servers and hence
        the value is ignored."

    VARIATION       cAAAServerProtoDeadTime
    ACCESS          not-implemented
    DESCRIPTION
        "Not supported."

    VARIATION       cAAAServerProtoTimeOut
    SYNTAX          TimeIntervalSec (1..60)
    DESCRIPTION
        "Only the range 1-60 is supported."

    VARIATION       cAAAServerProtoRetransmits
    SYNTAX          Unsigned32 (0..5)
    DESCRIPTION
        "Only the range of 0-5 is supported. The object
        is not relevant for tacacs+ servers and hence
        the value is ignored."

    VARIATION       cAAASvrExtSvrGrpConfigEntry
    DESCRIPTION
        "There is a special agent defined group with
        'cAAASvrGrpIndex' as 1, 'cAAASvrGrpName' as
        'radius' and 'cAAASvrGrpProtocol' as 'radius'.
        Whenever this group is used by any application
        in the system for any of the AAA functions,
        then the value of corresponding instance of
        'cAAAServerList' is updated with all the AAA
        server entries in the agent. This group entry
        can not be deleted by the user."

    VARIATION       cAAAServerProtocol
    DESCRIPTION
        "The supported protcols are;
        - tacacsplus(1) - TACACS+
        - radius(2)     - RADIUS
        ."

    VARIATION       cAAASvrGrpConfigRowStatus
    DESCRIPTION
        "Only allowed values are :
        - createAndGo(4)
        - destroy(6)
        - active(1)
        ."

    VARIATION       cAAASvrGrpProtocol
    DESCRIPTION
        "The supported protcols are;
        - tacacsplus(1) - TACACS+
        - radius(2)     - RADIUS
        ."
    ::= { ciscoAAAServerExtCapability 2 }

ciscoAAAServerExtCapACSWV03R000 AGENT-CAPABILITIES
    PRODUCT-RELEASE "ACSW (Application Control Software) 3.0"
    STATUS          current
    DESCRIPTION
        "Cisco AAA Server MIB capabilities"

    SUPPORTS        CISCO-AAA-SERVER-EXT-MIB
    INCLUDES        {
                        cAAASvrExtSvrTableConfGroup,
                        cAAASvrExtAppSvrGroupConfGroup,
                        cAAASvrExtGenericConfGroup1,
                        cAAASvrExtGenericConfGroup2,
                        cAAASvrExtSvrGroupConfGroup2,
                        cAAASvrExtProtoParamConfigGroup1,
                        cAAASvrExtSvrTableLDAPConfGroup,
                        cAAASvrExtSvrGroupLDAPConfGroup
                    }
    VARIATION       cAAAServerAddrType
    ACCESS          read-only
    DESCRIPTION
        "Create operation not supported."

    VARIATION       cAAAServerAddr
    ACCESS          read-only
    DESCRIPTION
        "Create operation not supported."

    VARIATION       cAAAServerKeyEncrType
    ACCESS          read-only
    DESCRIPTION
        "Create operation not supported."

    VARIATION       cAAAServerDeadTime
    ACCESS          not-implemented
    DESCRIPTION
        "Not supported."

    VARIATION       cAAAServerTimeOut
    SYNTAX          TimeIntervalSec (0..60)
    ACCESS          read-only
    DESCRIPTION
        "Only the range 0-60 is supported.
        Create operation not supported."

    VARIATION       cAAAServerRetransmits
    SYNTAX          Unsigned32 (0..5)
    ACCESS          read-only
    DESCRIPTION
        "Only the range of 0-5 is supported. The object
        is not relevant for tacacs+ servers and hence
        the value is ignored.
        Create operation not supported."

    VARIATION       cAAASvrGrpLocal
    ACCESS          read-only
    DESCRIPTION
        "Create operation not supported."

    VARIATION       cAAASvrGrpTrivial
    ACCESS          read-only
    DESCRIPTION
        "Create operation not supported."

    VARIATION       cAAASvrGrpList
    ACCESS          read-only
    DESCRIPTION
        "Create operation not supported."

    VARIATION       cAAASvrExtAppToSvrGrpMaxEnt
    SYNTAX          Unsigned32 (8 )
    DESCRIPTION
        "The maximum number of Server Group
        entries the Agent supports is 8."

    VARIATION       cAAASvrExtLocalAccLogMaxSize
    ACCESS          not-implemented
    DESCRIPTION
        "Not supported."

    VARIATION       cAAASvrExtClearAccLog
    ACCESS          read-only
    DESCRIPTION
        "Set operation not supported."

    VARIATION       cAAALoginAuthTypeMSCHAP
    ACCESS          read-only
    DESCRIPTION
        "Set operation not supported."

    VARIATION       cAAASvrGrpName
    ACCESS          read-only
    DESCRIPTION
        "Create operation not supported."

    VARIATION       cAAASvrGrpProtocol
    ACCESS          read-only
    DESCRIPTION
        "Create operation not supported."

    VARIATION       cAAAServerList
    ACCESS          read-only
    DESCRIPTION
        "Create operation not supported."

    VARIATION       cAAASvrGrpConfigRowStatus
    ACCESS          read-only
    DESCRIPTION
        "Create operation not supported."

    VARIATION       cAAASvrExtSvrGrpSvrListMaxEnt
    SYNTAX          Unsigned32 (12 )
    DESCRIPTION
        "The maximum number of Server Group
        entries the Agent supports is 12."

    VARIATION       cAAASvrGrpConfigDeadTime
    ACCESS          read-only
    DESCRIPTION
        "Create operation not supported."

    VARIATION       cAAAServerProtoAuthKey
    ACCESS          read-only
    DESCRIPTION
        "Create operation not supported."

    VARIATION       cAAAServerProtoKeyEncrType
    ACCESS          read-only
    DESCRIPTION
        "Create operation not supported."

    VARIATION       cAAAServerProtoDeadTime
    ACCESS          read-only
    DESCRIPTION
        "Create operation not supported."

    VARIATION       cAAAServerProtoTimeOut
    SYNTAX          TimeIntervalSec (1..60)
    ACCESS          read-only
    DESCRIPTION
        "Only the range 1-60 is supported.
        Create operation not supported."

    VARIATION       cAAAServerProtoRetransmits
    SYNTAX          Unsigned32 (0..5)
    ACCESS          read-only
    DESCRIPTION
        "Only the range of 0-5 is supported. The object
        is not relevant for tacacs+ servers and hence
        the value is ignored.
        Create operation not supported."

    VARIATION       cAAAServerProtoSvrTableMaxEnt
    SYNTAX          Unsigned32 (64 )
    DESCRIPTION
        "The maximum number of AAA server
        entries in the 'casConfigTable'
        for a particular protocol is 64."

    VARIATION       cAAAServerProtoDirectedReq
    ACCESS          read-only
    DESCRIPTION
        "Create operation not supported."

    VARIATION       cAAAServerRootDN
    ACCESS          read-only
    DESCRIPTION
        "Create operation not supported."

    VARIATION       cAAASvrGrpLDAPBaseDN
    ACCESS          read-only
    DESCRIPTION
        "Create operation not supported."

    VARIATION       cAAASvrGrpLDAPFilterUser
    ACCESS          read-only
    DESCRIPTION
        "Create operation not supported."

    VARIATION       cAAASvrGrpLDAPUserProfile
    ACCESS          read-only
    DESCRIPTION
        "Create operation not supported."
    ::= { ciscoAAAServerExtCapability 3 }

ciscoAAAServerExtCapc4710aceVA1R700 AGENT-CAPABILITIES
    PRODUCT-RELEASE "ACSW (Application Control Software) A1(7)
                        for ACE 4710 Application Control Engine 
                        Appliance."
    STATUS          current
    DESCRIPTION
        "Cisco AAA Server MIB capabilities"

    SUPPORTS        CISCO-AAA-SERVER-EXT-MIB
    INCLUDES        {
                        cAAASvrExtSvrTableConfGroup,
                        cAAASvrExtAppSvrGroupConfGroup,
                        cAAASvrExtGenericConfGroup1,
                        cAAASvrExtGenericConfGroup2,
                        cAAASvrExtSvrGroupConfGroup2,
                        cAAASvrExtProtoParamConfigGroup1,
                        cAAASvrExtSvrTableLDAPConfGroup,
                        cAAASvrExtSvrGroupLDAPConfGroup
                    }
    VARIATION       cAAAServerAddrType
    ACCESS          read-only
    DESCRIPTION
        "Create operation not supported."

    VARIATION       cAAAServerAddr
    ACCESS          read-only
    DESCRIPTION
        "Create operation not supported."

    VARIATION       cAAAServerKeyEncrType
    ACCESS          read-only
    DESCRIPTION
        "Create operation not supported."

    VARIATION       cAAAServerDeadTime
    ACCESS          not-implemented
    DESCRIPTION
        "Not supported."

    VARIATION       cAAAServerTimeOut
    SYNTAX          TimeIntervalSec (0..60)
    ACCESS          read-only
    DESCRIPTION
        "Only the range 0-60 is supported.
        Create operation not supported."

    VARIATION       cAAAServerRetransmits
    SYNTAX          Unsigned32 (0..5)
    ACCESS          read-only
    DESCRIPTION
        "Only the range of 0-5 is supported. The object
        is not relevant for tacacs+ servers and hence
        the value is ignored.
        Create operation not supported."

    VARIATION       cAAASvrGrpLocal
    ACCESS          read-only
    DESCRIPTION
        "Create operation not supported."

    VARIATION       cAAASvrGrpTrivial
    ACCESS          read-only
    DESCRIPTION
        "Create operation not supported."

    VARIATION       cAAASvrGrpList
    ACCESS          read-only
    DESCRIPTION
        "Create operation not supported."

    VARIATION       cAAASvrExtAppToSvrGrpMaxEnt
    SYNTAX          Unsigned32 (8 )
    DESCRIPTION
        "The maximum number of Server Group
        entries the Agent supports is 8."

    VARIATION       cAAASvrExtLocalAccLogMaxSize
    ACCESS          not-implemented
    DESCRIPTION
        "Not supported."

    VARIATION       cAAASvrExtClearAccLog
    ACCESS          read-only
    DESCRIPTION
        "Set operation not supported."

    VARIATION       cAAALoginAuthTypeMSCHAP
    ACCESS          read-only
    DESCRIPTION
        "Set operation not supported."

    VARIATION       cAAASvrGrpName
    ACCESS          read-only
    DESCRIPTION
        "Create operation not supported."

    VARIATION       cAAASvrGrpProtocol
    ACCESS          read-only
    DESCRIPTION
        "Create operation not supported."

    VARIATION       cAAAServerList
    ACCESS          read-only
    DESCRIPTION
        "Create operation not supported."

    VARIATION       cAAASvrGrpConfigRowStatus
    ACCESS          read-only
    DESCRIPTION
        "Create operation not supported."

    VARIATION       cAAASvrExtSvrGrpSvrListMaxEnt
    SYNTAX          Unsigned32 (12 )
    DESCRIPTION
        "The maximum number of Server Group
        entries the Agent supports is 12."

    VARIATION       cAAASvrGrpConfigDeadTime
    ACCESS          read-only
    DESCRIPTION
        "Create operation not supported."

    VARIATION       cAAAServerProtoAuthKey
    ACCESS          read-only
    DESCRIPTION
        "Create operation not supported."

    VARIATION       cAAAServerProtoKeyEncrType
    ACCESS          read-only
    DESCRIPTION
        "Create operation not supported."

    VARIATION       cAAAServerProtoDeadTime
    ACCESS          read-only
    DESCRIPTION
        "Create operation not supported."

    VARIATION       cAAAServerProtoTimeOut
    SYNTAX          TimeIntervalSec (1..60)
    ACCESS          read-only
    DESCRIPTION
        "Only the range 1-60 is supported.
        Create operation not supported."

    VARIATION       cAAAServerProtoRetransmits
    SYNTAX          Unsigned32 (0..5)
    ACCESS          read-only
    DESCRIPTION
        "Only the range of 0-5 is supported. The object
        is not relevant for tacacs+ servers and hence
        the value is ignored.
        Create operation not supported."

    VARIATION       cAAAServerProtoSvrTableMaxEnt
    SYNTAX          Unsigned32 (64 )
    DESCRIPTION
        "The maximum number of AAA server
        entries in the 'casConfigTable'
        for a particular protocol is 64."

    VARIATION       cAAAServerProtoDirectedReq
    ACCESS          read-only
    DESCRIPTION
        "Create operation not supported."

    VARIATION       cAAAServerRootDN
    ACCESS          read-only
    DESCRIPTION
        "Create operation not supported."

    VARIATION       cAAASvrGrpLDAPBaseDN
    ACCESS          read-only
    DESCRIPTION
        "Create operation not supported."

    VARIATION       cAAASvrGrpLDAPFilterUser
    ACCESS          read-only
    DESCRIPTION
        "Create operation not supported."

    VARIATION       cAAASvrGrpLDAPUserProfile
    ACCESS          read-only
    DESCRIPTION
        "Create operation not supported."
    ::= { ciscoAAAServerExtCapability 4 }

END
