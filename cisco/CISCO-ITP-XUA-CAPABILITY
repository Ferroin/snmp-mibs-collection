CISCO-ITP-XUA-CAPABILITY DEFINITIONS ::= BEGIN

IMPORTS
    MODULE-IDENTITY
        FROM SNMPv2-SMI
    AGENT-CAPABILITIES
        FROM SNMPv2-CONF
    ciscoAgentCapability
        FROM CISCO-SMI;

ciscoItpXuaCapability MODULE-IDENTITY
    LAST-UPDATED    "200806250000Z"
    ORGANIZATION    "Cisco Systems, Inc."
    CONTACT-INFO
            "Cisco Systems
            Customer Service

            Postal: 170 West Tasman Drive
                    San Jose, CA  95134
                    USA

            Tel: +1 800 553-NETS

            E-mail: cs-ss7@cisco.com"
    DESCRIPTION     "Agent capabilities for the CISCO-ITP-XUA-MIB."

    REVISION        "200806250000Z"
    DESCRIPTION
        "Added ciscoItpXuaCapabilityV12R0415SW,
               ciscoItpXuaCapabilityV12R0218IXE,
               ciscoItpXuaCapabilityV12R0233IRA capability statements."

    REVISION        "200709260000Z"
    DESCRIPTION
        "Added ciscoItpXuaCapabilityV12R0411SW capability statement.
         Corrected several problems with various capability statements
         as follows.

         Modified ciscoItpXuaCapabilityV12R0225SW

         Modified ciscoItpXuaCapabilityV12R0219SW as follows.
             removed cItpXuaInstOffload
             removed cItpXuaInstOffloadSlot
             added cItpXuaSgmRemoteIpType
             added cItpXuaSgmRemoteIpAddr
             added cItpXuaSgmRemoteIpRowStatus

         Update ciscoItpXuaCapabilityV12R0218IXA based on changes to
         prior capability statements.
         "

    REVISION        "200610050000Z"
    DESCRIPTION
        "Added ciscoItpXuaCapabilityV12R0218IXA capability statement."

    REVISION        "200411030000Z"
    DESCRIPTION
        "Added ciscoItpXuaCapabilityV12R0225SW agent
         capability statement to support the following
         changes.

         Added the following tables.
            cItpXuaASRouteTable
            cItpXuaASRouteAsTable

         Added the following objects.
            cItpXuaAspAsWeight to cItpXuaAspAsTable
            cItpXuaAsNetworkAppear to cItpXuaAsTable
            cItpXuaAsCongLevel to cItpXuaAsTable
        "

    REVISION        "200310150000Z"
    DESCRIPTION
        "Added ciscoItpXuaCapabilityV12R0223SW01 agent
         capability statement to support the following
         changes.

         Deprecated the following object.
           cItpXuaAspAssocId

         Added the following objects.
           cItpXuaAsNetworkName
           cItpXuaAspAssocIdU32"

    REVISION        "200308150000Z"
    DESCRIPTION
        "Added ciscoItpXuaCapabilityV12R0219SW agent
         capability statement to support the following
         changes.

         Added following objects and tables.
           cItpXuaSgmRemoteIpTable
           cItpXuaSgmCongLevel
           cItpXuaAspCongLevel

         Added following notifications.
           ciscoItpXuaAspCongChange
           ciscoItpXuaSgmCongChange"
    REVISION        "200205080000Z"
    DESCRIPTION
        "Initial version of this MIB module."
          ::= { ciscoAgentCapability 268 }

ciscoItpXuaCapabilityV12R0204MB5 AGENT-CAPABILITIES
    PRODUCT-RELEASE "Cisco IOS 12.2(4)MB5"
    STATUS          current
    DESCRIPTION
        "IOS 12.2(4)MB5 Cisco CISCO-ITP-XUA-MIB.my
        User Agent MIB capabilities."

    SUPPORTS        CISCO-ITP-XUA-MIB
    INCLUDES        {
                        ciscoItpXuaScalarsGroup,
                        ciscoItpXuaInstGroup,
                        ciscoItpXuaInstLocalIpGroup,
                        ciscoItpXuaSgmGroup,
                        ciscoItpXuaAspGroup,
                        ciscoItpXuaAspRemoteIpGroup,
                        ciscoItpXuaAspStatsGroup,
                        ciscoItpXuaAsGroup,
                        ciscoItpXuaAspAsGroup,
                        ciscoItpXuaNotifObjectsGroup,
                        ciscoItpXuaNotificationsGroup
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

-- **************************************************************
--              Entries in ASP-AS Table
-- **************************************************************
    VARIATION       cItpXuaAspAsRowStatus
    ACCESS          read-only
    DESCRIPTION     "Create/Write access is not supported."
    ::= { ciscoItpXuaCapability 1 }

ciscoItpXuaCapabilityV12R0219SW AGENT-CAPABILITIES
    PRODUCT-RELEASE "Cisco IOS 12.2(19)SW"
    STATUS          current
    DESCRIPTION
        "IOS 12.2(19)SW Cisco CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroup,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev2
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."
    ::= { ciscoItpXuaCapability 2 }

ciscoItpXuaCapabilityV12R0223SW01 AGENT-CAPABILITIES
    PRODUCT-RELEASE "Cisco IOS 12.2(23)SW01"
    STATUS          current
    DESCRIPTION
        "IOS 12.2(23)SW01 Cisco CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroup,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev3,
                        ciscoItpXuaAsrGroup,
                        ciscoItpXuaAsrAsGroup
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."
    ::= { ciscoItpXuaCapability 3 }

ciscoItpXuaCapabilityV12R0225SW AGENT-CAPABILITIES
    PRODUCT-RELEASE "Cisco IOS 12.2(25)SW"
    STATUS          current
    DESCRIPTION
        "IOS 12.2(25)SW Cisco CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroupRev3,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev3,
                        ciscoItpXuaAsrGroup,
                        ciscoItpXuaAsrAsGroup
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

    VARIATION       cItpXuaAsNetworkAppear
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

    VARIATION       cItpXuaAspAsWeight
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."

-- **************************************************************
--              Entries in cItpXuaASRouteTable Table
-- **************************************************************
    VARIATION       cItpXuaAsrProtocol
    ACCESS          read-only
    DESCRIPTION     "Create/Write access is not supported."

    VARIATION       cItpXuaAsrDpc
    ACCESS          read-only
    DESCRIPTION     "Create/Write access is not supported."

    VARIATION       cItpXuaAsrShut
    ACCESS          read-only
    DESCRIPTION     "Create/Write access is not supported."

    VARIATION       cItpXuaAsrRowStatus
    ACCESS          read-only
    DESCRIPTION     "Create/Write access is not supported."

-- **************************************************************
--              Entries in cItpXuaASRouteAsTable Table
-- **************************************************************
    VARIATION       cItpXuaAsrAsRowStatus
    ACCESS          read-only
    DESCRIPTION     "Create/Write access is not supported."
    ::= { ciscoItpXuaCapability 4 }

ciscoItpXuaCapabilityV12R0218IXA AGENT-CAPABILITIES
    PRODUCT-RELEASE "Cisco IOS 12.2(18)IXA"
    STATUS          current
    DESCRIPTION
        "IOS 12.2(18)IXA Cisco CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroupRev3,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev3,
                        ciscoItpXuaAsrGroup,
                        ciscoItpXuaAsrAsGroup
                    }
-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

    VARIATION       cItpXuaAsNetworkAppear
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

    VARIATION       cItpXuaAspAsWeight
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."

-- **************************************************************
--              Entries in cItpXuaASRouteTable Table
-- **************************************************************
    VARIATION       cItpXuaAsrProtocol
    ACCESS          read-only
    DESCRIPTION     "Create/Write access is not supported."

    VARIATION       cItpXuaAsrDpc
    ACCESS          read-only
    DESCRIPTION     "Create/Write access is not supported."

    VARIATION       cItpXuaAsrShut
    ACCESS          read-only
    DESCRIPTION     "Create/Write access is not supported."

    VARIATION       cItpXuaAsrRowStatus
    ACCESS          read-only
    DESCRIPTION     "Create/Write access is not supported."

-- **************************************************************
--              Entries in cItpXuaASRouteAsTable Table
-- **************************************************************
    VARIATION       cItpXuaAsrAsRowStatus
    ACCESS          read-only
    DESCRIPTION     "Create/Write access is not supported."
    ::= { ciscoItpXuaCapability 5 }

ciscoItpXuaCapabilityV12R0411SW AGENT-CAPABILITIES
    PRODUCT-RELEASE "Cisco IOS 12.4(11)SW"
    STATUS          current
    DESCRIPTION
        "Cisco IOS 12.4(11)SW CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroupRev3,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev3,
                        ciscoItpXuaAsrGroup,
                        ciscoItpXuaAsrAsGroup
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

    VARIATION       cItpXuaAsNetworkAppear
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

    VARIATION       cItpXuaAspAsWeight
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."

-- **************************************************************
--              Entries in cItpXuaASRouteTable Table
-- **************************************************************
    VARIATION       cItpXuaAsrProtocol
    ACCESS          read-only
    DESCRIPTION     "Create/Write access is not supported."

    VARIATION       cItpXuaAsrDpc
    ACCESS          read-only
    DESCRIPTION     "Create/Write access is not supported."

    VARIATION       cItpXuaAsrShut
    ACCESS          read-only
    DESCRIPTION     "Create/Write access is not supported."

    VARIATION       cItpXuaAsrRowStatus
    ACCESS          read-only
    DESCRIPTION     "Create/Write access is not supported."

-- **************************************************************
--              Entries in cItpXuaASRouteAsTable Table
-- **************************************************************
    VARIATION       cItpXuaAsrAsRowStatus
    ACCESS          read-only
    DESCRIPTION     "Create/Write access is not supported."
    ::= { ciscoItpXuaCapability 6 }

ciscoItpXuaCapabilityV12R0415SW AGENT-CAPABILITIES
    PRODUCT-RELEASE "Cisco IOS 12.4(15)SW"
    STATUS          current
    DESCRIPTION
        "Cisco IOS 12.4(15)SW CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroupRev3,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev3,
                        ciscoItpXuaAsrGroup,
                        ciscoItpXuaAsrAsGroup,
                        ciscoItpXuaSgmGroupSup1Group,
                        ciscoItpXuaSgmRemoteIpSup1Group,
                        ciscoItpXuaAspSup1Group,
                        ciscoItpXuaAspRemoteIpSup1Group,
                        ciscoItpXuaNotifGroup
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

    VARIATION       cItpXuaAsNetworkAppear
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

    VARIATION       cItpXuaAspAsWeight
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."

-- **************************************************************
--              Entries in cItpXuaASRouteTable Table
-- **************************************************************
    VARIATION       cItpXuaAsrProtocol
    ACCESS          read-only
    DESCRIPTION     "Create/Write access is not supported."

    VARIATION       cItpXuaAsrDpc
    ACCESS          read-only
    DESCRIPTION     "Create/Write access is not supported."

    VARIATION       cItpXuaAsrShut
    ACCESS          read-only
    DESCRIPTION     "Create/Write access is not supported."

    VARIATION       cItpXuaAsrRowStatus
    ACCESS          read-only
    DESCRIPTION     "Create/Write access is not supported."

-- **************************************************************
--              Entries in cItpXuaASRouteAsTable Table
-- **************************************************************
    VARIATION       cItpXuaAsrAsRowStatus
    ACCESS          read-only
    DESCRIPTION     "Create/Write access is not supported."
    ::= { ciscoItpXuaCapability 7 }

ciscoItpXuaCapabilityV12R0218IXE AGENT-CAPABILITIES
    PRODUCT-RELEASE "Cisco IOS 12.2(18)IXE"
    STATUS          current
    DESCRIPTION
        "Cisco IOS 12.2(18)IXE CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroupRev3,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev3,
                        ciscoItpXuaAsrGroup,
                        ciscoItpXuaAsrAsGroup,
                        ciscoItpXuaSgmGroupSup1Group,
                        ciscoItpXuaSgmRemoteIpSup1Group,
                        ciscoItpXuaAspSup1Group,
                        ciscoItpXuaAspRemoteIpSup1Group,
                        ciscoItpXuaNotifGroup
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

    VARIATION       cItpXuaAsNetworkAppear
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

    VARIATION       cItpXuaAspAsWeight
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."

-- **************************************************************
--              Entries in cItpXuaASRouteTable Table
-- **************************************************************
    VARIATION       cItpXuaAsrProtocol
    ACCESS          read-only
    DESCRIPTION     "Create/Write access is not supported."

    VARIATION       cItpXuaAsrDpc
    ACCESS          read-only
    DESCRIPTION     "Create/Write access is not supported."

    VARIATION       cItpXuaAsrShut
    ACCESS          read-only
    DESCRIPTION     "Create/Write access is not supported."

    VARIATION       cItpXuaAsrRowStatus
    ACCESS          read-only
    DESCRIPTION     "Create/Write access is not supported."

-- **************************************************************
--              Entries in cItpXuaASRouteAsTable Table
-- **************************************************************
    VARIATION       cItpXuaAsrAsRowStatus
    ACCESS          read-only
    DESCRIPTION     "Create/Write access is not supported."
    ::= { ciscoItpXuaCapability 8 }

ciscoItpXuaCapabilityV12R0233IRA AGENT-CAPABILITIES
    PRODUCT-RELEASE "Cisco IOS 12.2(33)IRA"
    STATUS          current
    DESCRIPTION
        "Cisco IOS 12.2(33)IRA CISCO-ITP-XUA-MIB.my
        User Agent MIB capabilities."

    SUPPORTS        CISCO-ITP-XUA-MIB
    INCLUDES        {
                        ciscoItpXuaScalarsGroup,
                        ciscoItpXuaInstLocalIpGroup,
                        ciscoItpXuaSgmGroupRev1,
                        ciscoItpXuaAspRemoteIpGroup,
                        ciscoItpXuaAspAsGroupRev3,
                        ciscoItpXuaNotifObjectsGroup,
                        ciscoItpXuaNotifGroupRev1,
                        ciscoItpXuaSgmRemoteIpGroup,
                        ciscoItpXuaInstGroupRev2,
                        ciscoItpXuaAspGroupRev2,
                        ciscoItpXuaAsGroupRev3,
                        ciscoItpXuaAsrGroup,
                        ciscoItpXuaAsrAsGroup,
                        ciscoItpXuaSgmGroupSup1Group,
                        ciscoItpXuaSgmRemoteIpSup1Group,
                        ciscoItpXuaAspSup1Group,
                        ciscoItpXuaAspRemoteIpSup1Group,
                        ciscoItpXuaNotifGroup,
                        ciscoItpXuaInstGroupSup1Group
                    }

-- **************************************************************
--              Entries in XUA Instance Table
-- **************************************************************
    VARIATION       cItpXuaInstProtocol
    ACCESS          read-only
    DESCRIPTION     "Create/Write access is not supported."

    VARIATION       cItpXuaInstShut
    ACCESS          read-only
    DESCRIPTION     "Create/Write access is not supported."

    VARIATION       cItpXuaInstRowStatus
    ACCESS          read-only
    DESCRIPTION     "Create/Write access is not supported."

-- **************************************************************
--              Entries in XUA Instance Local IP Table
-- **************************************************************
    VARIATION       cItpXuaInstLocalIpType
    ACCESS          read-only
    DESCRIPTION     "Create/Write access is not supported."

    VARIATION       cItpXuaInstLocalIpAddr
    ACCESS          read-only
    DESCRIPTION     "Create/Write access is not supported."

    VARIATION       cItpXuaInstLocalIpRowStatus
    ACCESS          read-only
    DESCRIPTION     "Create/Write access is not supported."

-- **************************************************************
--              Entries in Signaling Gateway Mate (SGM) Table
-- **************************************************************
    VARIATION       cItpXuaSgmLocalPort
    ACCESS          read-only
    DESCRIPTION     "Create/Write access is not supported."

    VARIATION       cItpXuaSgmRemotePort
    ACCESS          read-only
    DESCRIPTION     "Create/Write access is not supported."

    VARIATION       cItpXuaSgmShut
    ACCESS          read-only
    DESCRIPTION     "Create/Write access is not supported."

    VARIATION       cItpXuaSgmQosClass
    ACCESS          read-only
    DESCRIPTION     "Create/Write access is not supported."

    VARIATION       cItpXuaSgmPassive
    ACCESS          read-only
    DESCRIPTION     "Create/Write access is not supported."

    VARIATION       cItpXuaSgmRowStatus
    ACCESS          read-only
    DESCRIPTION     "Create/Write access is not supported."

-- **************************************************************
--              Entries in Application Server Process (ASP) Table
-- **************************************************************
    VARIATION       cItpXuaAspLocalPort
    ACCESS          read-only
    DESCRIPTION     "Create/Write access is not supported."

    VARIATION       cItpXuaAspRemotePort
    ACCESS          read-only
    DESCRIPTION     "Create/Write access is not supported."

    VARIATION       cItpXuaAspProtocol
    ACCESS          read-only
    DESCRIPTION     "Create/Write access is not supported."

    VARIATION       cItpXuaAspShut
    ACCESS          read-only
    DESCRIPTION     "Create/Write access is not supported."

    VARIATION       cItpXuaAspBlocked
    ACCESS          read-only
    DESCRIPTION     "Create/Write access is not supported."

    VARIATION       cItpXuaAspQosClass
    ACCESS          read-only
    DESCRIPTION     "Create/Write access is not supported."

    VARIATION       cItpXuaAspRowStatus
    ACCESS          read-only
    DESCRIPTION     "Create/Write access is not supported."

-- **************************************************************
--              Entries in ASP Remote IP Table
-- **************************************************************
    VARIATION       cItpXuaAspRemoteIpType
    ACCESS          read-only
    DESCRIPTION     "Create/Write access is not supported."

    VARIATION       cItpXuaAspRemoteIpAddr
    ACCESS          read-only
    DESCRIPTION     "Create/Write access is not supported."

    VARIATION       cItpXuaAspRemoteIpRowStatus
    ACCESS          read-only
    DESCRIPTION     "Create/Write access is not supported."

-- **************************************************************
--              Entries in Application Server (AS) Table
-- **************************************************************
    VARIATION       cItpXuaAsProtocol
    ACCESS          read-only
    DESCRIPTION     "Create/Write access is not supported."

    VARIATION       cItpXuaAsShut
    ACCESS          read-only
    DESCRIPTION     "Create/Write access is not supported."

    VARIATION       cItpXuaAsQosClass
    ACCESS          read-only
    DESCRIPTION     "Create/Write access is not supported."

    VARIATION       cItpXuaAsTrafMode
    ACCESS          read-only
    DESCRIPTION     "Create/Write access is not supported."

    VARIATION       cItpXuaAsRkParameters
    ACCESS          read-only
    DESCRIPTION     "Create/Write access is not supported."

    VARIATION       cItpXuaAsRkDpc
    ACCESS          read-only
    DESCRIPTION     "Create/Write access is not supported."

    VARIATION       cItpXuaAsRkOpc
    ACCESS          read-only
    DESCRIPTION     "Create/Write access is not supported."

    VARIATION       cItpXuaAsRkOpcMask
    ACCESS          read-only
    DESCRIPTION     "Create/Write access is not supported."

    VARIATION       cItpXuaAsRkSi
    ACCESS          read-only
    DESCRIPTION     "Create/Write access is not supported."

    VARIATION       cItpXuaAsRkSsn
    ACCESS          read-only
    DESCRIPTION     "Create/Write access is not supported."

    VARIATION       cItpXuaAsRkGtt
    ACCESS          read-only
    DESCRIPTION     "Create/Write access is not supported."

    VARIATION       cItpXuaAsRkCicMin
    ACCESS          read-only
    DESCRIPTION     "Create/Write access is not supported."

    VARIATION       cItpXuaAsRkCicMax
    ACCESS          read-only
    DESCRIPTION     "Create/Write access is not supported."

    VARIATION       cItpXuaAsRowStatus
    ACCESS          read-only
    DESCRIPTION     "Create/Write access is not supported."

    VARIATION       cItpXuaAsNetworkAppear
    ACCESS          read-only
    DESCRIPTION     "Create/Write access is not supported."

-- **************************************************************
--              Entries in ASP-AS Table
-- **************************************************************
    VARIATION       cItpXuaAspAsRowStatus
    ACCESS          read-only
    DESCRIPTION     "Create/Write access is not supported."

    VARIATION       cItpXuaAspAsWeight
    ACCESS          read-only
    DESCRIPTION     "Create/Write access is not supported."

-- **************************************************************
--              Entries in cItpXuaSgmRemoteIpTable Table
-- **************************************************************
    VARIATION       cItpXuaSgmRemoteIpType
    ACCESS          read-only
    DESCRIPTION     "Create/Write access is not supported."

    VARIATION       cItpXuaSgmRemoteIpAddr
    ACCESS          read-only
    DESCRIPTION     "Create/Write access is not supported."

    VARIATION       cItpXuaSgmRemoteIpRowStatus
    ACCESS          read-only
    DESCRIPTION     "Create/Write access is not supported."

-- **************************************************************
--              Entries in cItpXuaASRouteTable Table
-- **************************************************************
    VARIATION       cItpXuaAsrProtocol
    ACCESS          read-only
    DESCRIPTION     "Create/Write access is not supported."

    VARIATION       cItpXuaAsrDpc
    ACCESS          read-only
    DESCRIPTION     "Create/Write access is not supported."

    VARIATION       cItpXuaAsrShut
    ACCESS          read-only
    DESCRIPTION     "Create/Write access is not supported."

    VARIATION       cItpXuaAsrRowStatus
    ACCESS          read-only
    DESCRIPTION     "Create/Write access is not supported."

-- **************************************************************
--              Entries in cItpXuaASRouteAsTable Table
-- **************************************************************
    VARIATION       cItpXuaAsrAsRowStatus
    ACCESS          read-only
    DESCRIPTION     "Create/Write access is not supported."
    ::= { ciscoItpXuaCapability 9 }

END
