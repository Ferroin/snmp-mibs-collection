CISCO-VISM-SESSION-CAPABILITY DEFINITIONS ::= BEGIN
IMPORTS
        MODULE-IDENTITY,
        Integer32
                FROM SNMPv2-SMI
        AGENT-CAPABILITIES
                FROM SNMPv2-CONF
        ciscoAgentCapability
                FROM CISCO-SMI;

ciscoVismSessionCapability MODULE-IDENTITY
    LAST-UPDATED "200509190000Z"
    ORGANIZATION "Cisco Systems, Inc."
    CONTACT-INFO
        "        Cisco Systems
                 Customer Service
        Postal: 170 W Tasman Drive
                San Jose, CA 95134
                USA
           Tel: +1 800 553-NETS
        E-mail: cs-voice-gateway@cisco.com"
    DESCRIPTION
        "This MIB defines the agent capabilities for 
         CISCO-VISM-SESSION-MIB." 

    REVISION "200509190000Z"
    DESCRIPTION
        "Added capabilities for VISM Release 3.3.25."

    REVISION "200409030000Z"
    DESCRIPTION
        "Initial version of this MIB module."
    ::= { ciscoAgentCapability 415 }

ciscoVismSessionCapV5R015 AGENT-CAPABILITIES
    PRODUCT-RELEASE "MGX8850 Release 5.0.15"
    STATUS          current
    DESCRIPTION     "Agent capabilities for Voice Switch 
                     Service Module (VXSM) in MGX8850
                     release 5.0.15." 

    SUPPORTS        CISCO-VISM-SESSION-MIB
        INCLUDES    {          
                        ciscoVismSessionSetGrp,
                        ciscoVismSessionGrp,
                        ciscoVismRudpSessionGrp,
                        ciscoVismRudpSessionStatGrp
                    }

        VARIATION       vismSessionSetNum
            SYNTAX      Integer32 (1..1)
            DESCRIPTION "Limited data range is supported."

        VARIATION       vismSessionGrpNum
            SYNTAX      Integer32 (1..2)
            DESCRIPTION "Limited data range is supported."

        VARIATION       vismRudpSessionNum
            SYNTAX      Integer32 (1..8)
            DESCRIPTION "Limited data range is supported."

        VARIATION       vismRudpSessionType
            ACCESS      not-implemented
            DESCRIPTION "Not supported."               

        VARIATION       vismRudpSessionRmtGwIp
            ACCESS      not-implemented
            DESCRIPTION "Not supported."  

        VARIATION       vismRudpSessionStatNum
            SYNTAX      Integer32 (1..8)
            DESCRIPTION "Limited data range is supported."
    ::= { ciscoVismSessionCapability 1 }

ciscoVismSessionCapV3325 AGENT-CAPABILITIES
    PRODUCT-RELEASE      "Cisco VISM Release 3.3.25"
    STATUS               current
    DESCRIPTION          "CISCO-VISM-SESSION-MIB capabilities."

    SUPPORTS             CISCO-VISM-SESSION-MIB
        INCLUDES         { ciscoVismRudpSessionGrp }

        VARIATION        vismRudpSessionType
            ACCESS       read-create
            DESCRIPTION  "The value of this object can not be 
                          modified while the value of 
                          vismRudpSessionCnfRowStatus object 
                          is active(1)."
    ::= { ciscoVismSessionCapability 2 }

END
