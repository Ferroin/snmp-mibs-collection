CISCO-DLSW-MIB DEFINITIONS   ::= BEGIN

IMPORTS
        DisplayString, RowStatus,
        InstancePointer, TruthValue,
        TEXTUAL-CONVENTION                FROM SNMPv2-TC
        Counter32, Gauge32, Integer32, TimeTicks,
        OBJECT-TYPE, MODULE-IDENTITY,
        NOTIFICATION-TYPE                 FROM SNMPv2-SMI
        ciscoExperiment                   FROM CISCO-SMI
        MODULE-COMPLIANCE, OBJECT-GROUP   FROM SNMPv2-CONF
        ifIndex                           FROM IF-MIB
        sdlcLSAddress                     FROM SNA-SDLC-MIB;

ciscoDlswMIB MODULE-IDENTITY
	LAST-UPDATED	"9512050000Z"
	ORGANIZATION	"Cisco Systems Inc."
	CONTACT-INFO
                  "Ravi Periasamy
                   Cisco Systems Inc.
                   Research Triangle Park"
	DESCRIPTION
        	"This MIB module contains objects to manage Data Link
	         Switches."
	REVISION        "9512050000Z"
	DESCRIPTION
		"Correct minor syntax errors."
::= { ciscoExperiment 9 }

ciscoDlswMIBObjects   OBJECT IDENTIFIER ::= { ciscoDlswMIB 1 }
ciscoDlswDomains      OBJECT IDENTIFIER ::= { ciscoDlswMIB 2 }

-- *******************************************************************
-- Textual convention definitions
-- *******************************************************************

NBName ::= TEXTUAL-CONVENTION
    STATUS       current
    DESCRIPTION
       "Represents a single qualified NetBIOS name, which can include
        `don't care' and `wildcard' characters to represent a number
        of real NetBIOS names.  If an individual character position in
        the qualified name contains a `?', the corresponding character
        position in a real NetBIOS name is a `don't care'.  If the
        qualified name ends in `*', the remainder of a real NetBIOS
        name is a `don't care'. `*' is only considered a wildcard if it
        appears at the end of a name."
    SYNTAX  OCTET STRING (SIZE (0..16))

MacAddress ::= TEXTUAL-CONVENTION
    DISPLAY-HINT "1x:"
    STATUS       current
    DESCRIPTION
       "Represents an 802 MAC address represented in
        non-canonical format.  That is, the most significant
        bit will be transmitted first."
    SYNTAX       OCTET STRING (SIZE (0 | 6))  -- ravip
--@@ This is different from the definition in snmpv2 Textual-Convention.

TAddress ::= TEXTUAL-CONVENTION
    STATUS  current
    DESCRIPTION
       "Denotes a transport service address.
        For ciscoDlswTCPDomain, a TAddress is 4 octets long,
        containing the IP-address in network-byte order."
    SYNTAX  OCTET STRING (SIZE (4))

DlswTimeStamp ::= TEXTUAL-CONVENTION
    STATUS  current
    DESCRIPTION
       "The value of dlwsUpTime when the event of interest occurred."
    SYNTAX  TimeTicks

EndStationLocation ::= TEXTUAL-CONVENTION
    STATUS  current
    DESCRIPTION
       "Representing the location of an end station related
        to the managed DLSw node."
    SYNTAX  INTEGER  {
                other          (1),
                internal       (2),  -- local virtual MAC address
                remote         (3),  -- via DLSw partner
                local          (4)   -- locally attached
            }

DlcType ::= TEXTUAL-CONVENTION
    STATUS  current
    DESCRIPTION
       "Representing the type of DLC of an end station, if
        applicable."
    SYNTAX  INTEGER  {
                other          (1),  -- not assigned yet
                na             (2),  -- not applicable
                llc            (3),  -- 802.2 Logical Link Control
                sdlc           (4),  -- SDLC
                qllc           (5)   -- QLLC
            }

LFSize  ::= TEXTUAL-CONVENTION
    STATUS  current
    DESCRIPTION
       "The largest size of the INFO field (including DLC header,
        not including any MAC-level or framing octets).
        64 valid values as defined by the IEEE 802.1D
        Addendum are acceptable."
    SYNTAX  INTEGER  {
               lfs516(516), lfs635(635), lfs754(754), lfs873(873),
               lfs993(993), lfs1112(1112), lfs1231(1231),
               lfs1350(1350), lfs1470(1470), lfs1542(1542),
               lfs1615(1615), lfs1688(1688), lfs1761(1761),
               lfs1833(1833), lfs1906(1906), lfs1979(1979),
               lfs2052(2052), lfs2345(2345), lfs2638(2638),
               lfs2932(2932), lfs3225(3225), lfs3518(3518),
               lfs3812(3812), lfs4105(4105), lfs4399(4399),
               lfs4865(4865), lfs5331(5331), lfs5798(5798),
               lfs6264(6264), lfs6730(6730), lfs7197(7197),
               lfs7663(7663), lfs8130(8130), lfs8539(8539),
               lfs8949(8949), lfs9358(9358), lfs9768(9768),
               lfs10178(10178), lfs10587(10587), lfs10997(10997),
               lfs11407(11407), lfs12199(12199), lfs12992(12992),
               lfs13785(13785), lfs14578(14578), lfs15370(15370),
               lfs16163(16163), lfs16956(16956), lfs17749(17749),
               lfs20730(20730), lfs23711(23711), lfs26693(26693),
               lfs29674(29674), lfs32655(32655), lfs38618(38618),
               lfs41600(41600), lfs44591(44591), lfs47583(47583),
               lfs50575(50575), lfs53567(53567), lfs56559(56559),
               lfs59551(59551), lfs65535(65535)
            }

-- *******************************************************************
-- DLSw Transport Domain definitions
-- *******************************************************************

-- DLSw over TCP
ciscoDlswTCPDomain  OBJECT IDENTIFIER ::= { ciscoDlswDomains 1 }
-- for an IP address of length 4:
--
-- octets   contents        encoding
--  1-4     IP-address      network-byte order
--
--DlswTCPAddress ::= TEXTUAL-CONVENTION
--    DISPLAY-HINT "1d.1d.1d.1d"
--    STATUS       current
--    DESCRIPTION
--            "Represents the IP address of a DLSw which uses
--             TCP as a transport protocol."
--    SYNTAX       OCTET STRING (SIZE (4))

-- *******************************************************************
-- DLSw MIB Definition
-- *******************************************************************

-- The DLSw MIB module contains an object part and a conformance part.
-- Object part is organized in the following groups:
-- (1) ciscoDlswNode       information about this DLSw
-- (2) ciscoDlswTConn      about adjacent DLSw partners
-- (3) ciscoDlswInterface  about which interfaces DLSw is active on
-- (4) ciscoDlswDirectory  about any directory of local/remote resources
-- (5) ciscoDlswCircuit    about established circuits.
-- (6) ciscoDlswSdlc       about SDLC data link switched devices

ciscoDlswNode        OBJECT IDENTIFIER ::= { ciscoDlswMIBObjects 1 }
ciscoDlswTConn       OBJECT IDENTIFIER ::= { ciscoDlswMIBObjects 2 }
ciscoDlswInterface   OBJECT IDENTIFIER ::= { ciscoDlswMIBObjects 3 }
ciscoDlswDirectory   OBJECT IDENTIFIER ::= { ciscoDlswMIBObjects 4 }
ciscoDlswCircuit     OBJECT IDENTIFIER ::= { ciscoDlswMIBObjects 5 }
ciscoDlswSdlc        OBJECT IDENTIFIER ::= { ciscoDlswMIBObjects 6 }  -- SDLC

-- *******************************************************************
-- THE NODE GROUP
-- *******************************************************************

-- *******************************************************************
-- DLSw Node Identity
-- *******************************************************************
ciscoDlswVersion  OBJECT-TYPE
    SYNTAX     OCTET STRING (SIZE (2))
    MAX-ACCESS read-only
    STATUS     current
    DESCRIPTION
       "This value identifies the particular version of the DLSw
        standard supported by this DLSw.  The first octet is a hexadecimal
        value representing the DLSw standard Version number of
        this DLSw, and the second is a hexadecimal value representing the
        DLSw standard Release number. This information
        is reported in DLSw Capabilities Exchange."
    REFERENCE
       "DLSW: Switch-to-Switch Protocol RFC 1795"
    ::= { ciscoDlswNode 1 }

ciscoDlswVendorID  OBJECT-TYPE
    SYNTAX     OCTET STRING (SIZE (3))
    MAX-ACCESS read-only
    STATUS     current
    DESCRIPTION
       "The value identifies the manufacturer's IEEE-assigned
        organizationally Unique Identifier (OUI) of this DLSw.
        This information is reported in DLSw Capabilities
        Exchange."
    REFERENCE
       "DLSW: Switch-to-Switch Protocol RFC 1795"
    ::= { ciscoDlswNode 2 }

ciscoDlswVersionString  OBJECT-TYPE
    SYNTAX     DisplayString (SIZE (0..255))
    MAX-ACCESS read-only
    STATUS     current
    DESCRIPTION
       "This string gives product-specific information about
        this DLSw (e.g., product name, code release and fix level).
        This flows in Capabilities Exchange messages."
    REFERENCE
       "DLSW: Switch-to-Switch Protocol RFC 1795"
    ::= { ciscoDlswNode 3 }

-- *******************************************************************
-- DLSw Code Capability
-- *******************************************************************
ciscoDlswStdPacingSupport  OBJECT-TYPE
    SYNTAX     INTEGER  {
       none              (1),  -- does not support DLSw
                               -- Standard pacing scheme
       adaptiveRcvWindow (2),  -- the receive window size
                               -- varies
       fixedRcvWindow    (3)   -- the receive window size
                               -- remains constant
    }
    MAX-ACCESS read-only
    STATUS     current
    DESCRIPTION
       "Circuit pacing, as defined in the DLSw Standard, allows each
        of the two DLSw nodes on a circuit to control the amount
        of data the other is permitted to send to them.  This object
        reflects the level of support an implementation has for this
        protocol.  (1) means the node has no support for the standard
        circuit pacing flows;  it may use RFC 1434+ methods only, or
        a proprietary flow control scheme.  (2) means the node supports
        the standard scheme and can vary the window sizes it grants as
        a data receiver.  (3) means the node supports the standard
        scheme but never varies its receive window size."
    ::= { ciscoDlswNode 4 }

-- *******************************************************************
-- DLSw Node Operational Objects
-- *******************************************************************
ciscoDlswStatus  OBJECT-TYPE
    SYNTAX     INTEGER  {
        active        (1),
        inactive      (2)
    }
    MAX-ACCESS read-only
    STATUS     current
    DESCRIPTION
       "The status of the DLSw part of the system.  Changing the
        value from active to inactive causes DLSw to take
        the following actions - (1) it disconnects all circuits
        through all DLSw partners, (2) it disconnects all
        transport connections to all DLSw partners, (3) it
        disconnects all local DLC connections, and (4) it stops
        processing all DLC connection set-up traffic.
        Since these are destructive actions, the user should
        query the circuit and transport connection tables in
        advance to understand the effect this action will have.
        Changing the value from inactive to active causes DLSw
        to come up in its initial state, i.e., transport
        connections established and ready to bring up circuits."
    ::= { ciscoDlswNode 5 }

ciscoDlswUpTime  OBJECT-TYPE
    SYNTAX     TimeTicks
    MAX-ACCESS read-only
    STATUS     current
    DESCRIPTION
       "The time (in hundredths of a second) since the DLSw
        portion of the system was last re-initialized.
        That is, if dciscoDlswtate is in the active state,
        the time the ciscoDlswState entered the active state.
        It will remain zero if ciscoDlswState is in the
        inactive state."
    ::= { ciscoDlswNode 6 }

ciscoDlswVirtualSegmentLFSize  OBJECT-TYPE
    SYNTAX     LFSize
    MAX-ACCESS read-only
    STATUS     current
    DESCRIPTION
       "The largest frame size (including DLC header and info field
        but not any MAC-level or framing octets) this DLSw can forward
        on any path through itself.  This object can represent any box-
        level frame size forwarding restriction (e.g., from the use
        of fixed-size buffers).  Some DLSw implementations will have
        no such restriction.

        This value will affect the LF size of circuits during circuit
        creation.  The LF size of an existing circuit can be found in
        can be found in the RIF (Routing Information Field)."
    DEFVAL  { lfs17749 }
    ::= { ciscoDlswNode 7 }
--@@ Is there any value to this object being writable?

-- ...................................................................
-- NETBIOS Resources
-- ...................................................................

ciscoDlswResourceNBExclusivity  OBJECT-TYPE
    SYNTAX     TruthValue
    MAX-ACCESS read-only
    STATUS     current
    DESCRIPTION
       "The value of true indicates that the NetBIOS Names
        configured in ciscoDlswDirNBTable are the only ones accessible
        via this DLSw.

        If a node supports sending run-time capabilities exchange
        messages, changes to this object should cause that action.
        It is up to the implementation exactly when to start the
        run-time capabilities exchange."
    ::= { ciscoDlswNode 8 }
--@@ Revised description assumes that the old wording about "implementation
--@@ choice" referred to the choice to implement run-time capex, not the
--@@ choice of whether to send it or not if this object changes.

-- ...................................................................
-- MAC Address List
-- ...................................................................

ciscoDlswResourceMacExclusivity  OBJECT-TYPE
    SYNTAX     TruthValue
    MAX-ACCESS read-only
    STATUS     current
    DESCRIPTION
       "The value of true indicates that the MAC addresses
        configured in the ciscoDlswDirMacTable are the only ones
        accessible via this DLSw.

        If a node supports sending run-time capabilities exchange
        messages, changes to this object should cause that action.
        It is up to the implementation exactly when to start the
        run-time capabilities exchange."
    ::= { ciscoDlswNode 9 }

-- *******************************************************************
-- TRANSPORT CONNECTION (aka: PARTNER DLSW)
-- *******************************************************************

-- *******************************************************************
-- Transport Connection Statistics Objects
-- *******************************************************************
ciscoDlswTConnStat    OBJECT IDENTIFIER ::= { ciscoDlswTConn 1 }

ciscoDlswTConnStatActiveConnections  OBJECT-TYPE
    SYNTAX     Gauge32
    MAX-ACCESS read-only
    STATUS     current
    DESCRIPTION
       "The number of transport connections that are not in
        `disconnected' state."
    ::= { ciscoDlswTConnStat 1 }

ciscoDlswTConnStatCloseIdles  OBJECT-TYPE
    SYNTAX     Counter32
    MAX-ACCESS read-only
    STATUS     current
    DESCRIPTION
       "The number of times transport connections in this node
        exited the connected state with zero active circuits on
        the transport connection."
    --## VALID ciscoDlswUpTime
    ::= { ciscoDlswTConnStat 2 }

ciscoDlswTConnStatCloseBusys  OBJECT-TYPE
    SYNTAX     Counter32
    MAX-ACCESS read-only
    STATUS     current
    DESCRIPTION
       "The number of times transport connections in this node
        exited the connected state with some non-zero number
        of active circuits on the transport connection.  Normally
        this means the transport connection failed unexpectedly."
    --## VALID ciscoDlswUpTime
    ::= { ciscoDlswTConnStat 3 }

-- *******************************************************************
-- Transport Connection Configuration Table
-- *******************************************************************
ciscoDlswTConnConfigTable  OBJECT-TYPE
    SYNTAX     SEQUENCE OF DlswTConnConfigEntry
    MAX-ACCESS not-accessible
    STATUS     current
    DESCRIPTION
       "This table defines the transport connections
        that will be initiated or accepted by this
        DLSw.  Structure of masks allows wildcard
        definition for a collection of transport
        connections by a conceptual row.  For a
        specific transport connection, there may
        be multiple of conceptual rows match the
        transport address.  The `best' match will
        the one to determine the characteristics
        of the transport connection."
    ::= { ciscoDlswTConn 2 }

ciscoDlswTConnConfigEntry  OBJECT-TYPE
    SYNTAX     DlswTConnConfigEntry
    MAX-ACCESS not-accessible
    STATUS     current
    DESCRIPTION
       "Each conceptual row defines a collection of
        transport connections."
    INDEX   { ciscoDlswTConnConfigIndex }
    ::= { ciscoDlswTConnConfigTable 1 }

DlswTConnConfigEntry ::= SEQUENCE {
    ciscoDlswTConnConfigIndex              INTEGER,
    ciscoDlswTConnConfigTDomain            OBJECT IDENTIFIER,
    ciscoDlswTConnConfigLocalTAddr         TAddress,
    ciscoDlswTConnConfigRemoteTAddr        TAddress,
    ciscoDlswTConnConfigLastModifyTime     DlswTimeStamp,
    ciscoDlswTConnConfigEntryType          INTEGER,
    ciscoDlswTConnConfigGroupDefinition    InstancePointer,
    ciscoDlswTConnConfigSetupType          INTEGER,
    ciscoDlswTConnConfigSapList            OCTET STRING,
    ciscoDlswTConnConfigAdvertiseMacNB     TruthValue,
    ciscoDlswTConnConfigInitCirRecvWndw    INTEGER,
    ciscoDlswTConnConfigOpens              Counter32,
    ciscoDlswTConnConfigRowStatus          RowStatus
    }

ciscoDlswTConnConfigIndex  OBJECT-TYPE
    SYNTAX     INTEGER (1..65000) --ravip
    MAX-ACCESS not-accessible
    STATUS     current
    DESCRIPTION
       "The index to the conceptual row of the table.
        Non-positive numbers are not allowed.  There
        are objects defined that point to conceptual
        rows of this table with this index value.
        Zero is used to denote that no corresponding
        row exists.

        Index values are assigned by the managed station,
        and should not be reused but should continue to
        increase in value until they wrap."
    ::= { ciscoDlswTConnConfigEntry 1 }

ciscoDlswTConnConfigTDomain  OBJECT-TYPE
    SYNTAX     OBJECT IDENTIFIER
    MAX-ACCESS read-only
    STATUS     current
    DESCRIPTION
       "The object identifier which indicates the transport
        domain of this conceptual row."
    ::= { ciscoDlswTConnConfigEntry 2 }

ciscoDlswTConnConfigLocalTAddr  OBJECT-TYPE
    SYNTAX     TAddress
    MAX-ACCESS read-only
    STATUS     current
    DESCRIPTION
       "The local transport address for this conceptual row
        of the transport connection definition."
    ::= { ciscoDlswTConnConfigEntry 3 }

ciscoDlswTConnConfigRemoteTAddr  OBJECT-TYPE
    SYNTAX     TAddress
    MAX-ACCESS read-only
    STATUS     current
    DESCRIPTION
       "The remote transport address.  Together with the
        ciscoDlswTConnConfigRemoteTAddrMask, the object instance
        of this conceptual row identifies a collection of
        the transport connections that will be either
        initiated by this DLSw or initiated by partner
        DLSw and accepted by this DLSw."
    ::= { ciscoDlswTConnConfigEntry 4 }

ciscoDlswTConnConfigLastModifyTime  OBJECT-TYPE
    SYNTAX     DlswTimeStamp
    MAX-ACCESS read-only
    STATUS     current
    DESCRIPTION
       "The value of ciscoDlswUpTime when the value of any object in
        this conceptual row was last changed.  This value may
        be compared to ciscoDlswTConnOperConnectTime to determine
        whether values in this row are completely valid for a
        transport connection created using this row definition."
    ::= { ciscoDlswTConnConfigEntry 5 }

ciscoDlswTConnConfigEntryType  OBJECT-TYPE
    SYNTAX     INTEGER  {
        individual     (1),
        global         (2),
        group          (3)
    }
    MAX-ACCESS read-only
    STATUS     current
    DESCRIPTION
       "The object instance signifies the type of entry in the
        associated conceptual row.  The value of `individual'
        means that the entry applies to a specific partner DLSw
        node as identified by ciscoDlswTConnConfigRemoteTAddr and
        ciscoDlswTConnConfigTDomain.  The value of `global'
        means that the entry applies to all partner DLSw nodes
        of the TDomain.  The value of 'group' means that the entry
        applies to a specific set of DLSw nodes in the TDomain.
        Any group definitions are enterprise-specific and are pointed
        to by ciscoDlswTConnConfigGroupDefinition.  In the cases of
        `global' and `group', the value in ciscoDlswTConnConfigRemoteTAddr
        may not have any significance."
    ::= { ciscoDlswTConnConfigEntry 6 }

ciscoDlswTConnConfigGroupDefinition OBJECT-TYPE
    SYNTAX     InstancePointer
    MAX-ACCESS read-only
    STATUS     current
    DESCRIPTION
       "For conceptual rows of `individual' and `global' as
        specified in ciscoDlswTConnConfigEntryType, the instance
        of this object is  `0.0'.  For conceptual rows of
        `group', the instance points to the specific
        group definition."
    ::= { ciscoDlswTConnConfigEntry 7 }

ciscoDlswTConnConfigSetupType  OBJECT-TYPE
    SYNTAX     INTEGER  {
        other              (1),
        activePersistent   (2),
        activeOnDemand     (3),
        passive            (4),
        excluded           (5)
    }
    MAX-ACCESS read-only
    STATUS     current
    DESCRIPTION
       "This value of the instance of a conceptual row
        identifies the behavior of the collection of
        transport connections that this conceptual row
        defines.  The value of activePersistent, activeOnDemand
        and passive means this DLSw will accept any transport
        connections, initiated by partner DLSw nodes, which
        are defined by this conceptual row.  The value of
        activePersistent means this DLSw will also initiate
        the transport connections of this conceptual row and
        retry periodically if necessary.  The value of
        activeOnDemand means this DLSw will initiate a
        transport connection of this conceptual row, if
        there is a directory cache hits.  The value of
        other is implementation specific.  The value of exclude
        means that the specified node is not allowed to be
        a partner to this DLSw node.  To take a certain
        conceptual row definition out of service, a value of
        notInService for ciscoDlswTConnConfigRowStatus should be
        used."
    DEFVAL  { activePersistent }
    ::= { ciscoDlswTConnConfigEntry 8 }

ciscoDlswTConnConfigSapList  OBJECT-TYPE
    SYNTAX     OCTET STRING  (SIZE(16))
    MAX-ACCESS read-only
    STATUS     current
    DESCRIPTION
       "The SAP list indicates which SAPs are advertised to
        the transport connection defined by the local peer whose
        transport address is given by ciscoDlswTConnConfigLocalTAddr.

        The SAP list is configured on the local peer, and the SAP list
        is sent to other peers via capabilities exchange.

        The SAP list represents the SAPs specified via the configuration
        command:
          dlsw icanreach saps X
           or
          dlsw icannotreach saps X
        Where X is in the range 0-FE.

        Only SAPs with even numbers are represented,
        in the form of the most significant bit of the first
        octet representing the SAP 0, the next most significant
        bit representing the SAP 2, to the least significant
        bit of the last octet representing the SAP 254.  Data
        link switching is allowed for those SAPs which have
        one in its corresponding bit, not allowed otherwise.
        The whole SAP list has to be changed together.  Changing
        the SAP list affects only new circuit establishments
        and has no effect on established circuits.

        This list can be used to restrict specific partners
        from knowing about all the SAPs used by DLSw on all its
        interfaces (these are represented in ciscoDlswIfSapList for
        each interface).  For instance, one may want to run NetBIOS
        with some partners but not others.

        If a node supports sending run-time capabilities exchange
        messages, changes to this object should cause that action.
        It is up to the implementation exactly when to start the
        run-time capabilities exchange.

        The DEFVAL below indicates support for all SAPs."
    DEFVAL  { 'ffffffffffffffffffffffffffffffff'h }
    ::= { ciscoDlswTConnConfigEntry 9 }

ciscoDlswTConnConfigAdvertiseMacNB  OBJECT-TYPE
    SYNTAX     TruthValue
    MAX-ACCESS read-only
    STATUS     current
    DESCRIPTION
       "The value of true indicates that defined local MAC
       addresses and NetBIOS names will be advertised to a
        partner node via initial and (if supported) run-time
        capabilities exchange messages."
    DEFVAL  { true }
    ::= { ciscoDlswTConnConfigEntry 10 }
--@@ Not clear that this object is useful without further definition -
--@@ if false should the node send the exclusivity CV and not any of
--@@ the list entries, or not even the exclusivity CV?

ciscoDlswTConnConfigInitCirRecvWndw  OBJECT-TYPE
    SYNTAX     INTEGER (0..65535)
    UNITS      "SSP messages"
    MAX-ACCESS read-only
    STATUS     current
    DESCRIPTION
       "The initial circuit receive pacing window size, in the unit
        of SSP messages, to be used for future transport connections
        activated using this table row.  The managed node sends this
        value as its initial receive pacing window in its initial
        capabilities exchange message.  Changing this value does not
        affect the initial circuit receive pacing window size of
        currently active transport connections.  If the standard window
        pacing scheme is not supported, the value is zero.

        A larger receive window value may be appropriate for partners
        that are reachable only via physical paths that have longer
        network delays."
    DEFVAL  { 1 }
    ::= { ciscoDlswTConnConfigEntry 11 }

ciscoDlswTConnConfigOpens  OBJECT-TYPE
    SYNTAX     Counter32
    MAX-ACCESS read-only
    STATUS     current
    DESCRIPTION
       "Number of times transport connections entered
        connected state according to the definition of
        this conceptual row."
    --## VALID ciscoDlswUpTime
    ::= { ciscoDlswTConnConfigEntry 12 }

ciscoDlswTConnConfigRowStatus  OBJECT-TYPE
    SYNTAX     RowStatus
    MAX-ACCESS read-only
    STATUS     current
    DESCRIPTION
       "This object is used by a Management Station to create
        or delete the row entry in the ciscoDlswTConnConfigTable
        following the RowStatus textual convention.  The value
        of notInService will be used to take a conceptual
        row definition out of use."
    ::= { ciscoDlswTConnConfigEntry 13 }

-- *******************************************************************
-- Transport Connection Operation Table
-- *******************************************************************
-- (1) At most one transport connection can be connected between
--     this DLSw and one of its DLSw partners at a given time.
-- (2) Multiple transport types are supported.
-- (3) Since the entries may be reused, ciscoDlswTConnOperEntryTime
--     needs to be consulted for the possibility of counter reset.
-- *******************************************************************

ciscoDlswTConnOperTable  OBJECT-TYPE
    SYNTAX     SEQUENCE OF DlswTConnOperEntry
    MAX-ACCESS not-accessible
    STATUS     current
    DESCRIPTION
       "A list of transport connections.   It is optional but
        desirable for an implementation to keep an entry for
        some period of time after the transport connection is
        disconnected.  This allows a network management station
        to capture additional useful information about the connection,
        in particular, statistical information and the cause of the
        disconnection."
    ::= { ciscoDlswTConn 3 }

ciscoDlswTConnOperEntry  OBJECT-TYPE
    SYNTAX     DlswTConnOperEntry
    MAX-ACCESS not-accessible
    STATUS     current
    DESCRIPTION
       ""
    INDEX   { ciscoDlswTConnOperTDomain, ciscoDlswTConnOperRemoteTAddr }
    ::= { ciscoDlswTConnOperTable 1 }

DlswTConnOperEntry ::= SEQUENCE {
    ciscoDlswTConnOperTDomain                  OBJECT IDENTIFIER,
    ciscoDlswTConnOperLocalTAddr               TAddress,
    ciscoDlswTConnOperRemoteTAddr              TAddress,
    ciscoDlswTConnOperEntryTime                DlswTimeStamp,
    ciscoDlswTConnOperConnectTime              DlswTimeStamp,
    ciscoDlswTConnOperState                    INTEGER,
    ciscoDlswTConnOperConfigIndex              INTEGER,
    ciscoDlswTConnOperFlowCntlMode             INTEGER,
    ciscoDlswTConnOperPartnerVersion           OCTET STRING,
    ciscoDlswTConnOperPartnerVendorID          OCTET STRING,
    ciscoDlswTConnOperPartnerVersionStr        DisplayString,
    ciscoDlswTConnOperPartnerInitPacingWndw    INTEGER,
    ciscoDlswTConnOperPartnerSapList           OCTET STRING,
    ciscoDlswTConnOperPartnerNBExcl            TruthValue,
    ciscoDlswTConnOperPartnerMacExcl           TruthValue,
    ciscoDlswTConnOperPartnerNBInfo            INTEGER,
    ciscoDlswTConnOperPartnerMacInfo           INTEGER,
    ciscoDlswTConnOperDiscTime                 DlswTimeStamp,
    ciscoDlswTConnOperDiscReason               INTEGER,
    ciscoDlswTConnOperDiscActiveCir            INTEGER,
    ciscoDlswTConnOperInDataPkts               Counter32,
    ciscoDlswTConnOperOutDataPkts              Counter32,
    ciscoDlswTConnOperInDataOctets             Counter32,
    ciscoDlswTConnOperOutDataOctets            Counter32,
    ciscoDlswTConnOperInCntlPkts               Counter32,
    ciscoDlswTConnOperOutCntlPkts              Counter32,
    ciscoDlswTConnOperCURexSents               Counter32,
    ciscoDlswTConnOperICRexRcvds               Counter32,
    ciscoDlswTConnOperCURexRcvds               Counter32,
    ciscoDlswTConnOperICRexSents               Counter32,
    ciscoDlswTConnOperNQexSents                Counter32,
    ciscoDlswTConnOperNRexRcvds                Counter32,
    ciscoDlswTConnOperNQexRcvds                Counter32,
    ciscoDlswTConnOperNRexSents                Counter32,
    ciscoDlswTConnOperCirCreates               Counter32,
    ciscoDlswTConnOperCircuits                 Gauge32
    }

ciscoDlswTConnOperTDomain  OBJECT-TYPE
    SYNTAX     OBJECT IDENTIFIER
    MAX-ACCESS not-accessible
    STATUS     current
    DESCRIPTION
       "The object identifier indicates the transport domain
        of this transport connection."
    ::= { ciscoDlswTConnOperEntry 1 }

ciscoDlswTConnOperLocalTAddr  OBJECT-TYPE
    SYNTAX     TAddress
    MAX-ACCESS read-only
    STATUS     current
    DESCRIPTION
       "The local transport address for this transport connection.
        This value could be different from ciscoDlswTConnConfigLocalAddr,
        if the value of the latter were changed after this transport
        connection was established."
    ::= { ciscoDlswTConnOperEntry 2 }

ciscoDlswTConnOperRemoteTAddr  OBJECT-TYPE
    SYNTAX     TAddress
    MAX-ACCESS not-accessible
    STATUS     current
    DESCRIPTION
       "The remote transport address of this transport connection."
    ::= { ciscoDlswTConnOperEntry 3 }

ciscoDlswTConnOperEntryTime  OBJECT-TYPE
    SYNTAX     DlswTimeStamp
    MAX-ACCESS read-only
    STATUS     current
    DESCRIPTION
       "The value of ciscoDlswUpTime when this transport connection
        conceptual row was created."
    ::= { ciscoDlswTConnOperEntry 4 }

-- ...................................................................
-- DLSw Transport Connection Operational Objects
-- ...................................................................

ciscoDlswTConnOperConnectTime  OBJECT-TYPE
    SYNTAX     DlswTimeStamp
    MAX-ACCESS read-only
    STATUS     current
    DESCRIPTION
       "The value of ciscoDlswUpTime when this transport connection
        last entered the 'connected' state.  A value of zero means
        this transport connection has never been established."
    ::= { ciscoDlswTConnOperEntry 5 }

ciscoDlswTConnOperState  OBJECT-TYPE
    SYNTAX     INTEGER  {
        connecting         (1),
        initCapExchange    (2),
        connected          (3),
        quiescing          (4),
        disconnecting      (5),
        disconnected       (6)
    }
    MAX-ACCESS read-only
    STATUS     current
    DESCRIPTION
       "The state of this transport connection.  The transport
        connection enters `connecting' state when DLSw makes
        a connection request to the transport layer.  Once initial
        Capabilities Exchange is sent, the transport connection enters
        enters `initCapExchange' state.  When partner capabilities have been
        determined and the transport connection is ready for sending
        CanUReach (CUR) messages, it moves to the `connected' state.
        When DLSw is in the process of bringing down the connection,
        it is in the `disconnecting' state.  When the transport layer
        indicates one of its connections is disconnected, the transport
        connection moves to the `disconnected' state.

        Whereas all of the values will be returned in response to a
        management protocol retrieval operation, only two values may
        be specified in a management protocol set operation: `quiescing'
        and `disconnecting'.  Changing the value to `quiescing' prevents
        new circuits from being established, and will cause a transport
        disconnect when the last circuit on the connection goes away.
        Changing the value to `disconnecting' will force off all circuits
        immediately and bring the connection to `disconnected' state."
    ::= { ciscoDlswTConnOperEntry 6 }

ciscoDlswTConnOperConfigIndex  OBJECT-TYPE
    SYNTAX     INTEGER (1..65000) --ravip
    MAX-ACCESS read-only
    STATUS     current
    DESCRIPTION
       "The value of ciscoDlswTConnConfigIndex of the ciscoDlswTConnConfigEntry
        that governs the configuration information used by this
        ciscoDlswTConnOperEntry.  A management station can therefore
        normally examine both configured and operational information
        for this transport connection.

        This value is zero if the corresponding ciscoDlswTConnConfigEntry
        was deleted after the creation of this ciscoDlswTConnOperEntry.
        If some fields in the former were changed but the conceptual
        row was not deleted, some configuration information may not
        be valid for this operational transport connection.  A network
        management application can compare ciscoDlswTConnOperConnectTime and
        ciscoDlswTConnConfigLastModifyTime to determine if this condition
        exists."
    ::= { ciscoDlswTConnOperEntry 7 }

-- ...................................................................
-- Transport Connection Characteristics
-- ...................................................................

ciscoDlswTConnOperFlowCntlMode  OBJECT-TYPE
    SYNTAX     INTEGER  {
       undetermined   (1),
       pacing         (2),   -- DLSw standard flow control
       other          (3)    -- non-DLSw standard flow control
    }
    MAX-ACCESS read-only
    STATUS     current
    DESCRIPTION
       "The flow control mechanism in use on this transport connection.
        This value is undetermined (1) before the mode of flow control
        can be established on a new transport connection (i.e., after
        CapEx is sent but before Capex or other SSP control messages
        have been received).  Pacing (2) indicates that the standard
        RFC 1795 pacing mechanism is in use.  Other (3) may be either
        the RFC 1434+ xBusy mechanism operating to a back-level DLSw,
        or a vendor-specific flow control method.  Whether it is xBusy
        or not can be inferred from ciscoDlswTConnOperPartnerVersion."
    ::= { ciscoDlswTConnOperEntry 8 }

-- ...................................................................

ciscoDlswTConnOperPartnerVersion  OBJECT-TYPE
    SYNTAX     OCTET STRING (SIZE (0 | 2))
    MAX-ACCESS read-only
    STATUS     current
    DESCRIPTION
       "This value identifies which version (first octet) and release
        (second octet) of the DLSw standard is supported by this
        partner DLSw. This information is obtained from a DLSw
        capabilities exchange message received from the partner DLSw.
        A string of zero length is returned before a Capabilities
        Exchange message is received, or if one is never received.
        A conceptual row with a ciscoDlswTConnOperState of `connected' but
        a zero length partner version indicates that the partner is
        a non-standard DLSw partner.

        If an implementation chooses to keep ciscoDlswTConnOperEntrys in
        the `disconnected' state, this value should remain unchanged."
    REFERENCE
       "DLSW: Switch-to-Switch Protocol RFC 1795"
    ::= { ciscoDlswTConnOperEntry 9 }

ciscoDlswTConnOperPartnerVendorID  OBJECT-TYPE
    SYNTAX     OCTET STRING (SIZE (0 | 3))
    MAX-ACCESS read-only
    STATUS     current
    DESCRIPTION
       "This value identifies the IEEE-assigned organizationally
        Unique Identifier (OUI) of the maker of this partner
        DLSw.  This information is obtained from a DLSw
        capabilities exchange message received from the partner DLSw.
        A string of zero length is returned before a Capabilities
        Exchange message is received, or if one is never received.

        If an implementation chooses to keep ciscoDlswTConnOperEntrys in
        the `disconnected' state, this value should remain unchanged."
    ::= { ciscoDlswTConnOperEntry 10 }

ciscoDlswTConnOperPartnerVersionStr  OBJECT-TYPE
    SYNTAX     DisplayString (SIZE (0..253))
    MAX-ACCESS read-only
    STATUS     current
    DESCRIPTION
       "This value identifies the particular product version (e.g.,
        product name, code level, fix level) of this partner DLSw.
        The format of the actual version string is vendor-specific.
        This information is obtained from a DLSw capabilities exchange
        message received from the partner DLSw.
        A string of zero length is returned before a Capabilities
        Exchange message is received, if one is never received, or
        if one is received but it does not contain a version string.

        If an implementation chooses to keep ciscoDlswTConnOperEntrys in
        the `disconnected' state, this value should remain unchanged."
    REFERENCE
       "DLSW: Switch-to-Switch Protocol RFC 1795"
    ::= { ciscoDlswTConnOperEntry 11 }

ciscoDlswTConnOperPartnerInitPacingWndw  OBJECT-TYPE
    SYNTAX     INTEGER (0..65535)
    MAX-ACCESS read-only
    STATUS     current
    DESCRIPTION
       "The value of the partner initial receive pacing window.  This
        is our initial send pacing window for all new circuits on this
        transport connection, as modified and granted by the first flow
        control indication the partner sends on each circuit.
        This information is obtained from a DLSw capabilities exchange
        message received from the partner DLSw.
        A value of zero is returned before a Capabilities
        Exchange message is received, or if one is never received.

        If an implementation chooses to keep ciscoDlswTConnOperEntrys in
        the `disconnected' state, this value should remain unchanged."
    REFERENCE
       "DLSW: Switch-to-Switch Protocol RFC 1795"
    ::= { ciscoDlswTConnOperEntry 12 }

-- ...................................................................

ciscoDlswTConnOperPartnerSapList  OBJECT-TYPE
    SYNTAX     OCTET STRING (SIZE (0 | 16))
    MAX-ACCESS read-only
    STATUS     current
    DESCRIPTION
       "The Supported SAP List received in the capabilities
        exchange message from the partner DLSw.  This list has
        the same format described for ciscoDlswTConnConfigSapList.
        A string of zero length is returned before a Capabilities
        Exchange message is received, or if one is never received.

        If an implementation chooses to keep ciscoDlswTConnOperEntrys in
        the `disconnected' state, this value should remain unchanged."
    ::= { ciscoDlswTConnOperEntry 13 }

ciscoDlswTConnOperPartnerNBExcl  OBJECT-TYPE
    SYNTAX     TruthValue
    MAX-ACCESS read-only
    STATUS     current
    DESCRIPTION
       "The value of true signifies that the NetBIOS names received
        from this partner in the NetBIOS name list in its capabilities
        exchange message are the only NetBIOS names reachable by
        that partner.  `False' indicates that other NetBIOS names may
        be reachable.  `False' should be returned before a Capabilities
        Exchange message is received, if one is never received, or if
        one is received without a NB Name Exclusivity CV.

        If an implementation chooses to keep ciscoDlswTConnOperEntrys in
        the `disconnected' state, this value should remain unchanged."
    ::= { ciscoDlswTConnOperEntry 14 }

ciscoDlswTConnOperPartnerMacExcl  OBJECT-TYPE
    SYNTAX     TruthValue
    MAX-ACCESS read-only
    STATUS     current
    DESCRIPTION
       "The value of true signifies that the MAC addresses received
        from this partner in the MAC address list in its capabilities
        exchange message are the only MAC addresses reachable by
        that partner.  `False' indicates that other MAC addresses may
        be reachable.  `False' should be returned before a Capabilities
        Exchange message is received, if one is never received, or if
        one is received without a MAC Address Exclusivity CV.

        If an implementation chooses to keep ciscoDlswTConnOperEntrys in
        the `disconnected' state, this value should remain unchanged."
    ::= { ciscoDlswTConnOperEntry 15 }

ciscoDlswTConnOperPartnerNBInfo  OBJECT-TYPE
    SYNTAX     INTEGER  {
       none           (1),  -- none is kept
       partial        (2),  -- partial list is kept
       complete       (3),  -- complete list is kept
       notApplicable  (4)
    }
    MAX-ACCESS read-only
    STATUS     current
    DESCRIPTION
       "It is up to this DSLw whether to keep either none, some,
        or all of the NetBIOS name list that was received in
        the capabilities exchange message sent by this partner DLSw.
        This object identifies how much information was kept by
        this DLSw.  These names are stored as userConfigured
        remote entries in ciscoDlswDirNBTable.
        A value of (4), notApplicable, should be returned before
        a Capabilities Exchange message is received, or if one is
        never received.

        If an implementation chooses to keep ciscoDlswTConnOperEntrys in
        the `disconnected' state, this value should remain unchanged."
    ::= { ciscoDlswTConnOperEntry 16 }

ciscoDlswTConnOperPartnerMacInfo  OBJECT-TYPE
    SYNTAX     INTEGER  {
       none           (1),  -- none is kept
       partial        (2),  -- partial list is kept
       complete       (3),  -- complete list is kept
       notApplicable  (4)
    }
    MAX-ACCESS read-only
    STATUS     current
    DESCRIPTION
       "It is up to this DLSw whether to keep either none, some,
        or all of the MAC address list that was received in the
        capabilities exchange message sent by this partner DLSw.
        This object identifies how much information was kept by
        this DLSw.  These names are stored as userConfigured
        remote entries in ciscoDlswDirMACTable.
        A value of (4), notApplicable, should be returned before
        a Capabilities Exchange message is received, or if one is
        never received.

        If an implementation chooses to keep ciscoDlswTConnOperEntrys in
        the `disconnected' state, this value should remain unchanged."
    ::= { ciscoDlswTConnOperEntry 17 }

-- ...................................................................
-- Information about the last disconnect of this transport connection.
--   These objects make sense only for implementations that keep
--   transport connection information around after disconnection.
-- ...................................................................
ciscoDlswTConnOperDiscTime  OBJECT-TYPE
    SYNTAX     DlswTimeStamp
    MAX-ACCESS read-only
    STATUS     current
    DESCRIPTION
       "The value of ciscoDlswUpTime when ciscoDlswTConnOperState last
        entered `disconnected' state."
    ::= { ciscoDlswTConnOperEntry 18 }

ciscoDlswTConnOperDiscReason  OBJECT-TYPE
    SYNTAX     INTEGER  {
        other              (1),
        capExFailed        (2),
        transportLayerDisc (3),
        operatorCommand    (4),
        lastCircuitDiscd   (5),
        protocolError      (6)
    }
    MAX-ACCESS read-only
    STATUS     current
    DESCRIPTION
       "This object signifies the reason that either prevented the
        transport connection from entering the connected state, or
        caused the transport connection to enter the disconnected state."
    ::= { ciscoDlswTConnOperEntry 19 }

ciscoDlswTConnOperDiscActiveCir  OBJECT-TYPE
    SYNTAX     INTEGER (0..65000) -- ravip
    MAX-ACCESS read-only
    STATUS     current
    DESCRIPTION
       "The number of circuits active (not in DISCONNECTED state)
        at the time the transport connection was last disconnected.
        This value is zero if the transport connection has never
        been connected."
    ::= { ciscoDlswTConnOperEntry 20 }

-- ...................................................................
-- Transport Connection Statistics
-- (1) Traffic counts
-- ...................................................................
ciscoDlswTConnOperInDataPkts  OBJECT-TYPE
    SYNTAX     Counter32
    UNITS      "SSP messages"
    MAX-ACCESS read-only
    STATUS     current
    DESCRIPTION
       "The number of Switch-to-Switch Protocol (SSP) messages of
        type DGRMFRAME, DATAFRAME, or INFOFRAME received on this
        transport connection."
    --## VALID ciscoDlswTConnOperEntryTime
    ::= { ciscoDlswTConnOperEntry 21 }

ciscoDlswTConnOperOutDataPkts  OBJECT-TYPE
    SYNTAX     Counter32
    UNITS      "SSP messages"
    MAX-ACCESS read-only
    STATUS     current
    DESCRIPTION
       "The number of Switch-to-Switch Protocol (SSP) messages of
        type DGRMFRAME, DATAFRAME, or INFOFRAME transmitted on this
        transport connection."
    --## VALID ciscoDlswTConnOperEntryTime
    ::= { ciscoDlswTConnOperEntry 22 }

ciscoDlswTConnOperInDataOctets  OBJECT-TYPE
    SYNTAX     Counter32
    UNITS      "octets"
    MAX-ACCESS read-only
    STATUS     current
    DESCRIPTION
       "The number octets in Switch-to-Switch Protocol (SSP) messages
        of type DGRMFRAME, DATAFRAME, or INFOFRAME received on this
        transport connection.  Each message is counted starting with
        the first octet following the SSP message header."
    --## VALID ciscoDlswTConnOperEntryTime
    ::= { ciscoDlswTConnOperEntry 23 }

ciscoDlswTConnOperOutDataOctets  OBJECT-TYPE
    SYNTAX     Counter32
    UNITS      "octets"
    MAX-ACCESS read-only
    STATUS     current
    DESCRIPTION
       "The number octets in Switch-to-Switch Protocol (SSP) messages
        of type DGRMFRAME, DATAFRAME, or INFOFRAME transmitted on this
        transport connection.  Each message is counted starting with
        the first octet following the SSP message header."
    --## VALID ciscoDlswTConnOperEntryTime
    ::= { ciscoDlswTConnOperEntry 24 }

ciscoDlswTConnOperInCntlPkts  OBJECT-TYPE
    SYNTAX     Counter32
    UNITS      "SSP messages"
    MAX-ACCESS read-only
    STATUS     current
    DESCRIPTION
       "The number of Switch-to-Switch Protocol (SSP) messages
        received on this transport connection which were not of
        type DGRMFRAME, DATAFRAME, or INFOFRAME."
    --## VALID ciscoDlswTConnOperEntryTime
    ::= { ciscoDlswTConnOperEntry 25 }

ciscoDlswTConnOperOutCntlPkts  OBJECT-TYPE
    SYNTAX     Counter32
    UNITS      "SSP messages"
    MAX-ACCESS read-only
    STATUS     current
    DESCRIPTION
       "The number of Switch-to-Switch Protocol (SSP) messages of
        transmitted on this transport connection which were not of
        type DGRMFRAME, DATAFRAME, or INFOFRAME."
    --## VALID ciscoDlswTConnOperEntryTime
    ::= { ciscoDlswTConnOperEntry 26 }

-- ...................................................................
-- (2) Directory activities (Explorer messages)
-- ...................................................................

ciscoDlswTConnOperCURexSents  OBJECT-TYPE
    SYNTAX     Counter32
    MAX-ACCESS read-only
    STATUS     current
    DESCRIPTION
       "The number of CanUReach_ex messages sent on this transport
        connection."
    --## VALID ciscoDlswTConnOperEntryTime
    ::= { ciscoDlswTConnOperEntry 27 }

ciscoDlswTConnOperICRexRcvds  OBJECT-TYPE
    SYNTAX     Counter32
    MAX-ACCESS read-only
    STATUS     current
    DESCRIPTION
       "The number of ICanReach_ex messages received on this transport
        connection."
    --## VALID ciscoDlswTConnOperEntryTime
    ::= { ciscoDlswTConnOperEntry 28 }

ciscoDlswTConnOperCURexRcvds  OBJECT-TYPE
    SYNTAX     Counter32
    MAX-ACCESS read-only
    STATUS     current
    DESCRIPTION
       "The number of CanUReach_ex messages received on this transport
        connection."
    --## VALID ciscoDlswTConnOperEntryTime
    ::= { ciscoDlswTConnOperEntry 29 }

ciscoDlswTConnOperICRexSents  OBJECT-TYPE
    SYNTAX     Counter32
    MAX-ACCESS read-only
    STATUS     current
    DESCRIPTION
       "The number of ICanReach_ex messages sent on this transport
        connection."
    --## VALID ciscoDlswTConnOperEntryTime
    ::= { ciscoDlswTConnOperEntry 30 }

-- ...................................................................

ciscoDlswTConnOperNQexSents  OBJECT-TYPE
    SYNTAX     Counter32
    MAX-ACCESS read-only
    STATUS     current
    DESCRIPTION
       "The number of NetBIOS_NQ_ex (NetBIOS Name Query-explorer) messages
        sent on this transport connection."
    --## VALID ciscoDlswTConnOperEntryTime
    ::= { ciscoDlswTConnOperEntry 31 }

ciscoDlswTConnOperNRexRcvds  OBJECT-TYPE
    SYNTAX     Counter32
    MAX-ACCESS read-only
    STATUS     current
    DESCRIPTION
       "The number of NETBIOS_NR_ex (NetBIOS Name Recognized-explorer)
        messages received on this transport connection."
    --## VALID ciscoDlswTConnOperEntryTime
    ::= { ciscoDlswTConnOperEntry 32 }

ciscoDlswTConnOperNQexRcvds  OBJECT-TYPE
    SYNTAX     Counter32
    MAX-ACCESS read-only
    STATUS     current
    DESCRIPTION
       "The number of NETBIOS_NQ_ex messages received on this
        transport connection."
    --## VALID ciscoDlswTConnOperEntryTime
    ::= { ciscoDlswTConnOperEntry 33 }

ciscoDlswTConnOperNRexSents  OBJECT-TYPE
    SYNTAX     Counter32
    MAX-ACCESS read-only
    STATUS     current
    DESCRIPTION
       "The number of NETBIOS_NR_ex messages sent on this transport
        connection."
    --## VALID ciscoDlswTConnOperEntryTime
    ::= { ciscoDlswTConnOperEntry 34 }

-- ...................................................................
-- (3) Circuit activities on each transport connection
-- ...................................................................
ciscoDlswTConnOperCirCreates  OBJECT-TYPE
    SYNTAX     Counter32
    MAX-ACCESS read-only
    STATUS     current
    DESCRIPTION
       "The number of times that circuits entered `circuit_established'
        state (not counting transitions from `circuit_restart')."
    --## VALID ciscoDlswTConnOperEntryTime
    ::= { ciscoDlswTConnOperEntry 35 }

ciscoDlswTConnOperCircuits  OBJECT-TYPE
    SYNTAX     Gauge32
    MAX-ACCESS read-only
    STATUS     current
    DESCRIPTION
       "The number of currently active circuits on this transport
        connection, where `active' means not in `disconnected' state."
    ::= { ciscoDlswTConnOperEntry 36 }

-- *******************************************************************
-- Transport Connection Specific
-- *******************************************************************
ciscoDlswTConnSpecific OBJECT IDENTIFIER ::= { ciscoDlswTConn 4 }
ciscoDlswTConnTcp      OBJECT IDENTIFIER ::= { ciscoDlswTConnSpecific 1 }

-- ...................................................................
-- TCP Transport Connection Specific  Configuration
-- ...................................................................
ciscoDlswTConnTcpConfigTable  OBJECT-TYPE
    SYNTAX     SEQUENCE OF DlswTConnTcpConfigEntry
    MAX-ACCESS not-accessible
    STATUS     current
    DESCRIPTION
       "This table defines the TCP transport connections that
        will be either initiated by or accepted by this DSLw.
        It augments the entries in ciscoDlswTConnConfigTable whose domain
        is ciscoDlswTCPDomain."
    ::= { ciscoDlswTConnTcp 1 }

ciscoDlswTConnTcpConfigEntry  OBJECT-TYPE
    SYNTAX     DlswTConnTcpConfigEntry
    MAX-ACCESS not-accessible
    STATUS     current
    DESCRIPTION
       "Each conceptual row defines parameters that are
        specific to ciscoDlswTCPDomain transport connections."
    INDEX   { ciscoDlswTConnConfigIndex }
    ::= { ciscoDlswTConnTcpConfigTable 1 }

DlswTConnTcpConfigEntry ::= SEQUENCE {
    ciscoDlswTConnTcpConfigKeepAliveInt       INTEGER,
    ciscoDlswTConnTcpConfigTcpConnections     INTEGER,
    ciscoDlswTConnTcpConfigMaxSegmentSize     INTEGER
    }

ciscoDlswTConnTcpConfigKeepAliveInt  OBJECT-TYPE
    SYNTAX     INTEGER (0..1800)
    UNITS      "seconds"
    MAX-ACCESS read-only
    STATUS     current
    DESCRIPTION
       "The time in seconds between TCP keepAlive messages when
        no traffic is flowing.  Zero signifies no keepAlive protocol.
        Changes take effect only for new TCP connections."
    DEFVAL  { 0 }
    ::= { ciscoDlswTConnTcpConfigEntry 1 }

ciscoDlswTConnTcpConfigTcpConnections  OBJECT-TYPE
    SYNTAX     INTEGER (1..16)
    MAX-ACCESS read-only
    STATUS     current
    DESCRIPTION
       "This is our preferred number of TCP connections within a
        TCP transport connection.  The actual number used is negotiated
        at capabilities exchange time. Changes take effect only
        for new transport connections."
    DEFVAL  { 2 }
    ::= { ciscoDlswTConnTcpConfigEntry 2 }

ciscoDlswTConnTcpConfigMaxSegmentSize  OBJECT-TYPE
    SYNTAX     INTEGER (0..65535)
    UNITS      "packets"
    MAX-ACCESS read-only
    STATUS     current
    DESCRIPTION
       "This is the number of bytes that this node is
        willing to receive over the read TCP connection(s).
        Changes take effect for new transport connections."
    DEFVAL  { 4096 }
    ::= { ciscoDlswTConnTcpConfigEntry 3 }

-- ...................................................................
-- TCP Transport Connection Specific  Operation
-- ...................................................................
ciscoDlswTConnTcpOperTable  OBJECT-TYPE
    SYNTAX     SEQUENCE OF DlswTConnTcpOperEntry
    MAX-ACCESS not-accessible
    STATUS     current
    DESCRIPTION
       "A list of TCP transport connections.   It is optional but
        desirable for an implementation to keep an entry for
        some period of time after the transport connection is
        disconnected.  This allows a network management station
        to capture additional useful information about the connection,
        in particular, statistical information and the cause of the
        disconnection."
    ::= { ciscoDlswTConnTcp 2 }

ciscoDlswTConnTcpOperEntry  OBJECT-TYPE
    SYNTAX     DlswTConnTcpOperEntry
    MAX-ACCESS not-accessible
    STATUS     current
    DESCRIPTION
       ""
    INDEX   { ciscoDlswTConnOperTDomain, ciscoDlswTConnOperRemoteTAddr }
    ::= { ciscoDlswTConnTcpOperTable 1 }

DlswTConnTcpOperEntry ::= SEQUENCE {
    ciscoDlswTConnTcpOperKeepAliveInt             INTEGER,
    ciscoDlswTConnTcpOperPrefTcpConnections       INTEGER,
    ciscoDlswTConnTcpOperTcpConnections           INTEGER
    }

ciscoDlswTConnTcpOperKeepAliveInt  OBJECT-TYPE
    SYNTAX     INTEGER (0..1800)
    UNITS      "seconds"
    MAX-ACCESS read-only
    STATUS     current
    DESCRIPTION
       "The time in seconds between TCP keepAlive messages when
        no traffic is flowing.  Zero signifies no keepAlive protocol is
        operating."
    ::= { ciscoDlswTConnTcpOperEntry 1 }

ciscoDlswTConnTcpOperPrefTcpConnections  OBJECT-TYPE
    SYNTAX     INTEGER (1..16)
    MAX-ACCESS read-only
    STATUS     current
    DESCRIPTION
       "This is the number of TCP connections preferred by this DLSw
        partner, as received in its capabilities exchange message."
    ::= { ciscoDlswTConnTcpOperEntry 2 }

ciscoDlswTConnTcpOperTcpConnections  OBJECT-TYPE
    SYNTAX     INTEGER (1..16)
    MAX-ACCESS read-only
    STATUS     current
    DESCRIPTION
       "This is the actual current number of TCP connections within
        this transport connection."
    ::= { ciscoDlswTConnTcpOperEntry 3 }

-- *******************************************************************
-- DLSW INTERFACE GROUP
-- *******************************************************************

ciscoDlswIfTable  OBJECT-TYPE
    SYNTAX     SEQUENCE OF DlswIfEntry
    MAX-ACCESS not-accessible
    STATUS     current
    DESCRIPTION
       "The list of interfaces on which DLSw is active."
    ::= { ciscoDlswInterface 1 }

ciscoDlswIfEntry  OBJECT-TYPE
    SYNTAX     DlswIfEntry
    MAX-ACCESS not-accessible
    STATUS     current
    DESCRIPTION
       ""
    INDEX   { ifIndex }
    ::= { ciscoDlswIfTable 1 }

DlswIfEntry ::= SEQUENCE {
    ciscoDlswIfRowStatus      RowStatus,
    ciscoDlswIfVirtualSegment INTEGER,
    ciscoDlswIfSapList        OCTET STRING
    }

ciscoDlswIfRowStatus  OBJECT-TYPE
    SYNTAX     RowStatus
    MAX-ACCESS read-only
    STATUS     current
    DESCRIPTION
       "This object is used by a Management Station to create
        or delete the row entry in the ciscoDlswIfTable
        following the RowStatus textual convention."
    ::= { ciscoDlswIfEntry 1 }

ciscoDlswIfVirtualSegment  OBJECT-TYPE
    SYNTAX     INTEGER (0..4095 | 65535)
    MAX-ACCESS read-only
    STATUS     current
    DESCRIPTION
       "The segment number that uniquely identifies the virtual
        segment to which this DLSw interface is connected.
        Current source routing protocols limit this value to
        the range 0 - 4095. (The value 0 is used by some
        management applications for special test cases.)
        A value of 65535 signifies that no virtual segment
        is assigned to this interface.  For instance,
        in a non-source routing environment, segment number
        assignment is not required."
    DEFVAL { 65535 }
    ::= { ciscoDlswIfEntry 2 }

ciscoDlswIfSapList  OBJECT-TYPE
    SYNTAX     OCTET STRING  (SIZE(16))
    MAX-ACCESS read-only
    STATUS     current
    DESCRIPTION
       "The SAP list indicates which SAPs are allowed to be
        data link switched through this interface.  This list
        has the same format described for ciscoDlswTConnConfigSapList.

        It is up to the implementation to determine when changes
        to this object take effect.  Turning off a particular SAP
        can destroy active circuits that are using that SAP.  The
        implementation may reject such changes until there are no
        active circuits if it so chooses.  In this case, it is up
        to the management station to close the circuits first, using
        ciscoDlswCircuitState.

        This implementation of DLSw does not maintain a SAP list per
        interface.  To limit traffic based upon the SAP, inteface
        access-lists should be applied, and their associated mib
        objects consulted.

        The DEFVAL below indicates support for all SAPs."
    DEFVAL  { 'ffffffffffffffffffffffffffffffff'h }
    ::= { ciscoDlswIfEntry 3 }

-- *******************************************************************
-- DIRECTORY
-- Directory services caches the locations of MAC addresses
-- and NetBIOS names.  For resources which are attached via
-- local interfaces, the ifIndex may be cached, and for
-- resources which are reachable via a DLSw partner, the
-- transport address of the DLSw partner is cached.
-- *******************************************************************

-- *******************************************************************
-- Directory Related Statistical Objects
-- *******************************************************************
ciscoDlswDirStat     OBJECT IDENTIFIER ::= { ciscoDlswDirectory 1 }

ciscoDlswDirMacEntries  OBJECT-TYPE
    SYNTAX     Gauge32
    MAX-ACCESS read-only
    STATUS     current
    DESCRIPTION
       "The current total number of entries in the ciscoDlswDirMacTable."
    ::= { ciscoDlswDirStat 1 }

ciscoDlswDirMacCacheHits  OBJECT-TYPE
    SYNTAX     Counter32
    MAX-ACCESS read-only
    STATUS     current
    DESCRIPTION
       "The number of times a cache search for a particular MAC address
        resulted in success."
    --## VALID ciscoDlswUpTime
    ::= { ciscoDlswDirStat 2 }

ciscoDlswDirMacCacheMisses  OBJECT-TYPE
    SYNTAX     Counter32
    MAX-ACCESS read-only
    STATUS     current
    DESCRIPTION
       "The number of times a cache search for a particular MAC address
        resulted in failure."
    --## VALID ciscoDlswUpTime
    ::= { ciscoDlswDirStat 3 }

ciscoDlswDirNBEntries  OBJECT-TYPE
    SYNTAX     Gauge32
    MAX-ACCESS read-only
    STATUS     current
    DESCRIPTION
       "The current total number of entries in the ciscoDlswDirNBTable."
    ::= { ciscoDlswDirStat 4 }

ciscoDlswDirNBCacheHits  OBJECT-TYPE
    SYNTAX     Counter32
    MAX-ACCESS read-only
    STATUS     current
    DESCRIPTION
       "The number of times a cache search for a particular NetBIOS name
        resulted in success."
    --## VALID ciscoDlswUpTime
    ::= { ciscoDlswDirStat 5 }

ciscoDlswDirNBCacheMisses  OBJECT-TYPE
    SYNTAX     Counter32
    MAX-ACCESS read-only
    STATUS     current
    DESCRIPTION
       "The number of times a cache search for a particular NetBIOS name
        resulted in failure."
    --## VALID ciscoDlswUpTime
    ::= { ciscoDlswDirStat 6 }

-- *******************************************************************
-- Directory Cache
-- *******************************************************************
ciscoDlswDirCache     OBJECT IDENTIFIER ::= { ciscoDlswDirectory 2 }

-- ...................................................................
-- Directory for MAC Addresses.
-- All Possible combinations of values of these objects.
--
--     EntryType   LocationType       Location             Status
--  ************** ************ *********************** **************
--  userConfigured    local     ifEntry or 0.0          reachable, or
--                                                      notReachable, or
--                                                      unknown
--  userConfigured    remote    TConnConfigEntry        reachable, or
--                                                      notReachable, or
--                                                      unknown
--  partnerCapExMsg   remote    TConnOperEntry          unknown
--  dynamic           local     ifEntry or 0.0          reachable
--  dynamic           remote    TConnOperEntry          reachable
--
-- ...................................................................
ciscoDlswDirMacTable  OBJECT-TYPE
    SYNTAX     SEQUENCE OF DlswDirMacEntry
    MAX-ACCESS not-accessible
    STATUS     current
    DESCRIPTION
       "This table contains locations of MAC addresses.
        They could be either verified or not verified,
        local or remote, and configured locally or learned
        from either Capabilities Exchange messages or
        directory searches."
    ::= { ciscoDlswDirCache 1 }

ciscoDlswDirMacEntry  OBJECT-TYPE
    SYNTAX     DlswDirMacEntry
    MAX-ACCESS not-accessible
    STATUS     current
    DESCRIPTION
       "Indexed by ciscoDlswDirMacIndex."
    INDEX   { ciscoDlswDirMacIndex }
    ::= { ciscoDlswDirMacTable 1 }

DlswDirMacEntry ::= SEQUENCE {
    ciscoDlswDirMacIndex          INTEGER,
    ciscoDlswDirMacMac            MacAddress,
    ciscoDlswDirMacMask           MacAddress,
    ciscoDlswDirMacEntryType      INTEGER,
    ciscoDlswDirMacLocationType   INTEGER,
    ciscoDlswDirMacLocation       InstancePointer,
    ciscoDlswDirMacStatus         INTEGER,
    ciscoDlswDirMacLFSize         LFSize,
    ciscoDlswDirMacRowStatus      RowStatus
    }

ciscoDlswDirMacIndex  OBJECT-TYPE
    SYNTAX     INTEGER (0..65000) -- ravip
    MAX-ACCESS not-accessible
    STATUS     current
    DESCRIPTION
       "Uniquely identifies a conceptual row of this table."
    ::= { ciscoDlswDirMacEntry 1 }

ciscoDlswDirMacMac  OBJECT-TYPE
    SYNTAX     MacAddress
    MAX-ACCESS read-only
    STATUS     current
    DESCRIPTION
       "The MAC address, together with the ciscoDlswDirMacMask,
        specifies a set of MAC addresses that are defined or
        discovered through an interface or partner DLSw nodes."
    ::= { ciscoDlswDirMacEntry 2 }

ciscoDlswDirMacMask  OBJECT-TYPE
    SYNTAX     MacAddress
    MAX-ACCESS read-only
    STATUS     current
    DESCRIPTION
       "The MAC address mask, together with the ciscoDlswDirMacMac,
        specifies a set of MAC addresses that are defined or
        discovered through an interface or partner DLSw nodes."
    DEFVAL { 'ffffffffffff'h }
    ::= { ciscoDlswDirMacEntry 3 }

ciscoDlswDirMacEntryType  OBJECT-TYPE
    SYNTAX     INTEGER  {
        other                    (1),
        userConfiguredPublic     (2),
        userConfiguredPrivate    (3),
        partnerCapExMsg          (4),
        dynamic                  (5)
    }
    MAX-ACCESS read-only
    STATUS     current
    DESCRIPTION
       "The cause of the creation of this conceptual row.
        It could be one of the three methods: (1) user
        configured, including via management protocol
        set operations, configuration file, command line
        or equivalent methods; (2) learned from the
        partner DLSw Capabilities Exchange messages;
        and (3) dynamic, e.g., learned from ICanReach
        messages, or LAN explorer frames.  Since only
        individual MAC addresses can be dynamically learned,
        dynamic entries will all have a mask of all FFs.

        The public versus private distinction for user-
        configured resources applies only to local resources
        (UC remote resources are private), and indicates
        whether that resource should be advertised in
        capabilities exchange messages sent by this node."
    DEFVAL { userConfiguredPublic }
    ::= { ciscoDlswDirMacEntry 4 }

ciscoDlswDirMacLocationType  OBJECT-TYPE
    SYNTAX     INTEGER  {
        other                 (1),
        local                 (2),
        remote                (3)
    }
    MAX-ACCESS read-only
    STATUS     current
    DESCRIPTION
       "The location of the resource (or a collection of
        resources using a mask) of this conceptual row
        is either (1) local - the resource is reachable
        via an interface, or (2) remote - the resource
        is reachable via a partner DLSw node (or a set
        of partner DLSw nodes)."
    DEFVAL { local }
    ::= { ciscoDlswDirMacEntry 5 }

ciscoDlswDirMacLocation  OBJECT-TYPE
    SYNTAX     InstancePointer
    MAX-ACCESS read-only
    STATUS     current
    DESCRIPTION
       "Points to either the ifEntry, ciscoDlswTConnConfigEntry,
        ciscoDlswTConnOperEntry, 0.0, or something that is implementation
        specific.  It identifies the location of the MAC address
        (or the collection of MAC addresses.)"
--  DEFVAL { 0.0 }
    ::= { ciscoDlswDirMacEntry 6 }
-- @@ DEFVAL of 0 and 0.0 do not compile

ciscoDlswDirMacStatus  OBJECT-TYPE
    SYNTAX     INTEGER  {
        unknown               (1),
        reachable             (2),
        notReachable          (3)
    }
    MAX-ACCESS read-only
    STATUS     current
    DESCRIPTION
       "This object specifies whether DLSw currently believes
        the MAC address to be accessible at the specified location.
        The value `notReachable' allows a configured resource
        definition to be taken out of service when a search to
        that resource fails (avoiding a repeat of the search)."
    DEFVAL { unknown }
    ::= { ciscoDlswDirMacEntry 7 }

ciscoDlswDirMacLFSize  OBJECT-TYPE
    SYNTAX     LFSize
    MAX-ACCESS read-only
    STATUS     current
    DESCRIPTION
       "The largest size of the MAC INFO field (LLC header and data)
        that a circuit to the MAC address can carry through this path."
    DEFVAL { lfs65535 }
    ::= { ciscoDlswDirMacEntry 8 }

ciscoDlswDirMacRowStatus  OBJECT-TYPE
    SYNTAX     RowStatus
    MAX-ACCESS read-only
    STATUS     current
    DESCRIPTION
       "This object is used by a Management Station to create
        or delete the row entry in the ciscoDlswDirMacTable
        following the RowStatus textual convention."
    ::= { ciscoDlswDirMacEntry 9 }

-- ...................................................................
-- Directory for NetBIOS Names
-- All Possible combinations of values of these objects.
--
--     EntryType   LocationType       Location             Status
--  .............. ............ ....................... ..............
--  userConfigured    local     ifEntry or 0.0          reachable, or
--                                                      notReachable, or
--                                                      unknown
--  userConfigured    remote    TConnConfigEntry        reachable, or
--                                                      notReachable, or
--                                                      unknown
--  partnerCapExMsg   remote    TConnOperEntry          unknown
--  dynamic           local     ifEntry or 0.0          reachable
--  dynamic           remote    TConnOperEntry          reachable
--
-- ...................................................................
ciscoDlswDirNBTable  OBJECT-TYPE
    SYNTAX     SEQUENCE OF DlswDirNBEntry
    MAX-ACCESS not-accessible
    STATUS     current
    DESCRIPTION
       "This table contains locations of NetBIOS names.
        They could be either verified or not verified,
        local or remote, and configured locally or learned
        from either Capabilities Exchange messages or
        directory searches."
    ::= { ciscoDlswDirCache 2 }

ciscoDlswDirNBEntry  OBJECT-TYPE
    SYNTAX     DlswDirNBEntry
    MAX-ACCESS not-accessible
    STATUS     current
    DESCRIPTION
       "Indexed by ciscoDlswDirNBIndex."
    INDEX   { ciscoDlswDirNBIndex }
    ::= { ciscoDlswDirNBTable 1 }

DlswDirNBEntry ::= SEQUENCE {
    ciscoDlswDirNBIndex           INTEGER,
    ciscoDlswDirNBName            NBName,
    ciscoDlswDirNBNameType        INTEGER,
    ciscoDlswDirNBEntryType       INTEGER,
    ciscoDlswDirNBLocationType    INTEGER,
    ciscoDlswDirNBLocation        InstancePointer,
    ciscoDlswDirNBStatus          INTEGER,
    ciscoDlswDirNBLFSize          LFSize,
    ciscoDlswDirNBRowStatus       RowStatus
    }

ciscoDlswDirNBIndex  OBJECT-TYPE
    SYNTAX     INTEGER (0..65000) -- ravip
    MAX-ACCESS not-accessible
    STATUS     current
    DESCRIPTION
       "Uniquely identifies a conceptual row of this table."
    ::= { ciscoDlswDirNBEntry 1 }

ciscoDlswDirNBName  OBJECT-TYPE
    SYNTAX     NBName
    MAX-ACCESS read-only
    STATUS     current
    DESCRIPTION
       "The NetBIOS name (including `any char' and `wildcard' characters)
        specifies a set of NetBIOS names that are defined or discovered
        through an interface or partner DLSw nodes."
    ::= { ciscoDlswDirNBEntry 2 }

ciscoDlswDirNBNameType  OBJECT-TYPE
    SYNTAX     INTEGER  {
        unknown       (1),
        individual    (2),
        group         (3)
    }
    MAX-ACCESS read-only
    STATUS     current
    DESCRIPTION
       "Whether ciscoDlswDirNBName represents an (or a set of) individual
        or group NetBIOS name(s)."
    DEFVAL { unknown }
    ::= { ciscoDlswDirNBEntry 3 }

ciscoDlswDirNBEntryType  OBJECT-TYPE
    SYNTAX     INTEGER  {
        other                    (1),
        userConfiguredPublic     (2),
        userConfiguredPrivate    (3),
        partnerCapExMsg          (4),
        dynamic                  (5)
    }
    MAX-ACCESS read-only
    STATUS     current
    DESCRIPTION
       "The cause of the creation of this conceptual row.
        It could be one of the three methods: (1) user
        configured, including via management protocol
        set operations, configuration file, command line,
        or equivalent methods; (2) learned from the
        partner DLSw Capabilities Exchange messages;
        and (3) dynamic, e.g., learned from ICanReach
        messages, or test frames.  Since only actual
        NetBIOS names can be dynamically learned, dynamic
        entries will not contain any char or wildcard
        characters.

        The public versus private distinction for user-
        configured resources applies only to local resources
        (UC remote resources are private), and indicates
        whether that resource should be advertised in
        capabilities exchange messages sent by this node."
    DEFVAL { userConfiguredPublic }
    ::= { ciscoDlswDirNBEntry 4 }

ciscoDlswDirNBLocationType  OBJECT-TYPE
    SYNTAX     INTEGER  {
        other                 (1),
        local                 (2),
        remote                (3)
    }
    MAX-ACCESS read-only
    STATUS     current
    DESCRIPTION
       "The location of the resource (or a collection of resources
        using any char/wildcard characters) of this conceptual row
        is either (1) local - the resource is reachable via an
        interface, or (2) remote - the resource is reachable via a
        a partner DLSw node (or a set of partner DLSw nodes)."
    DEFVAL { local }
    ::= { ciscoDlswDirNBEntry 5 }

ciscoDlswDirNBLocation  OBJECT-TYPE
    SYNTAX     InstancePointer
    MAX-ACCESS read-only
    STATUS     current
    DESCRIPTION
       "Points to either the ifEntry, ciscoDlswTConnConfigEntry,
        ciscoDlswTConnOperEntry, 0.0, or something that is implementation
        specific.  It identifies the location of the NetBIOS name
        or the set of NetBIOS names."
--  DEFVAL { 0 }
    ::= { ciscoDlswDirNBEntry 6 }
-- @@ DEFVAL of 0 and 0.0 do not compile

ciscoDlswDirNBStatus  OBJECT-TYPE
    SYNTAX     INTEGER  {
        unknown               (1),
        reachable             (2),
        notReachable          (3)
    }
    MAX-ACCESS read-only
    STATUS     current
    DESCRIPTION
       "This object specifies whether DLSw currently believes
        the NetBIOS name to be accessible at the specified location.
        The value `notReachable' allows a configured resource
        definition to be taken out of service when a search to
        that resource fails (avoiding a repeat of the search)."
    DEFVAL { unknown }
    ::= { ciscoDlswDirNBEntry 7 }

ciscoDlswDirNBLFSize  OBJECT-TYPE
    SYNTAX     LFSize
    MAX-ACCESS read-only
    STATUS     current
    DESCRIPTION
       "The largest size of the MAC INFO field (LLC header and data)
        that a circuit to the NB name can carry through this path."
    DEFVAL { lfs65535 }
    ::= { ciscoDlswDirNBEntry 8 }

ciscoDlswDirNBRowStatus  OBJECT-TYPE
    SYNTAX     RowStatus
    MAX-ACCESS read-only
    STATUS     current
    DESCRIPTION
       "This object is used by a Management Station to create
        or delete the row entry in the ciscoDlswDirNBTable
        following the RowStatus textual convention."
    ::= { ciscoDlswDirNBEntry 9 }

-- ...................................................................
-- Resource Locations
-- ...................................................................
ciscoDlswDirLocate       OBJECT IDENTIFIER ::= { ciscoDlswDirectory 3 }

-- ...................................................................
-- Locate Entries in the ciscoDlswDirMacTable for a given MAC address
-- ...................................................................
ciscoDlswDirLocateMacTable  OBJECT-TYPE
    SYNTAX     SEQUENCE OF DlswDirLocateMacEntry
    MAX-ACCESS not-accessible
    STATUS     current
    DESCRIPTION
       "This table is used to retrieve all entries in the
        ciscoDlswDirMacTable that match a given MAC address,
        in the order of the best matched first, the
        second best matched second, and so on.
        We should fall out of the table if a GET-NEXT of
        the least matched entry is requested."
    ::= { ciscoDlswDirLocate 1 }

ciscoDlswDirLocateMacEntry  OBJECT-TYPE
    SYNTAX     DlswDirLocateMacEntry
    MAX-ACCESS not-accessible
    STATUS     current
    DESCRIPTION
       "Indexed by ciscoDlswDirLocateMacMac and ciscoDlswDirLocateMacMatch.
        The first object is the MAC address of interest, and
        the second object is the order in the list of all
        entries that match the MAC address."
    INDEX   { ciscoDlswDirLocateMacMac, ciscoDlswDirLocateMacMatch }
    ::= { ciscoDlswDirLocateMacTable 1 }

DlswDirLocateMacEntry ::= SEQUENCE {
    ciscoDlswDirLocateMacMac            MacAddress,
    ciscoDlswDirLocateMacMatch          Integer32 (0..2147483647),
    ciscoDlswDirLocateMacLocation       InstancePointer
    }

ciscoDlswDirLocateMacMac  OBJECT-TYPE
    SYNTAX     MacAddress
    MAX-ACCESS not-accessible
    STATUS     current
    DESCRIPTION
       "The MAC address to be located."
    ::= { ciscoDlswDirLocateMacEntry 1 }

ciscoDlswDirLocateMacMatch  OBJECT-TYPE
    SYNTAX     Integer32 (0..2147483647)
    MAX-ACCESS not-accessible
    STATUS     current
    DESCRIPTION
       "The order of the entries of ciscoDlswDirMacTable
        that match ciscoDlswDirLocateMacMac.  A value of
        one represents the entry that best matches the
        MAC address.  A value of two represents the second
        best matched entry.  A GET-NEXT of the value of
        the least matched entry will return an object
        instance outside of this table."
    ::= { ciscoDlswDirLocateMacEntry 2 }

ciscoDlswDirLocateMacLocation  OBJECT-TYPE
    SYNTAX     InstancePointer
    MAX-ACCESS read-only
    STATUS     current
    DESCRIPTION
       "Points to the ciscoDlswDirMacEntry."
    ::= { ciscoDlswDirLocateMacEntry 3 }
-- @@ was not-accessible, would not compile

-- ...................................................................
-- Locate Entries in the ciscoDlswDirNBTable for a given NetBIOS name
-- ...................................................................
ciscoDlswDirLocateNBTable  OBJECT-TYPE
    SYNTAX     SEQUENCE OF DlswDirLocateNBEntry
    MAX-ACCESS not-accessible
    STATUS     current
    DESCRIPTION
       "This table is used to retrieve all entries in the
        ciscoDlswDirNBTable that match a given NetBIOS name,
        in the order of the best matched first, the
        second best matched second, and so on.
        We should fall out of the table, if a GET-NEXT of
        the least matched entry is requested."
    ::= { ciscoDlswDirLocate 2 }

ciscoDlswDirLocateNBEntry  OBJECT-TYPE
    SYNTAX     DlswDirLocateNBEntry
    MAX-ACCESS not-accessible
    STATUS     current
    DESCRIPTION
       "Indexed by ciscoDlswDirLocateNBName and ciscoDlswDirLocateNBMatch.
        The first object is the NetBIOS name of interest, and
        the second object is the order in the list of all
        entries that match the NetBIOS name."
    INDEX   { ciscoDlswDirLocateNBName, ciscoDlswDirLocateNBMatch }
    ::= { ciscoDlswDirLocateNBTable 1 }

DlswDirLocateNBEntry ::= SEQUENCE {
    ciscoDlswDirLocateNBName           NBName,
    ciscoDlswDirLocateNBMatch          Integer32 (0..2147483647),
    ciscoDlswDirLocateNBLocation       InstancePointer
    }

ciscoDlswDirLocateNBName  OBJECT-TYPE
    SYNTAX     NBName
    MAX-ACCESS not-accessible
    STATUS     current
    DESCRIPTION
       "The NetBIOS name to be located (no any char or wildcards)."
    ::= { ciscoDlswDirLocateNBEntry 1 }

ciscoDlswDirLocateNBMatch  OBJECT-TYPE
    SYNTAX     Integer32 (0..2147483647)
    MAX-ACCESS not-accessible
    STATUS     current
    DESCRIPTION
       "The order of the entries of ciscoDlswDirNBTable
        that match ciscoDlswDirLocateNBName.  A value of
        one represents the entry that best matches the
        NetBIOS name.  A value of two represents the second
        best matched entry.  A GET-NEXT of the value of
        the least matched entry will return an object
        instance outside of this table."
    ::= { ciscoDlswDirLocateNBEntry 2 }

ciscoDlswDirLocateNBLocation  OBJECT-TYPE
    SYNTAX     InstancePointer
    MAX-ACCESS read-only
    STATUS     current
    DESCRIPTION
       "Points to the ciscoDlswDirNBEntry."
    ::= { ciscoDlswDirLocateNBEntry 3 }
-- @@ was not-accessible, would not compile

-- *******************************************************************
-- CIRCUIT
-- A circuit is the end-to-end association of two DLS entities
-- through one or two DLSw nodes.  It is the concatenation of
-- two "data links", optionally with an intervening transport
-- connection. The origin of the circuit is the end station that
-- initiates the circuit.  The target of the circuit is the end
-- station that receives the initiation.
-- *******************************************************************

-- ...................................................................
-- Statistics Related to Circuits
-- ...................................................................
ciscoDlswCircuitStat      OBJECT IDENTIFIER ::= { ciscoDlswCircuit 1 }

ciscoDlswActiveCircuits  OBJECT-TYPE
    SYNTAX     Gauge32
    MAX-ACCESS read-only
    STATUS     current
    DESCRIPTION
       "The current number of circuits in ciscoDlswCircuitTable that are
        not in the disconnected state."
    ::= { ciscoDlswCircuitStat 1 }

ciscoDlswCircuitCreates  OBJECT-TYPE
    SYNTAX     Counter32
    MAX-ACCESS read-only
    STATUS     current
    DESCRIPTION
       "The total number of entries ever added to ciscoDlswCircuitTable,
        or reactivated upon exiting `disconnected' state."
    --## VALID ciscoDlswUpTime
    ::= { ciscoDlswCircuitStat 2 }

-- ...................................................................
-- Circuit Table
--
-- This table is the DLSw entity's view of circuits.  There will be
-- a conceptual row in the table associated with each data link.
--
-- The chart below lists the various possible combinations of
-- origin and target MAC locations and the number of entries in
-- this Circuit Table:
--
--           number of       |    Origin End Station Location
--         entries in the    |......................................
--         Circuit Table     |  internal     local       remote
--    .......................|......................................
--     Target    |  internal |     NA          2           1
--     End       |  local    |     2           2           1
--     Station   |  remote   |     1           1           NA
--     Location  |           |
--
--     NA: Not applicable
--
--  Note:
--  (a) IfIndex and RouteInfo are applied only if location is local.
--  (b) TDomain and TAddr are applied only if location is remote.
--
-- Most of statistics related to circuits can be collected
-- from LLC-2 Link Station Table.
-- ...................................................................
ciscoDlswCircuitTable  OBJECT-TYPE
    SYNTAX     SEQUENCE OF DlswCircuitEntry
    MAX-ACCESS not-accessible
    STATUS     current
    DESCRIPTION
       "This table is the circuit representation in the DLSw
        entity. Virtual data links are used to represent any internal
        end stations.  There is a conceptual row associated with
        each data link.  Thus, for circuits without an intervening
        transport connection, there are two conceptual rows
        for each circuit.

        The table consists of the circuits being established,
        established, and as an implementation option, circuits that
        have been disconnected.  For circuits carried over
        transport connections, an entry is created after
        the CUR_cs was sent or received.  For circuits between
        two locally attached devices, or internal virtual MAC
        addresses, an entry is created when the equivalent of
        CUR_cs sent/received status is reached.

        End station 1 (S1) and End station 2 (S2) are used to
        represent the two end stations of the circuit.
        S1 is always an end station which is locally attached.
        S2 may be locally attached or remote.  If it is locally
        attached, the circuit will be represented by two rows indexed
        by (A, B) and (B, A) where A & B are the relevant MACs/SAPs.

        The table may be used to store the causes of disconnection of
        circuits.  It is recommended that the oldest disconnected
        circuit entry be removed from this table when the memory
        space of disconnected circuits is needed."
    ::= { ciscoDlswCircuit 2 }

ciscoDlswCircuitEntry  OBJECT-TYPE
    SYNTAX     DlswCircuitEntry
    MAX-ACCESS not-accessible
    STATUS     current
    DESCRIPTION
       ""
    INDEX   { ciscoDlswCircuitS1Mac,
              ciscoDlswCircuitS1Sap,
              ciscoDlswCircuitS2Mac,
              ciscoDlswCircuitS2Sap }
    ::= { ciscoDlswCircuitTable 1 }

DlswCircuitEntry ::= SEQUENCE {
    ciscoDlswCircuitS1Mac                MacAddress,
    ciscoDlswCircuitS1Sap                OCTET STRING,
    ciscoDlswCircuitS1IfIndex            INTEGER,
    ciscoDlswCircuitS1DlcType            DlcType,
    ciscoDlswCircuitS1RouteInfo          OCTET STRING,
    ciscoDlswCircuitS1CircuitId          OCTET STRING,
    ciscoDlswCircuitS1Dlc                InstancePointer,
    ciscoDlswCircuitS2Mac                MacAddress,
    ciscoDlswCircuitS2Sap                OCTET STRING,
    ciscoDlswCircuitS2Location           EndStationLocation,
    ciscoDlswCircuitS2TDomain            OBJECT IDENTIFIER,
    ciscoDlswCircuitS2TAddress           TAddress,
    ciscoDlswCircuitS2CircuitId          OCTET STRING,
    ciscoDlswCircuitOrigin               INTEGER,
    ciscoDlswCircuitEntryTime            DlswTimeStamp,
    ciscoDlswCircuitStateTime            DlswTimeStamp,
    ciscoDlswCircuitState                INTEGER,
    ciscoDlswCircuitPriority           INTEGER,
    ciscoDlswCircuitFCSendGrantedUnits   INTEGER,
    ciscoDlswCircuitFCSendCurrentWndw    INTEGER,
    ciscoDlswCircuitFCRecvGrantedUnits   INTEGER,
    ciscoDlswCircuitFCRecvCurrentWndw    INTEGER,
    ciscoDlswCircuitFCLargestRecvGranted Gauge32,
    ciscoDlswCircuitFCLargestSendGranted Gauge32,
    ciscoDlswCircuitFCHalveWndwSents     Counter32,
    ciscoDlswCircuitFCResetOpSents       Counter32,
    ciscoDlswCircuitFCHalveWndwRcvds     Counter32,
    ciscoDlswCircuitFCResetOpRcvds       Counter32,
    ciscoDlswCircuitDiscReasonLocal      INTEGER,
    ciscoDlswCircuitDiscReasonRemote     INTEGER,
    ciscoDlswCircuitDiscReasonRemoteData OCTET STRING
    }

-- ...................................................................
-- Information related to the End Station 1 (S1).
-- ...................................................................
ciscoDlswCircuitS1Mac  OBJECT-TYPE
    SYNTAX     MacAddress
    MAX-ACCESS not-accessible
    STATUS     current
    DESCRIPTION
       "The MAC Address of End Station 1 (S1) used for this circuit."
    ::= { ciscoDlswCircuitEntry 1 }

ciscoDlswCircuitS1Sap  OBJECT-TYPE
    SYNTAX     OCTET STRING (SIZE(1))
    MAX-ACCESS not-accessible
    STATUS     current
    DESCRIPTION
       "The SAP at End Station 1 (S1) used for this circuit."
    ::= { ciscoDlswCircuitEntry 2 }

ciscoDlswCircuitS1IfIndex  OBJECT-TYPE
    SYNTAX     INTEGER (0..65000) -- ravip
    MAX-ACCESS read-only
    STATUS     current
    DESCRIPTION
       "The IfEntry index of the local interface through which S1
        can be reached."
    ::= { ciscoDlswCircuitEntry 3 }

ciscoDlswCircuitS1DlcType  OBJECT-TYPE
    SYNTAX     DlcType
    MAX-ACCESS read-only
    STATUS     current
    DESCRIPTION
       "The DLC protocol in use between the DLSw node and S1."
    ::= { ciscoDlswCircuitEntry 4 }

ciscoDlswCircuitS1RouteInfo  OBJECT-TYPE
    SYNTAX     OCTET STRING (SIZE (0..30))
    MAX-ACCESS read-only
    STATUS     current
    DESCRIPTION
       "If source-route bridging is in use between the DLSw
        node and S1, this is the routing information field
        describing the path between the two devices.
        Otherwise the value will be an OCTET STRING of
        zero length."
    ::= { ciscoDlswCircuitEntry 5 }

ciscoDlswCircuitS1CircuitId  OBJECT-TYPE
    SYNTAX     OCTET STRING (SIZE (0 | 8))
    MAX-ACCESS read-only
    STATUS     current
    DESCRIPTION
       "The Circuit ID assigned by this DLSw node to this circuit.
        The first four octets are the DLC port Id, and
        the second four octets are the Data Link Correlator.
        If the DLSw SSP was not used to establish this circuit,
        the value will be a string of zero length."
    ::= { ciscoDlswCircuitEntry 6 }

ciscoDlswCircuitS1Dlc  OBJECT-TYPE
    SYNTAX     InstancePointer
    MAX-ACCESS read-only
    STATUS     current
    DESCRIPTION
       "Points to a conceptual row of the underlying DLC MIB,
        which could either be the standard SDLC or LLC MIBs, or an
        enterprise-specific DLC MIB."
    ::= { ciscoDlswCircuitEntry 7 }

-- ...................................................................
-- Information related to the End Station 2 (S2).
-- ...................................................................
ciscoDlswCircuitS2Mac  OBJECT-TYPE
    SYNTAX     MacAddress
    MAX-ACCESS not-accessible
    STATUS     current
    DESCRIPTION
       "The MAC Address of End Station 2 (S2) used for this circuit."
    ::= { ciscoDlswCircuitEntry 8 }

ciscoDlswCircuitS2Sap  OBJECT-TYPE
    SYNTAX     OCTET STRING (SIZE(1))
    MAX-ACCESS not-accessible
    STATUS     current
    DESCRIPTION
       "The SAP at End Station 2 (S2) used for this circuit."
    ::= { ciscoDlswCircuitEntry 9 }

ciscoDlswCircuitS2Location  OBJECT-TYPE
    SYNTAX     EndStationLocation
    MAX-ACCESS read-only
    STATUS     current
    DESCRIPTION
       "The location of End Station 2 (S2).
        If the location of End Station 2 is local, the
        interface information will be available in the
        conceptual row whose S1 and S2 are the S2 and
        the S1 of this conceptual row, respectively."
    ::= { ciscoDlswCircuitEntry 10 }

ciscoDlswCircuitS2TDomain  OBJECT-TYPE
    SYNTAX     OBJECT IDENTIFIER
    MAX-ACCESS read-only
    STATUS     current
    DESCRIPTION
       "If the location of End Station 2 is remote,
        this value is the transport domain of the
        transport protocol the circuit is running
        over.  Otherwise, the value is 0.0."
    ::= { ciscoDlswCircuitEntry 11 }

ciscoDlswCircuitS2TAddress  OBJECT-TYPE
    SYNTAX     TAddress
    MAX-ACCESS read-only
    STATUS     current
    DESCRIPTION
       "If the location of End Station 2 is remote,
        this object contains the address of the partner
        DLSw, else it will be an OCTET STRING of zero length."
    ::= { ciscoDlswCircuitEntry 12 }

ciscoDlswCircuitS2CircuitId  OBJECT-TYPE
    SYNTAX     OCTET STRING (SIZE (0 | 8))
    MAX-ACCESS read-only
    STATUS     current
    DESCRIPTION
       "The Circuit ID assigned to this circuit by the partner
        DLSw node.  The first four octets are the DLC port Id, and
        the second four octets are the Data Link Correlator.
        If the DLSw SSP was not used to establish this circuit,
        the value will be a string of zero length."
    ::= { ciscoDlswCircuitEntry 13 }

-- ...................................................................
ciscoDlswCircuitOrigin  OBJECT-TYPE
    SYNTAX     INTEGER  {
        s1             (1),
        s2             (2)
    }
    MAX-ACCESS read-only
    STATUS     current
    DESCRIPTION
       "This object specifies which of the two end stations
        initiated the establishment of this circuit."
    ::= { ciscoDlswCircuitEntry 14 }

-- ...................................................................
-- Operational information related to this circuit.
-- ...................................................................
ciscoDlswCircuitEntryTime  OBJECT-TYPE
    SYNTAX     DlswTimeStamp
    MAX-ACCESS read-only
    STATUS     current
    DESCRIPTION
       "The value of ciscoDlswUpTime when this circuit table
        conceptual row was created."
    ::= { ciscoDlswCircuitEntry 15 }

ciscoDlswCircuitStateTime  OBJECT-TYPE
    SYNTAX     DlswTimeStamp
    MAX-ACCESS read-only
    STATUS     current
    DESCRIPTION
       "The value of ciscoDlswUpTime when this circuit entered the
        current state."
    ::= { ciscoDlswCircuitEntry 16 }

ciscoDlswCircuitState  OBJECT-TYPE
    SYNTAX     INTEGER  {
        disconnected           (1),
        circuitStart           (2),
        resolvePending         (3),
        circuitPending         (4),
        circuitEstablished     (5),
        connectPending         (6),
        contactPending         (7),
        connected              (8),
        disconnectPending      (9),
        haltPending            (10),
        haltPendingNoack       (11),
        circuitRestart         (12),
        restartPending         (13)
    }
    MAX-ACCESS read-only
    STATUS     current
    DESCRIPTION
       "The current state of this circuit.  The implementation
        may choose to keep entries for some period of time after
        circuit disconnect, so the network management station can
        gather the time and cause of disconnection.

        While all of the specified values may be returned from a GET
        operation, the only SETable value is `disconnectPending'.
        When this value is set, DLSw should perform the appropriate
        action given its previous state (e.g., send HALT_DL if the
        state was `connected') to bring the circuit down to the
        `disconnected' state.  Both the partner DLSw and local end
        station(s) should be notified as appropriate.

        This MIB provides no facility to re-establish a disconnected
        circuit, because in DLSw this should be an end station-driven
        function."
    ::= { ciscoDlswCircuitEntry 17 }

ciscoDlswCircuitPriority  OBJECT-TYPE
    SYNTAX     INTEGER  {
        unsupported     (0),
        low             (1),
        medium          (2),
        high            (3),
        highest         (4)
    }
    MAX-ACCESS read-only
    STATUS     current
    DESCRIPTION
       "The transmission priority of this circuit as understood by
        this DLSw node.  This value is determined by the two DLSw
        nodes at circuit startup time.  If this DLSw node does not
        support DLSw circuit priority, the value `unsupported' should
        be returned."
    ::= { ciscoDlswCircuitEntry 18 }

-- ...................................................................
-- Pacing Objects:
-- These objects are applicable if DLSw is using the SSP circuit
-- pacing protocol to control the flow between the two data links
-- in this circuit.
-- ...................................................................
ciscoDlswCircuitFCSendGrantedUnits  OBJECT-TYPE
    SYNTAX     INTEGER (0..65535)
    MAX-ACCESS read-only
    STATUS     current
    DESCRIPTION
       "The number of paced SSP messages that this DLSw is currently
        authorized to send on this circuit before it must stop and
        wait for an additional flow control indication from the
        partner DLSw.

        The value zero should be returned if this circuit is not
        running the DLSw pacing protocol."
    ::= { ciscoDlswCircuitEntry 19 }

ciscoDlswCircuitFCSendCurrentWndw  OBJECT-TYPE
    SYNTAX     INTEGER (0..65535)
    MAX-ACCESS read-only
    STATUS     current
    DESCRIPTION
       "The current window size that this DLSw is using in its role
        as a data sender.  This is the value by which this DLSw would
        increase the number of messages it is authorized to send, if
        it were to receive a flow control indication with the bits
        specifying `repeat window'.

        The value zero should be returned if this circuit is not
        running the DLSw pacing protocol."
    ::= { ciscoDlswCircuitEntry 20 }

ciscoDlswCircuitFCRecvGrantedUnits  OBJECT-TYPE
    SYNTAX     INTEGER (0..65535)
    MAX-ACCESS read-only
    STATUS     current
    DESCRIPTION
       "The current number of paced SSP messages that this DLSw has
        authorized the partner DLSw to send on this circuit before
        the partner DLSw must stop and wait for an additional flow
        control indication from this DLSw.

        The value zero should be returned if this circuit is not
        running the DLSw pacing protocol."
    ::= { ciscoDlswCircuitEntry 21 }

ciscoDlswCircuitFCRecvCurrentWndw  OBJECT-TYPE
    SYNTAX     INTEGER (0..65535)
    MAX-ACCESS read-only
    STATUS     current
    DESCRIPTION
       "The current window size that this DLSw is using in its role
        as a data receiver.  This is the number of additional paced
        SSP messages that this DLSw would be authorizing its DLSw
        partner to send, if this DLSw were to send a flow control
        indication with the bits specifying `repeat window'.

        The value zero should be returned if this circuit is not
        running the DLSw pacing protocol."
    ::= { ciscoDlswCircuitEntry 22 }

ciscoDlswCircuitFCLargestRecvGranted  OBJECT-TYPE
    SYNTAX     Gauge32
    MAX-ACCESS read-only
    STATUS     current
    DESCRIPTION
       "The largest receive window size granted by this DLSw during
        the current activation of this circuit.  This is not the
        largest number of messages granted at any time, but the
        largest window size as represented by FCIND operator bits.

        The value zero should be returned if this circuit is not
        running the DLSw pacing protocol."
    ::= { ciscoDlswCircuitEntry 23 }

ciscoDlswCircuitFCLargestSendGranted  OBJECT-TYPE
    SYNTAX     Gauge32
    MAX-ACCESS read-only
    STATUS     current
    DESCRIPTION
       "The largest send (with respect to this DLSw) window size
        granted by the partner DLSw during the current activation of
        this circuit.

        The value zero should be returned if this circuit is not
        running the DLSw pacing protocol."
    ::= { ciscoDlswCircuitEntry 24 }

ciscoDlswCircuitFCHalveWndwSents  OBJECT-TYPE
    SYNTAX     Counter32
    MAX-ACCESS read-only
    STATUS     current
    DESCRIPTION
       "The number of Halve Window operations this DLSw has sent on
        this circuit, in its role as a data receiver.

        The value zero should be returned if this circuit is not
        running the DLSw pacing protocol."
    --## VALID ciscoDlswCircuitEntryTime
    ::= { ciscoDlswCircuitEntry 25 }

ciscoDlswCircuitFCResetOpSents  OBJECT-TYPE
    SYNTAX     Counter32
    MAX-ACCESS read-only
    STATUS     current
    DESCRIPTION
       "The number of Reset Window operations this DLSw has sent on
        this circuit, in its role as a data receiver.

        The value zero should be returned if this circuit is not
        running the DLSw pacing protocol."
    --## VALID ciscoDlswCircuitEntryTime
    ::= { ciscoDlswCircuitEntry 26 }

ciscoDlswCircuitFCHalveWndwRcvds  OBJECT-TYPE
    SYNTAX     Counter32
    MAX-ACCESS read-only
    STATUS     current
    DESCRIPTION
       "The number of Halve Window operations this DLSw has received on
        this circuit, in its role as a data sender.

        The value zero should be returned if this circuit is not
        running the DLSw pacing protocol."
    --## VALID ciscoDlswCircuitEntryTime
    ::= { ciscoDlswCircuitEntry 27 }

ciscoDlswCircuitFCResetOpRcvds  OBJECT-TYPE
    SYNTAX     Counter32
    MAX-ACCESS read-only
    STATUS     current
    DESCRIPTION
       "The number of Reset Window operations this DLSw has received on
        this circuit, in its role as a data sender.

        The value zero should be returned if this circuit is not
        running the DLSw pacing protocol."
    --## VALID ciscoDlswCircuitEntryTime
    ::= { ciscoDlswCircuitEntry 28 }

-- ...................................................................
-- Information about the circuit disconnection
-- ...................................................................
ciscoDlswCircuitDiscReasonLocal  OBJECT-TYPE
    SYNTAX     INTEGER  {
        endStationDiscRcvd           (1),
        endStationDlcError           (2),
        protocolError                (3),
        operatorCommand              (4),
        haltDlRcvd                   (5),
        haltDlNoAckRcvd              (6),
        transportConnClosed          (7)
    }
    MAX-ACCESS read-only
    STATUS     current
    DESCRIPTION
       "The reason why this circuit was last disconnected, as seen
        by this DLSw node.

        This object is present only if the implementation keeps circuit
        table entries around for some period after circuit disconnect."
    ::= { ciscoDlswCircuitEntry 29 }

ciscoDlswCircuitDiscReasonRemote  OBJECT-TYPE
    SYNTAX     INTEGER  {
        unknown                      (0),
        endStationDiscRcvd           (1),
        endStationDlcError           (2),
        protocolError                (3),
        operatorCommand              (4)
    }
    MAX-ACCESS read-only
    STATUS     current
    DESCRIPTION
       "The generic reason code why this circuit was last disconnected,
        as reported by the DLSw partner in a HALT_DL or HALT_DL_NOACK.
        If the partner does not send a reason code in these messages, or
        the DLSw implementation does not report receiving one, the value
        `unknown' is returned.

        This object is present only if the implementation keeps circuit
        table entries around for some period after circuit disconnect."
    ::= { ciscoDlswCircuitEntry 30 }

ciscoDlswCircuitDiscReasonRemoteData  OBJECT-TYPE
    SYNTAX     OCTET STRING (SIZE (0 | 4))
    MAX-ACCESS read-only
    STATUS     current
    DESCRIPTION
       "Implementation-specific data reported by the DLSw partner in a
        HALT_DL or HALT_DL_NOACK, to help specify how and why this
        circuit was last disconnected.  If the partner does not send
        this data in these messages, or the DLSw implementation does
        not report receiving it, a string of zero length is returned.

        This object is present only if the implementation keeps circuit
        table entries around for some period after circuit disconnect."
    ::= { ciscoDlswCircuitEntry 31 }

-- ...................................................................
-- Statistics related to this circuit.
-- All statistics are in LLC-2 Link Station Statistical Table.
-- All SDLC statistics are in SDLC MIB
-- ...................................................................

-- *******************************************************************
-- DLSW SDLC EXTENSION
-- *******************************************************************
ciscoDlswSdlcLsEntries  OBJECT-TYPE
    SYNTAX     Gauge32
    MAX-ACCESS read-only
    STATUS     current
    DESCRIPTION
       "The number of entries in ciscoDlswSdlcLsTable."
    ::= { ciscoDlswSdlc 1 }

-- ...................................................................
ciscoDlswSdlcLsTable  OBJECT-TYPE
    SYNTAX     SEQUENCE OF DlswSdlcLsEntry
    MAX-ACCESS not-accessible
    STATUS     current
    DESCRIPTION
       "The table defines the virtual MAC addresses for those
        SDLC link stations that participate in data link switching."
    ::= { ciscoDlswSdlc 2 }

ciscoDlswSdlcLsEntry  OBJECT-TYPE
    SYNTAX     DlswSdlcLsEntry
    MAX-ACCESS not-accessible
    STATUS     current
    DESCRIPTION
       "The index of this table is the ifIndex value for the
        SDLC port which owns this link station and the poll
        address of the particular SDLC link station."
    INDEX  { ifIndex, sdlcLSAddress }
    ::= { ciscoDlswSdlcLsTable 1 }

DlswSdlcLsEntry ::= SEQUENCE {
    ciscoDlswSdlcLsLocalMac           MacAddress,
    ciscoDlswSdlcLsLocalSap           OCTET STRING,
    ciscoDlswSdlcLsLocalBlockNum      DisplayString,
    ciscoDlswSdlcLsLocalIdNum         DisplayString,
    ciscoDlswSdlcLsRemoteMac          MacAddress,
    ciscoDlswSdlcLsRemoteSap          OCTET STRING,
    ciscoDlswSdlcLsRowStatus          RowStatus
    }

ciscoDlswSdlcLsLocalMac    OBJECT-TYPE
    SYNTAX     MacAddress
    MAX-ACCESS read-only
    STATUS     current
    DESCRIPTION
       "The virtual MAC address used to represent the SDLC-attached
        link station to the rest of the DLSw network."
    ::= { ciscoDlswSdlcLsEntry 1 }

ciscoDlswSdlcLsLocalSap    OBJECT-TYPE
    SYNTAX     OCTET STRING (SIZE(1))
    MAX-ACCESS read-only
    STATUS     current
    DESCRIPTION
       "The SAP used to represent this link station."
    ::= { ciscoDlswSdlcLsEntry 2 }

ciscoDlswSdlcLsLocalBlockNum OBJECT-TYPE
    SYNTAX     DisplayString  (SIZE (0 | 3))
    MAX-ACCESS read-only
    STATUS     current
    DESCRIPTION
       "The block number is the first three digits of the node_id,
        if available.  These 3 hexadecimal digits identify the
        product and are not configurable."
    DEFVAL { ''h }
    ::= { ciscoDlswSdlcLsEntry 3 }

ciscoDlswSdlcLsLocalIdNum OBJECT-TYPE
    SYNTAX     DisplayString  (SIZE (0 | 5))
    MAX-ACCESS read-only
    STATUS     current
    DESCRIPTION
       "The ID number is the last 5 digits of the node_id, if
        available.  These 5 hexadecimal digits are
        administratively defined and combined with the 3 digit
        block number form the node_id.  This node_id is used to
        identify the local node and is included in SNA XIDs."
    DEFVAL { ''h }
    ::= { ciscoDlswSdlcLsEntry 4 }

ciscoDlswSdlcLsRemoteMac    OBJECT-TYPE
    SYNTAX     MacAddress
    MAX-ACCESS read-only
    STATUS     current
    DESCRIPTION
       "The MAC address to which DLSw should attempt to connect
        this link station. If this information is not available,
        a value of zero for this object should be returned."
    DEFVAL { ''h }
    ::= { ciscoDlswSdlcLsEntry 5 }

ciscoDlswSdlcLsRemoteSap    OBJECT-TYPE
    SYNTAX     OCTET STRING (SIZE (0 | 1))
    MAX-ACCESS read-only
    STATUS     current
    DESCRIPTION
       "The SAP of the remote station to which this link
        station should be connected.  If this information
        is not available, a length of zero for this object
        should be returned."
    DEFVAL { ''h }
    ::= { ciscoDlswSdlcLsEntry 6 }

ciscoDlswSdlcLsRowStatus    OBJECT-TYPE
    SYNTAX     RowStatus
    MAX-ACCESS read-only
    STATUS     current
    DESCRIPTION
       "This object is used by a Management Station to create
        or delete the row entry in the ciscoDlswSdlcLsTable
        following the RowStatus textual convention."
    ::= { ciscoDlswSdlcLsEntry 7 }

-- *******************************************************************
-- TRAP GENERATION CONTROL
-- *******************************************************************
ciscoDlswTrapControl OBJECT IDENTIFIER  ::= { ciscoDlswNode 10}

ciscoDlswTrapCntlTConnPartnerReject  OBJECT-TYPE
    SYNTAX     INTEGER  {
        enabled     (1),
        disabled    (2),
        partial     (3)
    }
    MAX-ACCESS read-only
    STATUS     current
    DESCRIPTION
       "Indicates whether the DLSw is permitted to emit partner
        reject related traps.  With the value of `enabled'
        the DLSw will emit all partner reject related traps.
        With the value of `disabled' the DLSw will not emit
        any partner reject related traps.  With the value
        of `partial' the DLSw will only emits partner reject
        traps for CapEx reject.  The changes take effect
        immediately."
    ::= { ciscoDlswTrapControl 1 }

ciscoDlswTrapCntlTConnProtViolation  OBJECT-TYPE
    SYNTAX     TruthValue
    MAX-ACCESS read-only
    STATUS     current
    DESCRIPTION
       "Indicates whether the DLSw is permitted to generate
        protocol-violation traps on the events such as
        window size violation.  The changes take effect
        immediately."
    ::= { ciscoDlswTrapControl 2 }

ciscoDlswTrapCntlTConn  OBJECT-TYPE
    SYNTAX     INTEGER {
        enabled     (1),
        disabled    (2),
        partial     (3)
    }
    MAX-ACCESS read-only
    STATUS     current
    DESCRIPTION
       "Indicates whether the DLSw is permitted to emit transport
        connection up and down traps.  With the value of `enabled'
        the DLSw will emit traps when connections enter `connected'
        and `disconnected' states.  With the value of `disabled'
        the DLSw will not emit traps when connections enter of
        `connected' and `disconnected' states.  With the value
        of `partial' the DLSw will only emits transport connection
        down traps when the connection is closed with busy.
        The changes take effect immediately."
    ::= { ciscoDlswTrapControl 3 }

ciscoDlswTrapCntlCircuit  OBJECT-TYPE
    SYNTAX     INTEGER {
        enabled     (1),
        disabled    (2),
        partial     (3)
    }
    MAX-ACCESS read-only
    STATUS     current
    DESCRIPTION
       "Indicates whether the DLSw is permitted to generate
        circuit up and down traps.  With the value of `enabled'
        the DLSw will emit traps when circuits enter `connected'
        and `disconnected' states.  With the value of `disabled'
        the DLSw will not emit traps when circuits enter of
        `connected' and `disconnected' states.  With the value
        of `partial' the DLSw will emit traps only for those
        circuits that are initiated by this DLSw, e.g.,
        originating the CUR_CS message.  The changes take effect
        immediately."
    ::= { ciscoDlswTrapControl 4 }

--@@ Should we have a trap control table instead of defining
--@@ an object to control each class of traps?

-- *******************************************************************
-- NOTIFICATIONS, i.e., TRAP DEFINITIONS

-- *******************************************************************
ciscoDlswTraps              OBJECT IDENTIFIER ::= { ciscoDlswMIBObjects 7 }

-- *******************************************************************
-- This section defines the well-known notifications sent by
-- DLSW agents.
-- Care must be taken to insure that no particular notification
-- is sent to a single receiving entity more often than once
-- every five seconds.
--
-- Traps includes:
-- (1) Partner rejected (capEx rejection, not in partner list, etc.)
-- (2) DLSw protocol violation (e.g., window size violation, etc.)
-- (3) Transport connection up/down
-- (4) Circuit up/down
-- *******************************************************************
--
--@@ Should this be definition in SNMP, or SNMPv2, or both?

ciscoDlswTrapTConnPartnerReject NOTIFICATION-TYPE
    OBJECTS { ciscoDlswTConnOperTDomain, ciscoDlswTConnOperRemoteTAddr
    }
    STATUS     current
    --## CONTROL   ciscoDlswTrapCntlTConnPartnerReject
    DESCRIPTION
       "This trap is sent each time a transport connection
        is rejected by a partner DLSw during Capabilities
        Exchanges."
    ::= { ciscoDlswTraps 1 }

ciscoDlswTrapTConnProtViolation NOTIFICATION-TYPE
    OBJECTS { ciscoDlswTConnOperTDomain, ciscoDlswTConnOperRemoteTAddr
    }
    STATUS     current
    --## CONTROL   ciscoDlswTrapCntlTConnProtViolation
    DESCRIPTION
       "This trap is sent each time a protocol violation
        is detected for a transport connection."
    ::= { ciscoDlswTraps 2 }

ciscoDlswTrapTConnUp NOTIFICATION-TYPE
    OBJECTS { ciscoDlswTConnOperTDomain, ciscoDlswTConnOperRemoteTAddr
    }
    STATUS     current
    --## CONTROL   ciscoDlswTrapCntlTConn
    DESCRIPTION
       "This trap is sent each time a transport connection
        enters `connected' state."
    ::= { ciscoDlswTraps 3 }

ciscoDlswTrapTConnDown NOTIFICATION-TYPE
    OBJECTS { ciscoDlswTConnOperTDomain, ciscoDlswTConnOperRemoteTAddr
    }
    STATUS     current
    --## CONTROL   ciscoDlswTrapCntlTConn
    DESCRIPTION
       "This trap is sent each time a transport connection
        enters `disconnected' state."
    ::= { ciscoDlswTraps 4 }

ciscoDlswTrapCircuitUp NOTIFICATION-TYPE
    OBJECTS { ciscoDlswCircuitS1Mac, ciscoDlswCircuitS1Sap,
              ciscoDlswCircuitS2Mac, ciscoDlswCircuitS2Sap
    }
    STATUS     current
    --## CONTROL   ciscoDlswTrapCntlCircuit
    DESCRIPTION
       "This trap is sent each time a circuit enters
        `connected' state."
    ::= { ciscoDlswTraps 5 }

ciscoDlswTrapCircuitDown NOTIFICATION-TYPE
    OBJECTS { ciscoDlswCircuitS1Mac, ciscoDlswCircuitS1Sap,
              ciscoDlswCircuitS2Mac, ciscoDlswCircuitS2Sap
    }
    STATUS     current
    --## CONTROL   ciscoDlswTrapCntlCircuit
    DESCRIPTION
       "This trap is sent each time a circuit enters
        `disconnected' state."
    ::= { ciscoDlswTraps 6 }

-- *******************************************************************
-- CONFORMANCE INFORMATION
-- *******************************************************************
ciscoDlswConformance        OBJECT IDENTIFIER ::= { ciscoDlswMIB 3 }

ciscoDlswCompliances        OBJECT IDENTIFIER ::= { ciscoDlswConformance 1 }
ciscoDlswGroups             OBJECT IDENTIFIER ::= { ciscoDlswConformance 2 }

-- *******************************************************************
-- COMPLIANCE STATEMENTS
-- *******************************************************************

-- ...................................................................
-- Core Compliance for all DLSw Entities
-- ...................................................................
ciscoDlswCoreCompliance MODULE-COMPLIANCE
    STATUS obsolete -- obsoleted by ciscoDlswCoreComplianceV11R01
    DESCRIPTION
       "The core compliance statement for all DLSw nodes."
    MODULE
        MANDATORY-GROUPS  {
                ciscoDlswNodeGroup,
                ciscoDlswTConnStatGroup,
                ciscoDlswTConnConfigGroup,
                ciscoDlswTConnOperGroup,
                ciscoDlswTConnTcpConfigGroup,
                ciscoDlswTConnTcpOperGroup,
                ciscoDlswInterfaceGroup,
                ciscoDlswCircuitStatGroup,
                ciscoDlswCircuitGroup }

--        GROUP ciscoDlswNodeNBGroup
--            DESCRIPTION
--               "The ciscoDlsw NetBIOS Node group is mandatory only for
--                those DLSw entities which also implement
--                NetBIOS."
-- 
--        GROUP ciscoDlswTConnNBGroup
--            DESCRIPTION
--               "The ciscoDlsw NetBIOS Transport Connection group is
--                mandatory only for those DLSw entities which
--                also implement NetBIOS."
-- 
--        OBJECT  ciscoDlswStatus
--            MIN-ACCESS  read-only
--            DESCRIPTION
--                "Write access is not required."
-- 
--        OBJECT  ciscoDlswVirtualSegmentLFSize
--            MIN-ACCESS  read-only
--            DESCRIPTION
--                "Write access is not required."
-- 
--        OBJECT  ciscoDlswResourceMacExclusivity
--            MIN-ACCESS  read-only
--            DESCRIPTION
--                "Write access is not required."
-- 
--        OBJECT  ciscoDlswResourceNBExclusivity
--            MIN-ACCESS  read-only
--            DESCRIPTION
--                "Write access is not required."
-- 
--        OBJECT  ciscoDlswTrapCntlTConnPartnerReject
--            MIN-ACCESS  read-only
--            DESCRIPTION
--                "Write access is not required."
-- 
--        OBJECT  ciscoDlswTrapCntlTConnProtViolation
--            MIN-ACCESS  read-only
--            DESCRIPTION
--                "Write access is not required."
-- 
--        OBJECT  ciscoDlswTrapCntlTConn
--            MIN-ACCESS  read-only
--            DESCRIPTION
--                "Write access is not required."
-- 
--        OBJECT  ciscoDlswTrapCntlCircuit
--            MIN-ACCESS  read-only
--            DESCRIPTION
--                "Write access is not required."
-- 
--        OBJECT  ciscoDlswTConnConfigTDomain
--            MIN-ACCESS  read-only
--            DESCRIPTION
--                "Write access is not required."
-- 
--        OBJECT  ciscoDlswTConnConfigLocalTAddr
--            MIN-ACCESS  read-only
--            DESCRIPTION
--                "Write access is not required."
-- 
--        OBJECT  ciscoDlswTConnConfigRemoteTAddr
--            MIN-ACCESS  read-only
--            DESCRIPTION
--                "Write access is not required."
-- 
--        OBJECT  ciscoDlswTConnConfigSetupType
--            MIN-ACCESS  read-only
--            DESCRIPTION
--                "Write access is not required."
-- 
--        OBJECT  ciscoDlswTConnConfigSapList
--            MIN-ACCESS  read-only
--            DESCRIPTION
--                "Write access is not required."
-- 
--        OBJECT  ciscoDlswTConnConfigAdvertiseMacNB
--            MIN-ACCESS  read-only
--            DESCRIPTION
--                "Write access is not required."
-- 
--        OBJECT  ciscoDlswTConnConfigInitCirRecvWndw
--            MIN-ACCESS  read-only
--            DESCRIPTION
--                "Write access is not required."
-- 
--        OBJECT  ciscoDlswTConnConfigOpens
--            MIN-ACCESS  read-only
--            DESCRIPTION
--                "Write access is not required."
-- 
--        OBJECT  ciscoDlswTConnConfigRowStatus
--            MIN-ACCESS  read-only
--            DESCRIPTION
--                "Write access is not required."
-- 
--        OBJECT  ciscoDlswTConnOperState
--            MIN-ACCESS  read-only
--            DESCRIPTION
--                "Write access is not required."
-- 
--        OBJECT  ciscoDlswIfRowStatus
--            MIN-ACCESS  read-only
--            DESCRIPTION
--                "Write access is not required."
-- 
--        OBJECT  ciscoDlswIfVirtualSegment
--            MIN-ACCESS  read-only
--            DESCRIPTION
--                "Write access is not required."
-- 
--        OBJECT  ciscoDlswIfSapList
--            MIN-ACCESS  read-only
--            DESCRIPTION
--                "Write access is not required."
-- 
--        OBJECT  ciscoDlswCircuitState
--            MIN-ACCESS  read-only
--            DESCRIPTION
--                "Write access is not required."
    ::= { ciscoDlswCompliances 1 }

ciscoDlswCoreComplianceV11R01 MODULE-COMPLIANCE
    STATUS current
    DESCRIPTION
       "The core compliance statement for all DLSw nodes."
    MODULE
        MANDATORY-GROUPS  {
                ciscoDlswNodeGroup,
                ciscoDlswTConnStatGroup,
                ciscoDlswTConnConfigGroup,
                ciscoDlswTConnOperGroup,
                ciscoDlswTConnTcpConfigGroup,
                ciscoDlswTConnTcpOperGroup,
                ciscoDlswInterfaceGroup,
                ciscoDlswCircuitStatGroup,
                ciscoDlswCircuitGroup }

        GROUP ciscoDlswNodeNBGroup
            DESCRIPTION
               "The ciscoDlsw NetBIOS Node group is mandatory only for
                those DLSw entities which also implement
                NetBIOS."

        GROUP ciscoDlswTConnNBGroup
            DESCRIPTION
               "The ciscoDlsw NetBIOS Transport Connection group is
                mandatory only for those DLSw entities which
                also implement NetBIOS."
    ::= { ciscoDlswCompliances 5 }

-- ...................................................................
-- Compliance for all DLSw Entities Which Implements the Directory
-- ...................................................................
ciscoDlswDirCompliance MODULE-COMPLIANCE
    STATUS obsolete	-- obsoleted by ciscoDlswDirComplianceV11R01
    DESCRIPTION
       ""
    MODULE
        MANDATORY-GROUPS  {
                ciscoDlswDirGroup }

        GROUP ciscoDlswDirNBGroup
            DESCRIPTION
               "The ciscoDlsw NetBIOS group is mandatory only for
                those DLSw entities which also implement
                NetBIOS."

--        OBJECT  ciscoDlswDirMacMac
--            MIN-ACCESS  read-only
--            DESCRIPTION
--                "Write access is not required."
-- 
--        OBJECT  ciscoDlswDirMacMask
--            MIN-ACCESS  read-only
--            DESCRIPTION
--                "Write access is not required."
-- 
--        OBJECT  ciscoDlswDirMacEntryType
--            MIN-ACCESS  read-only
--            DESCRIPTION
--                "Write access is not required."
-- 
--        OBJECT  ciscoDlswDirMacLocationType
--            MIN-ACCESS  read-only
--            DESCRIPTION
--                "Write access is not required."
-- 
--        OBJECT  ciscoDlswDirMacLocation
--            MIN-ACCESS  read-only
--            DESCRIPTION
--                "Write access is not required."
-- 
--        OBJECT  ciscoDlswDirMacLFSize
--            MIN-ACCESS  read-only
--            DESCRIPTION
--                "Write access is not required."
-- 
--        OBJECT  ciscoDlswDirMacRowStatus
--            MIN-ACCESS  read-only
--            DESCRIPTION
--                "Write access is not required."
-- 
--        OBJECT  ciscoDlswDirNBName
--            MIN-ACCESS  read-only
--            DESCRIPTION
--                "Write access is not required."
-- 
--        OBJECT  ciscoDlswDirNBNameType
--            MIN-ACCESS  read-only
--            DESCRIPTION
--                "Write access is not required."
-- 
--        OBJECT  ciscoDlswDirNBEntryType
--            MIN-ACCESS  read-only
--            DESCRIPTION
--                "Write access is not required."
-- 
--        OBJECT  ciscoDlswDirNBLocationType
--            MIN-ACCESS  read-only
--            DESCRIPTION
--                "Write access is not required."
-- 
--        OBJECT  ciscoDlswDirNBLocation
--            MIN-ACCESS  read-only
--            DESCRIPTION
--                "Write access is not required."
-- 
--        OBJECT  ciscoDlswDirNBLFSize
--            MIN-ACCESS  read-only
--            DESCRIPTION
--                "Write access is not required."
-- 
--        OBJECT  ciscoDlswDirNBRowStatus
--            MIN-ACCESS  read-only
--            DESCRIPTION
--                "Write access is not required."
    ::= { ciscoDlswCompliances 2 }

ciscoDlswDirComplianceV11R01 MODULE-COMPLIANCE
    STATUS current
    DESCRIPTION
       ""
    MODULE
        MANDATORY-GROUPS  {
                ciscoDlswDirGroup }

        GROUP ciscoDlswDirNBGroup
            DESCRIPTION
               "The ciscoDlsw NetBIOS group is mandatory only for
                those DLSw entities which also implement
                NetBIOS."
    ::= { ciscoDlswCompliances 6 }

-- ...................................................................
-- Compliance for all DLSw Entities That Provide Ordered
-- List of Directory Entries That Match a Resource.
-- ...................................................................
ciscoDlswDirLocateCompliance MODULE-COMPLIANCE
    STATUS current
    DESCRIPTION
       ""
    MODULE
        MANDATORY-GROUPS  {
                ciscoDlswDirLocateGroup }

        GROUP ciscoDlswDirLocateNBGroup
            DESCRIPTION
               "The ciscoDlsw NetBIOS group is mandatory only for
                those DLSw entities which also implement
                NetBIOS."
    ::= { ciscoDlswCompliances 3 }

-- ...................................................................
-- Compliance for all DLSw Entities Which Support SDLC.
-- ...................................................................
ciscoDlswSdlcCompliance MODULE-COMPLIANCE
    STATUS obsolete	-- obsoleted by ciscoDlswSdlcComplianceV11R01
    DESCRIPTION
       ""
    MODULE
        MANDATORY-GROUPS  {
                ciscoDlswSdlcGroup }

--        OBJECT  ciscoDlswSdlcLsLocalMac
--            MIN-ACCESS  read-only
--            DESCRIPTION
--               "Write access is not required."
-- 
--        OBJECT  ciscoDlswSdlcLsLocalSap
--            MIN-ACCESS  read-only
--            DESCRIPTION
--               "Write access is not required."
-- 
--        OBJECT  ciscoDlswSdlcLsLocalBlockNum
--            MIN-ACCESS  read-only
--            DESCRIPTION
--               "Write access is not required."
-- 
--        OBJECT  ciscoDlswSdlcLsLocalIdNum
--            MIN-ACCESS  read-only
--            DESCRIPTION
--               "Write access is not required."
-- 
--        OBJECT  ciscoDlswSdlcLsRemoteMac
--            MIN-ACCESS  read-only
--            DESCRIPTION
--               "Write access is not required."
-- 
--        OBJECT  ciscoDlswSdlcLsRemoteSap
--            MIN-ACCESS  read-only
--            DESCRIPTION
--               "Write access is not required."
-- 
--        OBJECT  ciscoDlswSdlcLsRowStatus
--            MIN-ACCESS  read-only
--            DESCRIPTION
--               "Write access is not required."
    ::= { ciscoDlswCompliances 4 }

ciscoDlswSdlcComplianceV11R01 MODULE-COMPLIANCE
    STATUS current
    DESCRIPTION
       ""
    MODULE
        MANDATORY-GROUPS  {
                ciscoDlswSdlcGroup }
    ::= { ciscoDlswCompliances 7 }

-- *******************************************************************
-- CONFORMANCE GROUPS
-- *******************************************************************

-- ...................................................................
-- Node Conformance Group
-- ...................................................................
ciscoDlswNodeGroup  OBJECT-GROUP
    OBJECTS  {
        ciscoDlswVersion,
        ciscoDlswVendorID,
        ciscoDlswVersionString,
        ciscoDlswStdPacingSupport,
        ciscoDlswStatus,
        ciscoDlswUpTime,
        ciscoDlswVirtualSegmentLFSize,
        ciscoDlswResourceMacExclusivity,
        ciscoDlswTrapCntlTConnPartnerReject,
        ciscoDlswTrapCntlTConnProtViolation,
        ciscoDlswTrapCntlTConn,
        ciscoDlswTrapCntlCircuit
        }
    STATUS current
    DESCRIPTION
       ""
    ::= { ciscoDlswGroups 1 }

-- ...................................................................
ciscoDlswNodeNBGroup  OBJECT-GROUP
    OBJECTS  {
        ciscoDlswResourceNBExclusivity
        }
    STATUS current
    DESCRIPTION
       ""
    ::= { ciscoDlswGroups 2 }

-- ...................................................................
ciscoDlswTConnStatGroup  OBJECT-GROUP
    OBJECTS  {
        ciscoDlswTConnStatActiveConnections,
        ciscoDlswTConnStatCloseIdles,
        ciscoDlswTConnStatCloseBusys
        }
    STATUS current
    DESCRIPTION
       ""
    ::= { ciscoDlswGroups 3 }

-- ...................................................................
ciscoDlswTConnConfigGroup  OBJECT-GROUP
    OBJECTS  {
        ciscoDlswTConnConfigTDomain,
        ciscoDlswTConnConfigLocalTAddr,
        ciscoDlswTConnConfigRemoteTAddr,
        ciscoDlswTConnConfigLastModifyTime,
        ciscoDlswTConnConfigEntryType,
        ciscoDlswTConnConfigGroupDefinition,
        ciscoDlswTConnConfigSetupType,
        ciscoDlswTConnConfigSapList,
        ciscoDlswTConnConfigAdvertiseMacNB,
        ciscoDlswTConnConfigInitCirRecvWndw,
        ciscoDlswTConnConfigOpens,
        ciscoDlswTConnConfigRowStatus
        }
    STATUS current
    DESCRIPTION
       ""
    ::= { ciscoDlswGroups 4 }

-- ...................................................................
ciscoDlswTConnOperGroup  OBJECT-GROUP
    OBJECTS  {
        ciscoDlswTConnOperLocalTAddr,
        ciscoDlswTConnOperEntryTime,
        ciscoDlswTConnOperConnectTime,
        ciscoDlswTConnOperState,
        ciscoDlswTConnOperConfigIndex,
        ciscoDlswTConnOperFlowCntlMode,
        ciscoDlswTConnOperPartnerVersion,
        ciscoDlswTConnOperPartnerVendorID,
        ciscoDlswTConnOperPartnerVersionStr,
        ciscoDlswTConnOperPartnerInitPacingWndw,   -- ravip
        ciscoDlswTConnOperPartnerSapList,
        ciscoDlswTConnOperPartnerMacExcl,
        ciscoDlswTConnOperPartnerMacInfo,
        ciscoDlswTConnOperDiscTime,
        ciscoDlswTConnOperDiscReason,
        ciscoDlswTConnOperDiscActiveCir,    -- ravip
        ciscoDlswTConnOperInDataPkts,
        ciscoDlswTConnOperOutDataPkts,
        ciscoDlswTConnOperInDataOctets,
        ciscoDlswTConnOperOutDataOctets,
        ciscoDlswTConnOperInCntlPkts,
        ciscoDlswTConnOperOutCntlPkts,
        ciscoDlswTConnOperCURexSents,
        ciscoDlswTConnOperICRexRcvds,
        ciscoDlswTConnOperCURexRcvds,
        ciscoDlswTConnOperICRexSents,
        ciscoDlswTConnOperCirCreates,
        ciscoDlswTConnOperCircuits
        }
    STATUS current
    DESCRIPTION
       ""
    ::= { ciscoDlswGroups 5 }

-- ...................................................................
ciscoDlswTConnNBGroup  OBJECT-GROUP
    OBJECTS  {
        ciscoDlswTConnOperPartnerNBInfo,
        ciscoDlswTConnOperPartnerNBExcl,
        ciscoDlswTConnOperNQexSents,
        ciscoDlswTConnOperNRexRcvds,
        ciscoDlswTConnOperNQexRcvds,
        ciscoDlswTConnOperNRexSents
        }
    STATUS current
    DESCRIPTION
       ""
    ::= { ciscoDlswGroups 6 }

-- ...................................................................
ciscoDlswInterfaceGroup  OBJECT-GROUP
    OBJECTS  {
        ciscoDlswIfRowStatus,
        ciscoDlswIfVirtualSegment,
        ciscoDlswIfSapList
        }
    STATUS current
    DESCRIPTION
       ""
    ::= { ciscoDlswGroups 7 }

-- ...................................................................
ciscoDlswDirGroup  OBJECT-GROUP
    OBJECTS  {
        ciscoDlswDirMacEntries,
        ciscoDlswDirMacCacheHits,
        ciscoDlswDirMacCacheMisses,
        ciscoDlswDirMacMac,
        ciscoDlswDirMacMask,
        ciscoDlswDirMacEntryType,
        ciscoDlswDirMacLocationType,
        ciscoDlswDirMacLocation,
        ciscoDlswDirMacStatus,
        ciscoDlswDirMacLFSize,
        ciscoDlswDirMacRowStatus
        }
    STATUS current
    DESCRIPTION
       ""
    ::= { ciscoDlswGroups 8 }

-- ...................................................................
ciscoDlswDirNBGroup  OBJECT-GROUP
    OBJECTS  {
        ciscoDlswDirNBEntries,
        ciscoDlswDirNBCacheHits,
        ciscoDlswDirNBCacheMisses,
        ciscoDlswDirNBName,
        ciscoDlswDirNBNameType,
        ciscoDlswDirNBEntryType,
        ciscoDlswDirNBLocationType,
        ciscoDlswDirNBLocation,
        ciscoDlswDirNBStatus,
        ciscoDlswDirNBLFSize,
        ciscoDlswDirNBRowStatus
        }
    STATUS current
    DESCRIPTION
       ""
    ::= { ciscoDlswGroups 9 }

-- ...................................................................
ciscoDlswDirLocateGroup  OBJECT-GROUP
    OBJECTS  {
        ciscoDlswDirLocateMacLocation
        }
    STATUS current
    DESCRIPTION
       ""
    ::= { ciscoDlswGroups 10 }

-- ...................................................................
ciscoDlswDirLocateNBGroup  OBJECT-GROUP
    OBJECTS  {
        ciscoDlswDirLocateNBLocation
        }
    STATUS current
    DESCRIPTION
       ""
    ::= { ciscoDlswGroups 11 }

-- ...................................................................
ciscoDlswCircuitGroup  OBJECT-GROUP
    OBJECTS  {
        ciscoDlswCircuitS1IfIndex,
        ciscoDlswCircuitS1DlcType,
        ciscoDlswCircuitS1RouteInfo,
        ciscoDlswCircuitS1CircuitId,
        ciscoDlswCircuitS1Dlc,
        ciscoDlswCircuitS2Location,
        ciscoDlswCircuitS2TDomain,
        ciscoDlswCircuitS2TAddress,
        ciscoDlswCircuitS2CircuitId,
        ciscoDlswCircuitOrigin,
        ciscoDlswCircuitEntryTime,
        ciscoDlswCircuitStateTime,
        ciscoDlswCircuitState,
        ciscoDlswCircuitPriority,
        ciscoDlswCircuitFCSendGrantedUnits,
        ciscoDlswCircuitFCSendCurrentWndw,
        ciscoDlswCircuitFCRecvGrantedUnits,
        ciscoDlswCircuitFCRecvCurrentWndw,
        ciscoDlswCircuitFCLargestRecvGranted,
        ciscoDlswCircuitFCLargestSendGranted,
        ciscoDlswCircuitFCHalveWndwSents,
        ciscoDlswCircuitFCResetOpSents,
        ciscoDlswCircuitFCHalveWndwRcvds,
        ciscoDlswCircuitFCResetOpRcvds,
        ciscoDlswCircuitDiscReasonLocal,
        ciscoDlswCircuitDiscReasonRemote,
        ciscoDlswCircuitDiscReasonRemoteData
        }
    STATUS current
    DESCRIPTION
       ""
    ::= { ciscoDlswGroups 12 }

-- ...................................................................
ciscoDlswSdlcGroup  OBJECT-GROUP
    OBJECTS  {
        ciscoDlswSdlcLsEntries,
        ciscoDlswSdlcLsLocalMac,
        ciscoDlswSdlcLsLocalSap,
        ciscoDlswSdlcLsLocalBlockNum,
        ciscoDlswSdlcLsLocalIdNum,
        ciscoDlswSdlcLsRemoteMac,
        ciscoDlswSdlcLsRemoteSap,
        ciscoDlswSdlcLsRowStatus
        }
    STATUS current
    DESCRIPTION
       ""
    ::= { ciscoDlswGroups 13 }

-- ...................................................................
-- ciscoDlswNotificationGroup  NOTIFICATION-GROUP
--    NOTIFICATIONS  {
--        ciscoDlswTrapTConnPartnerReject,
--        ciscoDlswTrapTConnProtViolation,
--        ciscoDlswTrapTConnUp,
--        ciscoDlswTrapTConnDown,
--        ciscoDlswTrapCircuitUp,
--        ciscoDlswTrapCircuitDown
--        }
--    STATUS current
--    DESCRIPTION
--       ""
--    ::= { ciscoDlswGroups 14 }

-- .ravip ..................................................................
ciscoDlswTConnTcpConfigGroup OBJECT-GROUP
  OBJECTS {
    ciscoDlswTConnTcpConfigKeepAliveInt,
    ciscoDlswTConnTcpConfigTcpConnections,
    ciscoDlswTConnTcpConfigMaxSegmentSize
    }
    STATUS current
    DESCRIPTION
       ""
    ::= { ciscoDlswGroups 15 }

ciscoDlswTConnTcpOperGroup OBJECT-GROUP
  OBJECTS {
    ciscoDlswTConnTcpOperKeepAliveInt,
    ciscoDlswTConnTcpOperPrefTcpConnections,
    ciscoDlswTConnTcpOperTcpConnections
    }
    STATUS current
    DESCRIPTION
       ""
    ::= { ciscoDlswGroups 16 }

ciscoDlswCircuitStatGroup OBJECT-GROUP
  OBJECTS { 
    ciscoDlswActiveCircuits,
    ciscoDlswCircuitCreates
    }
    STATUS current
    DESCRIPTION
       ""
    ::= { ciscoDlswGroups 17 }
-- .ravip ..................................................................

END
