CISCO-IETF-DHCP-SERVER-CAPABILITY DEFINITIONS ::= BEGIN

IMPORTS
    MODULE-IDENTITY
        FROM SNMPv2-SMI
    AGENT-CAPABILITIES
        FROM SNMPv2-CONF
    ciscoAgentCapability
        FROM CISCO-SMI;

ciscoIetfDhcpSrvCapability MODULE-IDENTITY
    LAST-UPDATED    "200702141200Z"
    ORGANIZATION    "Cisco Systems, Inc."
    CONTACT-INFO
            "Cisco Systems
            Customer Service

            Postal: 170 W Tasman Drive
            San Jose, CA  95134
            USA

            Tel: +1 800 553-NETS

            E-mail: cs-dhcp-mib@cisco.com"
    DESCRIPTION
        "Agent capabilities for the CISCO-IETF-DHCP-SERVER-MIB."
    REVISION        "200702141200Z"
    DESCRIPTION
        "Added capability definition ciscoIetfDhcpServerCapabilityV12R02SRC
        for 12.2SRC."
    REVISION        "200505240000Z"
    DESCRIPTION
        "Initial version of this MIB module."
    ::= { ciscoAgentCapability 439 }

ciscoIetfDhcpServerCapabilityV62R00 AGENT-CAPABILITIES
    PRODUCT-RELEASE "Cisco CNS Network Registrar 6.2"
    STATUS          current
    DESCRIPTION
        "CISCO-IETF-DHCP-SERVER-MIB capabilities for
        Cisco CNS Network Registrar 6.2"

    SUPPORTS        CISCO-IETF-DHCP-SERVER-MIB
    INCLUDES        {
                        cDhcpv4SrvSystemObjects,
                        cDhcpv4CounterObjects
                    }
    VARIATION       cBootpCountRequests
    ACCESS          not-implemented
    DESCRIPTION
        "Not supported."

    VARIATION       cBootpCountInvalids
    ACCESS          not-implemented
    DESCRIPTION
        "Not supported."

    VARIATION       cBootpCountReplies
    ACCESS          not-implemented
    DESCRIPTION
        "Not supported."

    VARIATION       cBootpCountDropUnknownClients
    ACCESS          not-implemented
    DESCRIPTION
        "Not supported."

    VARIATION       cBootpCountDropNotServingSubnet
    ACCESS          not-implemented
    DESCRIPTION
        "Not supported."

    VARIATION       cDhcpv4CountInvalids
    ACCESS          not-implemented
    DESCRIPTION
        "Not supported."

    VARIATION       cDhcpv4CountDropUnknownClient
    ACCESS          not-implemented
    DESCRIPTION
        "Not supported."

    VARIATION       cDhcpv4CountDropNotServingSubnet
    ACCESS          not-implemented
    DESCRIPTION
        "Not supported."
    ::= { ciscoIetfDhcpSrvCapability 1 }

ciscoIetfDhcpServerCapabilityV12R02SRC AGENT-CAPABILITIES
    PRODUCT-RELEASE "Cisco IOS 12.2SRC"
    STATUS          current
    DESCRIPTION
        "CISCO-IETF-DHCP-SERVER-MIB capabilities for
        Cisco IOS 12.2SRC"

    SUPPORTS        CISCO-IETF-DHCP-SERVER-MIB
    INCLUDES        {
                        cDhcpv4SrvSystemObjects,
                        cBootpHCCountersGroup,
                        cDhcpv4HCCounterObjects,
                        cDhcpv4ServerSharedNetObjects,
                        cDhcpv4ServerSubnetObjects,
                        cDhcpv4ServerNotifyObjectsGroup,
                        cDhcpv4ServerNotificationsGroup
                    }
    VARIATION       cBootpHCCountInvalids
    ACCESS          not-implemented
    DESCRIPTION
        "Not supported."

    VARIATION       cBootpHCCountDropUnknownClients
    ACCESS          not-implemented
    DESCRIPTION
        "Not supported."

    VARIATION       cBootpHCCountDropNotServingSubnet
    ACCESS          not-implemented
    DESCRIPTION
        "Not supported."

    VARIATION       cDhcpv4HCCountForcedRenews
    ACCESS          not-implemented
    DESCRIPTION
        "Not supported."

    VARIATION       cDhcpv4CountDropUnknownClient
    ACCESS          not-implemented
    DESCRIPTION
        "Not supported."

    VARIATION       cDhcpv4CountDropNotServingSubnet
    ACCESS          not-implemented
    DESCRIPTION
        "Not supported."

    VARIATION       cDhcpv4ServerSharedNetFreeAddrLowThreshold
    ACCESS          read-only
    DESCRIPTION
        "Write/create not implemented"

    VARIATION       cDhcpv4ServerSharedNetFreeAddrHighThreshold
    ACCESS          read-only
    DESCRIPTION
        "Write/create not implemented"

    VARIATION       cDhcpv4ServerSubnetFreeAddrLowThreshold
    ACCESS          read-only
    DESCRIPTION
        "Write/create not implemented"

    VARIATION       cDhcpv4ServerSubnetFreeAddrHighThreshold
    ACCESS          read-only
    DESCRIPTION
        "Write/create not implemented"
    ::= { ciscoIetfDhcpSrvCapability 2 }

END
