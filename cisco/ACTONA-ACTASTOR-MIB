ACTONA-ACTASTOR-MIB DEFINITIONS ::= BEGIN

IMPORTS
    OBJECT-GROUP,
    NOTIFICATION-GROUP
        FROM SNMPv2-CONF
    enterprises,
    MODULE-IDENTITY,
    OBJECT-IDENTITY,
    OBJECT-TYPE,
    NOTIFICATION-TYPE,
    Counter32,
    Integer32,
    TimeTicks,
    Unsigned32
        FROM SNMPv2-SMI
    DisplayString
        FROM SNMPv2-TC;

actona MODULE-IDENTITY
    LAST-UPDATED    "201007300000Z"
    ORGANIZATION    "Cisco Systems, Inc."
    CONTACT-INFO
            "Cisco Systems
            170 W Tasman Drive
            San Jose, CA  95134
            USA
            Tel: +1 800 553-NETS
            E-mail: cs-webcache@cisco.com"
    DESCRIPTION
        "Actona ActaStor MIB file"
    REVISION        "201007300000Z"
    DESCRIPTION
        "Added cifs AO related objects"
    REVISION        "200412230000Z"
    DESCRIPTION
        "(1) Added aclogSeverity and aclogMsgText objects.
        (2) deprecated csLogsTrap, esLogsTrap, mgrLogsTrap objects
            and replaced it with acCsLOgsTrap, acEsLogsTrap, 
            and acMgrLogsTrap objects.
        (2) deprecated logNotificationsGroup and replaced it with
            logNotificationsGroupRev1."
    REVISION        "200311241610Z"
    DESCRIPTION
        "Actona Technologies"
    ::= { enterprises 17471 }

acNotifications  OBJECT IDENTIFIER
    ::= { actona 0 }

actastor OBJECT-IDENTITY
    STATUS          current
    DESCRIPTION
        "Actona ActaStor product"
    ::= { actona 1 }

generalInformation OBJECT-IDENTITY
    STATUS          current
    DESCRIPTION
        "ActaStor general information"
    ::= { actastor 1 }

actastorVersion OBJECT-TYPE
    SYNTAX          OCTET STRING
    MAX-ACCESS      read-only
    STATUS          current
    DESCRIPTION
        "ActaStor installed version number" 
    ::= { generalInformation 1 }

buildString OBJECT-TYPE
    SYNTAX          OCTET STRING
    MAX-ACCESS      read-only
    STATUS          current
    DESCRIPTION
        "ActaStor installed build label" 
    ::= { generalInformation 2 }

support OBJECT-IDENTITY
    STATUS          current
    DESCRIPTION
        "Actona Support contact information"
    ::= { generalInformation 3 }

email OBJECT-TYPE
    SYNTAX          OCTET STRING
    MAX-ACCESS      read-only
    STATUS          current
    DESCRIPTION
        "Actona Support email address" 
    ::= { support 1 }

license OBJECT-IDENTITY
    STATUS          current
    DESCRIPTION
        "ActaStor license infromation"
    ::= { generalInformation 4 }

isValid OBJECT-TYPE
    SYNTAX          INTEGER  {
                        no(0),
                        yes(1)
                    }
    MAX-ACCESS      read-only
    STATUS          current
    DESCRIPTION
        "Indicates whether the installed license is valid" 
    ::= { license 1 }

daysLeft OBJECT-TYPE
    SYNTAX          Integer32 (0..99999)
    UNITS           "days (99999 is unlimited license)"
    MAX-ACCESS      read-only
    STATUS          current
    DESCRIPTION
        "The number of days remaining until the installed license expires" 
    ::= { license 2 }

manager OBJECT-IDENTITY
    STATUS          current
    DESCRIPTION
        "ActaStor manager-related information"
    ::= { actastor 2 }

mgrCentralServerHost OBJECT-TYPE
    SYNTAX          OCTET STRING
    MAX-ACCESS      read-only
    STATUS          current
    DESCRIPTION
        "The name/IP address of the host acting as the Central Manager
        of this gateway, in the ActaStor network" 
    ::= { manager 1 }

mgrLogsTrap NOTIFICATION-TYPE
    STATUS          deprecated
    DESCRIPTION
        "The OID of trap messages related to ActaStor management.
        This object is deprecated in the favor of acMgrLogsTrap."
   ::= { manager 2 }

coreServer OBJECT-IDENTITY
    STATUS          current
    DESCRIPTION
        "ActaStor CoreServer-related information"
    ::= { actastor 3 }

csGeneral OBJECT-IDENTITY
    STATUS          current
    DESCRIPTION
        "CoreServer general infromation"
    ::= { coreServer 1 }

csIsConfigured OBJECT-TYPE
    SYNTAX          INTEGER  {
                        no(0),
                        yes(1)
                    }
    MAX-ACCESS      read-only
    STATUS          current
    DESCRIPTION
        "Indicates whether the CoreServer component has been configured
        to run on this gateway" 
    ::= { csGeneral 1 }

csIsAlive OBJECT-TYPE
    SYNTAX          INTEGER  {
                        no(0),
                        yes(1)
                    }
    MAX-ACCESS      read-only
    STATUS          current
    DESCRIPTION
        "Indicates whether the CoreServer component is currently
        running on this gateway" 
    ::= { csGeneral 2 }

csUpTime OBJECT-TYPE
    SYNTAX          TimeTicks
    MAX-ACCESS      read-only
    STATUS          current
    DESCRIPTION
        "The elapsed time since the CoreServer was started" 
    ::= { csGeneral 3 }

csState OBJECT-IDENTITY
    STATUS          current
    DESCRIPTION
        "The current run-time state of the CoreServer"
    ::= { coreServer 2 }

csConnectivityTable OBJECT-TYPE
    SYNTAX          SEQUENCE OF CsConnectivityEntry 
    MAX-ACCESS      not-accessible
    STATUS          current
    DESCRIPTION
        "A table describing the current state of EdgeServer
        connections to this CoreServer"
    ::= { csState 1 }

csConnectivityEntry OBJECT-TYPE
    SYNTAX          CsConnectivityEntry
    MAX-ACCESS      not-accessible
    STATUS          current
    DESCRIPTION
        "A single entry in the connection table - denoting a
        specific EdgeServer"
    INDEX           { csConTabIndex } 
    ::= { csConnectivityTable 1 }

CsConnectivityEntry ::= SEQUENCE {
        csConTabIndex                    Integer32,
        csConTabClusterID                Integer32,
        csConTabClusterName              OCTET STRING,
        csConTabIsConnected              INTEGER,
        csConTabTotalSentMessages        Counter32,
        csConTabSentCompressionRatio     Integer32,
        csConTabTotalReceivedMessages    Counter32,
        csConTabReceivedCompressionRatio Integer32,
        csConTabTotalSentKBytes          Unsigned32,
        csConTabTotalReceivedKBytes      Unsigned32
}

csConTabIndex OBJECT-TYPE
    SYNTAX          Integer32 (1..1000)
    MAX-ACCESS      not-accessible
    STATUS          current
    DESCRIPTION
        "Index column - sequential line number in the table" 
    ::= { csConnectivityEntry 1 }

csConTabClusterID OBJECT-TYPE
    SYNTAX          Integer32 (0..2147483647)
    MAX-ACCESS      read-only
    STATUS          current
    DESCRIPTION
        "ID of the CoreServer cluster to which this CoreServer belongs" 
    ::= { csConnectivityEntry 2 }

csConTabClusterName OBJECT-TYPE
    SYNTAX          OCTET STRING
    MAX-ACCESS      read-only
    STATUS          current
    DESCRIPTION
        "Name of the CoreServer cluster to which this CoreServer belongs" 
    ::= { csConnectivityEntry 3 }

csConTabIsConnected OBJECT-TYPE
    SYNTAX          INTEGER  {
                        no(0),
                        yes(1)
                    }
    MAX-ACCESS      read-only
    STATUS          current
    DESCRIPTION
        "Indicates whether the EdgeServer is currently connected to
        this CoreServer" 
    ::= { csConnectivityEntry 4 }

csConTabTotalSentMessages OBJECT-TYPE
    SYNTAX          Counter32
    MAX-ACCESS      read-only
    STATUS          current
    DESCRIPTION
        "The total number of messages sent from the CoreServer
        to this EdgeServer" 
    ::= { csConnectivityEntry 5 }

csConTabSentCompressionRatio OBJECT-TYPE
    SYNTAX          Integer32 (0..100)
    UNITS           "%"
    MAX-ACCESS      read-only
    STATUS          current
    DESCRIPTION
        "The compression ratio (in %) of the messages sent from
        the CoreServer to this EdgeServer" 
    ::= { csConnectivityEntry 6 }

csConTabTotalReceivedMessages OBJECT-TYPE
    SYNTAX          Counter32
    MAX-ACCESS      read-only
    STATUS          current
    DESCRIPTION
        "The total number of messages received by the CoreServer
        from this EdgeServer" 
    ::= { csConnectivityEntry 7 }

csConTabReceivedCompressionRatio OBJECT-TYPE
    SYNTAX          Integer32 (0..100)
    UNITS           "%"
    MAX-ACCESS      read-only
    STATUS          current
    DESCRIPTION
        "The compression ratio (in %) of the messages received by
        the CoreServer from this EdgeServer" 
    ::= { csConnectivityEntry 8 }

csConTabTotalSentKBytes OBJECT-TYPE
    SYNTAX          Unsigned32
    UNITS           "KB"
    MAX-ACCESS      read-only
    STATUS          current
    DESCRIPTION
        "The total number of kilobytes sent from the CoreServer to
        this EdgeServer" 
    ::= { csConnectivityEntry 9 }

csConTabTotalReceivedKBytes OBJECT-TYPE
    SYNTAX          Unsigned32
    UNITS           "KB"
    MAX-ACCESS      read-only
    STATUS          current
    DESCRIPTION
        "The total number of kilobytes received by the CoreServer from
        this EdgeServer" 
    ::= { csConnectivityEntry 10 }

csDeviceName OBJECT-TYPE
    SYNTAX          OCTET STRING
    MAX-ACCESS      read-only
    STATUS          current
    DESCRIPTION
        "The network interface card inside the appliance used by
        the CoreServer (ETH0 or ETH1)" 
    ::= { csState 2 }

csWINS OBJECT-TYPE
    SYNTAX          OCTET STRING
    MAX-ACCESS      read-only
    STATUS          current
    DESCRIPTION
        "The WINS server defined for this CoreServer (if any)" 
    ::= { csState 3 }

csCIFSServersTable OBJECT-TYPE
    SYNTAX          SEQUENCE OF CsCIFSServersEntry 
    MAX-ACCESS      not-accessible
    STATUS          current
    DESCRIPTION
        "A table listing all the CIFS file servers exported by this CoreServer"
    ::= { csState 4 }

csCIFSServersEntry OBJECT-TYPE
    SYNTAX          CsCIFSServersEntry
    MAX-ACCESS      not-accessible
    STATUS          current
    DESCRIPTION
        "A single entry in the CIFS server table"
    INDEX           { csCIFSServersTabIndex } 
    ::= { csCIFSServersTable 1 }

CsCIFSServersEntry ::= SEQUENCE {
        csCIFSServersTabIndex      Integer32,
        csCIFSServersTabServerName OCTET STRING
}

csCIFSServersTabIndex OBJECT-TYPE
    SYNTAX          Integer32 (1..1000)
    MAX-ACCESS      not-accessible
    STATUS          current
    DESCRIPTION
        "Index column - sequential line number in the table" 
    ::= { csCIFSServersEntry 1 }

csCIFSServersTabServerName OBJECT-TYPE
    SYNTAX          OCTET STRING
    MAX-ACCESS      read-only
    STATUS          current
    DESCRIPTION
        "Name of the CIFS server exported by this CoreServer" 
    ::= { csCIFSServersEntry 2 }

csNFSServersTable OBJECT-TYPE
    SYNTAX          SEQUENCE OF CsNFSServersEntry 
    MAX-ACCESS      not-accessible
    STATUS          current
    DESCRIPTION
        "A table listing all the NFS servers exported by this CoreServer"
    ::= { csState 5 }

csNFSServersEntry OBJECT-TYPE
    SYNTAX          CsNFSServersEntry
    MAX-ACCESS      not-accessible
    STATUS          current
    DESCRIPTION
        "A single entry in the NFS server table"
    INDEX           { csNFSServersTabIndex } 
    ::= { csNFSServersTable 1 }

CsNFSServersEntry ::= SEQUENCE {
        csNFSServersTabIndex      Integer32,
        csNFSServersTabServerName OCTET STRING,
        csNFSServersTabUseTCP     INTEGER,
        csNFSServersTabUseUDP     INTEGER
}

csNFSServersTabIndex OBJECT-TYPE
    SYNTAX          Integer32 (1..1000)
    MAX-ACCESS      not-accessible
    STATUS          current
    DESCRIPTION
        "Index column - sequential line number in the table" 
    ::= { csNFSServersEntry 1 }

csNFSServersTabServerName OBJECT-TYPE
    SYNTAX          OCTET STRING
    MAX-ACCESS      read-only
    STATUS          current
    DESCRIPTION
        "Name of the NFS server exported by this CoreServer" 
    ::= { csNFSServersEntry 2 }

csNFSServersTabUseTCP OBJECT-TYPE
    SYNTAX          INTEGER  {
                        no(0),
                        yes(1)
                    }
    MAX-ACCESS      read-only
    STATUS          current
    DESCRIPTION
        "Indicates whether this NFS server supports
        the TCP transport layer protocol" 
    ::= { csNFSServersEntry 3 }

csNFSServersTabUseUDP OBJECT-TYPE
    SYNTAX          INTEGER  {
                        no(0),
                        yes(1)
                    }
    MAX-ACCESS      read-only
    STATUS          current
    DESCRIPTION
        "Indicates whether this NFS server supports
        the UDP transport layer protocol" 
    ::= { csNFSServersEntry 4 }

csLogsTrap NOTIFICATION-TYPE
    STATUS          deprecated
    DESCRIPTION
        "The OID of trap messages related to the CoreServer.
        This object is deprecated in favor of acCsLogsTrap."
   ::= { coreServer 3 }

edgeServer OBJECT-IDENTITY
    STATUS          current
    DESCRIPTION
        "ActaStor EdgeServer-related information"
    ::= { actastor 4 }

esGeneral OBJECT-IDENTITY
    STATUS          current
    DESCRIPTION
        "EdgeServer general information"
    ::= { edgeServer 1 }

esIsConfigured OBJECT-TYPE
    SYNTAX          INTEGER  {
                        no(0),
                        yes(1)
                    }
    MAX-ACCESS      read-only
    STATUS          current
    DESCRIPTION
        "Indicates whether the EdgeServer component has been configured
        to run on this gateway" 
    ::= { esGeneral 1 }

esIsAlive OBJECT-TYPE
    SYNTAX          INTEGER  {
                        no(0),
                        yes(1)
                    }
    MAX-ACCESS      read-only
    STATUS          current
    DESCRIPTION
        "Indicates whether the EdgeServer component is currently
        running on this gateway" 
    ::= { esGeneral 2 }

esUpTime OBJECT-TYPE
    SYNTAX          TimeTicks
    MAX-ACCESS      read-only
    STATUS          current
    DESCRIPTION
        "The elapsed time since the EdgeServer was started" 
    ::= { esGeneral 3 }

esState OBJECT-IDENTITY
    STATUS          current
    DESCRIPTION
        "The current run-time state of the EdgeServer"
    ::= { edgeServer 2 }

esConnectivityTable OBJECT-TYPE
    SYNTAX          SEQUENCE OF EsConnectivityEntry 
    MAX-ACCESS      not-accessible
    STATUS          current
    DESCRIPTION
        "A table describing the current state of CoreServer
        connections to this EdgeServer"
    ::= { esState 1 }

esConnectivityEntry OBJECT-TYPE
    SYNTAX          EsConnectivityEntry
    MAX-ACCESS      not-accessible
    STATUS          current
    DESCRIPTION
        "A single entry in the connection table - denoting
        a specific CoreServer"
    INDEX           { esConTabIndex } 
    ::= { esConnectivityTable 1 }

EsConnectivityEntry ::= SEQUENCE {
        esConTabIndex                    Integer32,
        esConTabClusterID                Integer32,
        esConTabClusterName              OCTET STRING,
        esConTabIsConnected              INTEGER,
        esConTabTotalSentMessages        Counter32,
        esConTabSentCompressionRatio     Integer32,
        esConTabTotalReceivedMessages    Counter32,
        esConTabReceivedCompressionRatio Integer32,
        esConTabTotalSentKBytes          Unsigned32,
        esConTabTotalReceivedKBytes      Unsigned32
}

esConTabIndex OBJECT-TYPE
    SYNTAX          Integer32 (1..1000)
    MAX-ACCESS      not-accessible
    STATUS          current
    DESCRIPTION
        "Index column - sequential line number in the table" 
    ::= { esConnectivityEntry 1 }

esConTabClusterID OBJECT-TYPE
    SYNTAX          Integer32 (0..2147483647)
    MAX-ACCESS      read-only
    STATUS          current
    DESCRIPTION
        "ID of the CoreServer cluster to which this CoreServer belongs" 
    ::= { esConnectivityEntry 2 }

esConTabClusterName OBJECT-TYPE
    SYNTAX          OCTET STRING
    MAX-ACCESS      read-only
    STATUS          current
    DESCRIPTION
        "Name of the CoreServer cluster to which this CoreServer belongs" 
    ::= { esConnectivityEntry 3 }

esConTabIsConnected OBJECT-TYPE
    SYNTAX          INTEGER  {
                        no(0),
                        yes(1)
                    }
    MAX-ACCESS      read-only
    STATUS          current
    DESCRIPTION
        "Indicates whether the CoreServer is currently connected
        to this EdgeServer" 
    ::= { esConnectivityEntry 4 }

esConTabTotalSentMessages OBJECT-TYPE
    SYNTAX          Counter32
    MAX-ACCESS      read-only
    STATUS          current
    DESCRIPTION
        "The total number of messasges sent from the EdgeServer to
        this CoreServer" 
    ::= { esConnectivityEntry 5 }

esConTabSentCompressionRatio OBJECT-TYPE
    SYNTAX          Integer32 (0..100)
    UNITS           "%"
    MAX-ACCESS      read-only
    STATUS          current
    DESCRIPTION
        "The compression ratio (in %) of the messages sent from the
        EdgeServer to this CoreServer" 
    ::= { esConnectivityEntry 6 }

esConTabTotalReceivedMessages OBJECT-TYPE
    SYNTAX          Counter32
    MAX-ACCESS      read-only
    STATUS          current
    DESCRIPTION
        "The total number of messages received by the EdgeServer
        from this CoreServer" 
    ::= { esConnectivityEntry 7 }

esConTabReceivedCompressionRatio OBJECT-TYPE
    SYNTAX          Integer32 (0..100)
    UNITS           "%"
    MAX-ACCESS      read-only
    STATUS          current
    DESCRIPTION
        "The compression ratio (in %) of the messages received by
        the EdgeServer from this CoreServer" 
    ::= { esConnectivityEntry 8 }

esConTabTotalSentKBytes OBJECT-TYPE
    SYNTAX          Unsigned32
    UNITS           "KB"
    MAX-ACCESS      read-only
    STATUS          current
    DESCRIPTION
        "The total number of kilobytes sent from the EdgeServer
        to this CoreServer" 
    ::= { esConnectivityEntry 9 }

esConTabTotalReceivedKBytes OBJECT-TYPE
    SYNTAX          Unsigned32
    UNITS           "KB"
    MAX-ACCESS      read-only
    STATUS          current
    DESCRIPTION
        "The total number of kilobytes received by
        the EdgeServer from this CoreServer" 
    ::= { esConnectivityEntry 10 }

esCIFSInfo OBJECT-IDENTITY
    STATUS          current
    DESCRIPTION
        "EdgeServer CIFS (Windows) protocol information"
    ::= { esState 2 }

esTotalBytesRead OBJECT-TYPE
    SYNTAX          Unsigned32
    UNITS           "KB"
    MAX-ACCESS      read-only
    STATUS          current
    DESCRIPTION
        "The total number of kilobytes read by clients from
        the EdgeServer (via cache or remotely) using the CIFS protocol" 
    ::= { esCIFSInfo 1 }

esTotalWrittenBytes OBJECT-TYPE
    SYNTAX          Unsigned32
    UNITS           "KB"
    MAX-ACCESS      read-only
    STATUS          current
    DESCRIPTION
        "The total number of kilobytes written to
        the EdgeServer using the CIFS protocol" 
    ::= { esCIFSInfo 2 }

esRemoteRequestCount OBJECT-TYPE
    SYNTAX          Counter32
    MAX-ACCESS      read-only
    STATUS          current
    DESCRIPTION
        "The total number of remote synchronous CIFS requests
        sent to the CoreServer" 
    ::= { esCIFSInfo 3 }

esLocalRequestCount OBJECT-TYPE
    SYNTAX          Counter32
    MAX-ACCESS      read-only
    STATUS          current
    DESCRIPTION
        "The total number of CIFS requests the EdgeServer handled locally
        or sent asynchronously to the CoreServer" 
    ::= { esCIFSInfo 4 }

esTotalRemoteTime OBJECT-TYPE
    SYNTAX          TimeTicks
    MAX-ACCESS      read-only
    STATUS          current
    DESCRIPTION
        "The total duration of all remote synchronous CIFS requests
        sent to the CoreServer" 
    ::= { esCIFSInfo 5 }

esTotalLocalTime OBJECT-TYPE
    SYNTAX          TimeTicks
    MAX-ACCESS      read-only
    STATUS          current
    DESCRIPTION
        "The total duration of all CIFS requests to
        the EdgeServer (handled either locally or asynchronously)" 
    ::= { esCIFSInfo 6 }

esConnectedSessionCount OBJECT-TYPE
    SYNTAX          Integer32 (0..1000)
    MAX-ACCESS      read-only
    STATUS          current
    DESCRIPTION
        "The number of currently connected CIFS sessions" 
    ::= { esCIFSInfo 7 }

esCifsOpenFiles OBJECT-TYPE
    SYNTAX          Integer32 (0..1000000)
    MAX-ACCESS      read-only
    STATUS          current
    DESCRIPTION
        "The number of currently open CIFS files" 
    ::= { esCIFSInfo 8 }

esCacheInfo OBJECT-IDENTITY
    STATUS          current
    DESCRIPTION
        "EdgeServer cache state information"
    ::= { esState 4 }

esMaxCacheVolume OBJECT-TYPE
    SYNTAX          Unsigned32
    UNITS           "KB"
    MAX-ACCESS      read-only
    STATUS          current
    DESCRIPTION
        "The maximum disk space (in KB) allocated for data in
        the EdgeServer cache" 
    ::= { esCacheInfo 1 }

esCurrentCacheVolume OBJECT-TYPE
    SYNTAX          Unsigned32
    UNITS           "KB"
    MAX-ACCESS      read-only
    STATUS          current
    DESCRIPTION
        "The amount of disk space currently being used for data
        in the EdgeServer cache" 
    ::= { esCacheInfo 2 }

esMaxCacheResources OBJECT-TYPE
    SYNTAX          Integer32 (0..2147483647)
    MAX-ACCESS      read-only
    STATUS          current
    DESCRIPTION
        "The maximum number of cache resources (files and directories)
        supported by the EdgeServer cache, regardless of the size of 
        these resources" 
    ::= { esCacheInfo 3 }

esCurrentCacheResources OBJECT-TYPE
    SYNTAX          Integer32 (0..2147483647)
    MAX-ACCESS      read-only
    STATUS          current
    DESCRIPTION
        "The current number of cache resources (files and directories)
        held in the EdgeServer cache" 
    ::= { esCacheInfo 4 }

esResourceEvictedNum OBJECT-TYPE
    SYNTAX          Counter32
    MAX-ACCESS      read-only
    STATUS          current
    DESCRIPTION
        "The number of cache resources (files and directories) that have been
        evicted from the cache since the EdgeServer started" 
    ::= { esCacheInfo 5 }

esLastEvictedTime OBJECT-TYPE
    SYNTAX          TimeTicks
    MAX-ACCESS      read-only
    STATUS          current
    DESCRIPTION
        "The time cache resources (files and directories) were last evicted
        from the EdgeServer cache. 00:00 is displayed if no cache resources
        have been evicted since the EdgeServer started." 
    ::= { esCacheInfo 6 }

esVolHiWatermark OBJECT-TYPE
    SYNTAX          Integer32 (0..100)
    UNITS           "%"
    MAX-ACCESS      read-only
    STATUS          current
    DESCRIPTION
        "The disk-usage percentage that triggers the eviction of
        resources from the EdgeServer cache" 
    ::= { esCacheInfo 7 }

esVolLoWatermark OBJECT-TYPE
    SYNTAX          Integer32 (0..100)
    UNITS           "%"
    MAX-ACCESS      read-only
    STATUS          current
    DESCRIPTION
        "The target disk-usage percentage to be reached via cache eviction
        when triggered by esVolHiWatermark. When this low watermark 
        is reached, cache eviction stops." 
    ::= { esCacheInfo 8 }

esAmntHiWatermark OBJECT-TYPE
    SYNTAX          Integer32 (0..100)
    UNITS           "%"
    MAX-ACCESS      read-only
    STATUS          current
    DESCRIPTION
        "The percentage of maximum cache resources
        (defined by esMaxCacheResources) that triggers the eviction
        of resources from the EdgeServer cache" 
    ::= { esCacheInfo 9 }

esAmntLoWatermark OBJECT-TYPE
    SYNTAX          Integer32 (0..100)
    UNITS           "%"
    MAX-ACCESS      read-only
    STATUS          current
    DESCRIPTION
        "The target percetage of total cache resources
        (defined by esMaxCacheResources) to be reached 
        via cache eviction when triggered by esAmntHiWatermark. 
        When this low watermark is reached, cache eviction stops." 
    ::= { esCacheInfo 10 }

esEvictedAge OBJECT-TYPE
    SYNTAX          TimeTicks
    MAX-ACCESS      read-only
    STATUS          current
    DESCRIPTION
        "The amount of time spent in the EdgeServer cache by the resource
        that was last evicted. If this amount is too short or too long,
        it is recommended to modify the size of the cache." 
    ::= { esCacheInfo 11 }

esEvictedLastAccess OBJECT-TYPE
    SYNTAX          OCTET STRING
    MAX-ACCESS      read-only
    STATUS          current
    DESCRIPTION
        "The time when the resource last evicted from the EdgeServer
        cache was last accessed" 
    ::= { esCacheInfo 12 }

esLogsTrap NOTIFICATION-TYPE
    STATUS          deprecated
    DESCRIPTION
        "The OID of trap messages related to the EdgeServer.
        This object is deprecated in favor of acEsLogsTrap."
   ::= { edgeServer 3 }

cifsAO OBJECT-IDENTITY
    STATUS          current
    DESCRIPTION
        "CIFS AO-related information"
    ::= { actastor 6 }

cfGeneral OBJECT-IDENTITY
    STATUS          current
    DESCRIPTION
        "CIFS AO general information"
    ::= { cifsAO 1 }

cfIsConfigured OBJECT-TYPE
    SYNTAX          INTEGER  {
                        no(0),
                        yes(1)
                    }
    MAX-ACCESS      read-only
    STATUS          current
    DESCRIPTION
        "Indicates whether CIFS AO has been configured to run
        on this WAE" 
    ::= { cfGeneral 1 }

cfIsAlive OBJECT-TYPE
    SYNTAX          INTEGER  {
                        no(0),
                        yes(1)
                    }
    MAX-ACCESS      read-only
    STATUS          current
    DESCRIPTION
        "Indicates whether CIFS AO is currently running on this WAE" 
    ::= { cfGeneral 2 }

cfUpTime OBJECT-TYPE
    SYNTAX          TimeTicks
    MAX-ACCESS      read-only
    STATUS          current
    DESCRIPTION
        "Elapsed time since the CIFS AO was started" 
    ::= { cfGeneral 3 }

cfState OBJECT-IDENTITY
    STATUS          current
    DESCRIPTION
        "Current run-time state of CIFS AO"
    ::= { cifsAO 2 }

cfCIFSInfo OBJECT-IDENTITY
    STATUS          current
    DESCRIPTION
        "CIFS AO - CIFS (Windows) protocol information"
    ::= { cfState 1 }

cfTotalBytesRead OBJECT-TYPE
    SYNTAX          Unsigned32
    UNITS           "KB"
    MAX-ACCESS      read-only
    STATUS          current
    DESCRIPTION
        "Total number of kilobytes read by clients from the
        Client-side (via cache or remotely) using CIFS AO" 
    ::= { cfCIFSInfo 1 }

cfTotalWrittenBytes OBJECT-TYPE
    SYNTAX          Unsigned32
    UNITS           "KB"
    MAX-ACCESS      read-only
    STATUS          current
    DESCRIPTION
        "Total number of kilobytes written to the Client-side using the
        CIFS AO" 
    ::= { cfCIFSInfo 2 }

cfRemoteRequestCount OBJECT-TYPE
    SYNTAX          Counter32
    MAX-ACCESS      read-only
    STATUS          current
    DESCRIPTION
        "Total number of remote requests processed by CIFS AO" 
    ::= { cfCIFSInfo 3 }

cfLocalRequestCount OBJECT-TYPE
    SYNTAX          Counter32
    MAX-ACCESS      read-only
    STATUS          current
    DESCRIPTION
        "Total number of local requests processed by CIFS AO" 
    ::= { cfCIFSInfo 4 }

cfTotalRemoteTime OBJECT-TYPE
    SYNTAX          TimeTicks
    MAX-ACCESS      read-only
    STATUS          current
    DESCRIPTION
        "Total duration of time taken by CIFS AO to process all remote
        requests" 
    ::= { cfCIFSInfo 5 }

cfTotalLocalTime OBJECT-TYPE
    SYNTAX          TimeTicks
    MAX-ACCESS      read-only
    STATUS          current
    DESCRIPTION
        "Total duration of time taken by CIFS AO to process all local
        requests" 
    ::= { cfCIFSInfo 6 }

cfConnectedSessionCount OBJECT-TYPE
    SYNTAX          Integer32 (0..100000)
    MAX-ACCESS      read-only
    STATUS          current
    DESCRIPTION
        "Number of currently connected CIFS sessions" 
    ::= { cfCIFSInfo 7 }

cfCifsOpenFiles OBJECT-TYPE
    SYNTAX          Integer32 (0..100000)
    MAX-ACCESS      read-only
    STATUS          current
    DESCRIPTION
        "Number of currently open CIFS files" 
    ::= { cfCIFSInfo 8 }

cfCacheInfo OBJECT-IDENTITY
    STATUS          current
    DESCRIPTION
        "CIFS AO cache state information"
    ::= { cfState 2 }

cfMaxCacheVolume OBJECT-TYPE
    SYNTAX          Unsigned32
    UNITS           "KB"
    MAX-ACCESS      read-only
    STATUS          current
    DESCRIPTION
        "Maximum disk space (in KB) allocated for data in the CIFS AO
        cache" 
    ::= { cfCacheInfo 1 }

cfCurrentCacheVolume OBJECT-TYPE
    SYNTAX          Unsigned32
    UNITS           "KB"
    MAX-ACCESS      read-only
    STATUS          current
    DESCRIPTION
        "Amount of disk space currently being used for data in the CIFS
        AO cache" 
    ::= { cfCacheInfo 2 }

cfMaxCacheResources OBJECT-TYPE
    SYNTAX          Integer32 (0..2147483647)
    MAX-ACCESS      read-only
    STATUS          current
    DESCRIPTION
        "Maximum number of cache resources (files and directories)
        supported by the CIFS AO cache, regardless of the size of these
        resources" 
    ::= { cfCacheInfo 3 }

cfCurrentCacheResources OBJECT-TYPE
    SYNTAX          Integer32 (0..2147483647)
    MAX-ACCESS      read-only
    STATUS          current
    DESCRIPTION
        "Current number of cache resources (files and directories) held
        in the CIFS AO cache" 
    ::= { cfCacheInfo 4 }

cfResourceEvictedNum OBJECT-TYPE
    SYNTAX          Counter32
    MAX-ACCESS      read-only
    STATUS          current
    DESCRIPTION
        "Number of cache resources (files and directories) that have
        been evicted from the cache since CIFS AO started" 
    ::= { cfCacheInfo 5 }

cfLastEvictedTime OBJECT-TYPE
    SYNTAX          TimeTicks
    MAX-ACCESS      read-only
    STATUS          current
    DESCRIPTION
        "Time when cache resources (files and directories)
        were last evicted from the CIFS AO cache. N/A is 
        displayed if no cache resources have been evicted 
        since CIFS AO started" 
    ::= { cfCacheInfo 6 }

cfVolHiWatermark OBJECT-TYPE
    SYNTAX          Integer32 (0..100)
    UNITS           "%"
    MAX-ACCESS      read-only
    STATUS          current
    DESCRIPTION
        "Disk-usage percentage that triggers the eviction of resources
        from the CIFS AO cache" 
    ::= { cfCacheInfo 7 }

cfVolLoWatermark OBJECT-TYPE
    SYNTAX          Integer32 (0..100)
    UNITS           "%"
    MAX-ACCESS      read-only
    STATUS          current
    DESCRIPTION
        "Target disk-usage percentage to be reached via cache eviction
        when triggered by cfVolHiWatermark. When this low watermark is
        reached, cache eviction stops" 
    ::= { cfCacheInfo 8 }

cfAmntHiWatermark OBJECT-TYPE
    SYNTAX          Integer32 (0..100)
    UNITS           "%"
    MAX-ACCESS      read-only
    STATUS          current
    DESCRIPTION
        "Percentage of maximum cache resources (defined by
        cfMaxCacheResources) that triggers the eviction of resources
        from the CIFS AO cache" 
    ::= { cfCacheInfo 9 }

cfAmntLoWatermark OBJECT-TYPE
    SYNTAX          Integer32 (0..100)
    UNITS           "%"
    MAX-ACCESS      read-only
    STATUS          current
    DESCRIPTION
        "Target percetage of maximum cache resources (defined by
        cfMaxCacheResources) to be reached via cache eviction when
        triggered by cfAmntHiWatermark. When this low watermark is
        reached, cache eviction stops" 
    ::= { cfCacheInfo 10 }

cfEvictedAge OBJECT-TYPE
    SYNTAX          TimeTicks
    MAX-ACCESS      read-only
    STATUS          current
    DESCRIPTION
        "Amount of time spent in the CIFS AO cache by the resource that
        was last evicted. If this amount is too short or too long, it is
        recommended to modify the size of the cache" 
    ::= { cfCacheInfo 11 }

cfEvictedLastAccess OBJECT-TYPE
    SYNTAX          OCTET STRING
    MAX-ACCESS      read-only
    STATUS          current
    DESCRIPTION
        "Time when the resource last evicted from the CIFS AO cache was
        last accessed" 
    ::= { cfCacheInfo 12 }

notificationsInfo OBJECT-IDENTITY
    STATUS          current
    DESCRIPTION
        "ActaStor notification related information"
    ::= { actastor 5 }

acLogSeverity OBJECT-TYPE
    SYNTAX          INTEGER  {
                        fatal(1),
                        error(2),
                        warning(3),
                        info(4),
                        debug(5)
                    }
    MAX-ACCESS      accessible-for-notify
    STATUS          current
    DESCRIPTION
        "The severity level of the actastor log message" 
    ::= { notificationsInfo 1 }

acLogMsgText OBJECT-TYPE
    SYNTAX          DisplayString (SIZE  (0..255))
    MAX-ACCESS      accessible-for-notify
    STATUS          current
    DESCRIPTION
        "The actastor log message text" 
    ::= { notificationsInfo 2 }

acCsLogsTrap NOTIFICATION-TYPE
    OBJECTS         {
                        acLogSeverity,
                        acLogMsgText
                    }
    STATUS          current
    DESCRIPTION
        "This trap indicates that the CoreServer has generated a
        log message.  This object supersedes mgrLogsTrap"
   ::= { acNotifications 0 }

acMgrLogsTrap NOTIFICATION-TYPE
    OBJECTS         {
                        acLogSeverity,
                        acLogMsgText
                    }
    STATUS          current
    DESCRIPTION
        "This trap indicates that the ManagerServer has generated a
        log message. This object supersedes mgrLogsTrap"
   ::= { acNotifications 1 }

acEsLogsTrap NOTIFICATION-TYPE
    OBJECTS         {
                        acLogSeverity,
                        acLogMsgText
                    }
    STATUS          current
    DESCRIPTION
        "This trap indicates that the EdgeServer has generated a
        log message. This object supersedes esLogsTrap"
   ::= { acNotifications 2 }

actastorGroups OBJECT-IDENTITY
    STATUS          current
    DESCRIPTION
        "ActaStor object groups"
    ::= { actona 2 }

generalGroup OBJECT-GROUP
    OBJECTS         {
                        actastorVersion,
                        buildString,
                        email,
                        isValid,
                        daysLeft
                    }
    STATUS          current
    DESCRIPTION
        "General information group"
    ::= { actastorGroups 1 }

managerGroup OBJECT-GROUP
    OBJECTS         { mgrCentralServerHost }
    STATUS          current
    DESCRIPTION
        "Manager group"
    ::= { actastorGroups 2 }

coreServerGroup OBJECT-GROUP
    OBJECTS         {
                        csDeviceName,
                        csIsConfigured,
                        csIsAlive,
                        csUpTime,
                        csWINS,
                        csConTabClusterID,
                        csConTabClusterName,
                        csConTabIsConnected,
                        csConTabTotalSentMessages,
                        csConTabSentCompressionRatio,
                        csConTabTotalReceivedMessages,
                        csConTabReceivedCompressionRatio,
                        csConTabTotalSentKBytes,
                        csConTabTotalReceivedKBytes,
                        csCIFSServersTabServerName,
                        csNFSServersTabServerName,
                        csNFSServersTabUseTCP,
                        csNFSServersTabUseUDP
                    }
    STATUS          current
    DESCRIPTION
        "CoreServer group"
    ::= { actastorGroups 3 }

edgeServerGroup OBJECT-GROUP
    OBJECTS         {
                        esIsConfigured,
                        esIsAlive,
                        esUpTime,
                        esTotalBytesRead,
                        esTotalWrittenBytes,
                        esRemoteRequestCount,
                        esLocalRequestCount,
                        esConnectedSessionCount,
                        esCifsOpenFiles,
                        esMaxCacheVolume,
                        esCurrentCacheVolume,
                        esMaxCacheResources,
                        esCurrentCacheResources,
                        esTotalRemoteTime,
                        esTotalLocalTime,
                        esConTabClusterID,
                        esConTabClusterName,
                        esConTabIsConnected,
                        esConTabTotalSentMessages,
                        esConTabSentCompressionRatio,
                        esConTabTotalReceivedMessages,
                        esConTabReceivedCompressionRatio,
                        esConTabTotalSentKBytes,
                        esConTabTotalReceivedKBytes,
                        esResourceEvictedNum,
                        esLastEvictedTime,
                        esVolHiWatermark,
                        esVolLoWatermark,
                        esAmntHiWatermark,
                        esAmntLoWatermark,
                        esEvictedAge,
                        esEvictedLastAccess
                    }
    STATUS          current
    DESCRIPTION
        "EdgeServer group"
    ::= { actastorGroups 4 }

logNotificationsGroup NOTIFICATION-GROUP
   NOTIFICATIONS    {
                        csLogsTrap,
                        esLogsTrap,
                        mgrLogsTrap
                    }
    STATUS          deprecated
    DESCRIPTION
        "Log message traps group"
    ::= { actastorGroups 5 }

logNotificationsGroupRev1 NOTIFICATION-GROUP
   NOTIFICATIONS    {
                        acCsLogsTrap,
                        acEsLogsTrap,
                        acMgrLogsTrap
                    }
    STATUS          current
    DESCRIPTION
        "Log message traps group"
    ::= { actastorGroups 6 }

acNotificationInfoGroup OBJECT-GROUP
    OBJECTS         {
                        acLogSeverity,
                        acLogMsgText
                    }
    STATUS          current
    DESCRIPTION
        "A collection of objects which provides info
        about notifications."
    ::= { actastorGroups 7 }

cifsAOGroup OBJECT-GROUP
    OBJECTS         {
                        cfIsConfigured,
                        cfIsAlive,
                        cfUpTime,
                        cfTotalBytesRead,
                        cfTotalWrittenBytes,
                        cfRemoteRequestCount,
                        cfLocalRequestCount,
                        cfTotalRemoteTime,
                        cfTotalLocalTime,
                        cfConnectedSessionCount,
                        cfCifsOpenFiles,
                        cfMaxCacheVolume,
                        cfCurrentCacheVolume,
                        cfMaxCacheResources,
                        cfCurrentCacheResources,
                        cfResourceEvictedNum,
                        cfLastEvictedTime,
                        cfVolHiWatermark,
                        cfVolLoWatermark,
                        cfAmntHiWatermark,
                        cfAmntLoWatermark,
                        cfEvictedAge,
                        cfEvictedLastAccess
                    }
    STATUS          current
    DESCRIPTION
        "CifsAO group"
    ::= { actastorGroups 9 }

END
