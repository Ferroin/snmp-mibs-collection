CISCO-DLSW-EXT-MIB DEFINITIONS ::= BEGIN

IMPORTS
	MODULE-IDENTITY,
	OBJECT-TYPE,
        NOTIFICATION-TYPE,
        TimeTicks
		FROM SNMPv2-SMI
	MODULE-COMPLIANCE,
	OBJECT-GROUP
		FROM SNMPv2-CONF
	TruthValue,
        TEXTUAL-CONVENTION,
        DisplayString
		FROM SNMPv2-TC
        InterfaceIndex
                FROM IF-MIB
	dlswTConnConfigEntry,
	dlswTConnOperEntry,
        dlswTConnTcpConfigEntry,
        dlswIfEntry,
        dlswCircuitEntry,
        dlswTConnConfigIndex,
        DlcType,
        TAddress,
        MacAddressNC,
        LFSize,
        dlswTConnOperState,
        dlswCircuitState
		FROM DLSW-MIB
        DlciNumber
                FROM CISCO-FRAME-RELAY-MIB
        SAPType
                FROM CISCO-TC
	ciscoMgmt
		FROM CISCO-SMI;

ciscoDlswExtMIB MODULE-IDENTITY
    LAST-UPDATED "9703110000Z"
    ORGANIZATION "Cisco IBU Engineering Working Group"
    CONTACT-INFO
          "       Cisco Systems
                  Customer Service

          Postal: 170 W. Tasman Drive
                  San Jose, CA 95134
                  USA

                  Tel: +1 800 553-NETS
          E-mail: cs-dlsw@cisco.com"
    DESCRIPTION
            "The MIB module for management of Cisco specific Data Link
            Switching protocol enhancements.  DLSw is described in 
            RFC 1795 and RFC 2024.

            DLSw+ Defined

            Data link switching Plus (DLSw+) is a means of transporting
            Systems Network Architecture (SNA) and NetBIOS traffic over
            an IP network. The end systems can attach to the network over
            Token Ring, Ethernet, Synchronous Data Link Control
            (SDLC) protocol, or Qualified Logical Link Control (QLLC).
            DLSw+ switches between diverse media, and locally terminates
            the data links, keeping acknowledgments, keepalives, and polling
            off of the WAN. Local termination of data links also
            eliminates data link control time-outs that can occur during
            transient network congestion or when rerouting around failed
            links. Finally, DLSw+ provides a mechanism for dynamically
            searching a network for SNA or NetBIOS resources and
            includes caching algorithms that minimize the broadcast traffic
            required. 

            In this document, DLSw+ routers are referred to as
            peers, or partners. The connection between two DLSw+
            routers is referred to as a peer connection. A DLSw circuit is
            comprised of the data link control connection between the
            originating end system and the originating router, the connection
            between the two routers (typically a TCP connection), and
            the data link control connection between the target router and
            the target end system. A single peer connection can carry
            multiple circuits.

            The transport connection between DLSw+ routers can vary according
            to the needs of the network and is not tied to TCP/IP
            as the DLSw standard is. Cisco supports four different transport
            protocols between DLSw+ routers:

            TCP/IP-for transport of SNA and NetBIOS traffic across WANs where
            local acknowledgment is required to minimize
            unnecessary traffic and prevent data-link control timeouts and
            where non-disruptive rerouting around link failures is
            critical. This transport option is required when DLSw+ is
            operating in DLSw standards mode. 

            FST/IP-for transport across WANs with an arbitrary topology and
            with sufficient bandwidth to accommodate SNA
            and NetBIOS traffic. This solution allows for rerouting around
            link failures, but recovery may be disruptive depending
            on the time required to find an alternate path. This option does
            not support local acknowledgment of frames. 

            Direct-encapsulation for transport across a point-to-point or
            Frame Relay connection where the benefits of an
            arbitrary topology are not important and where nondisruptive
            rerouting around link failures is not required. This option
            does not support local acknowledgment of frames. 

            DLSw Lite-also known as Logical Link Control, Type2 (LLC2)
            encapsulation -for transport across a point-to-point
            connection (currently only Frame Relay is supported) where
            local acknowledgment and reliable transport are
            important, but where nondisruptive rerouting around link
            failures is not required. DLSw Lite uses RFC 1490
            encapsulation of LLC2."
    REVISION		  "9703110000Z"
    DESCRIPTION
            "Initial version of this MIB module."
    ::= { ciscoMgmt 74 }

ciscoDlswExtMIBObjects OBJECT IDENTIFIER ::= { ciscoDlswExtMIB 1 }

cdeDomains     OBJECT IDENTIFIER ::= { ciscoDlswExtMIBObjects 1 }
cdeNode        OBJECT IDENTIFIER ::= { ciscoDlswExtMIBObjects 2 }
cdeTConn       OBJECT IDENTIFIER ::= { ciscoDlswExtMIBObjects 3 }
cdeInterface   OBJECT IDENTIFIER ::= { ciscoDlswExtMIBObjects 4 }
cdeCircuit     OBJECT IDENTIFIER ::= { ciscoDlswExtMIBObjects 5 }
cdeFast        OBJECT IDENTIFIER ::= { ciscoDlswExtMIBObjects 6 }
cdeTrapControl OBJECT IDENTIFIER ::= { ciscoDlswExtMIBObjects 7 }

TDomainType ::= TEXTUAL-CONVENTION
    STATUS  current
    DESCRIPTION
       "The type of DLSw encapsulation in use on this peer connection."
    SYNTAX     INTEGER  {
        tcp                     (1),
        fst                     (2),
        directHdlc              (3),
        directFrameRelay        (4),
        llc2                    (5)
    }

Cost ::= TEXTUAL-CONVENTION
    STATUS  current
    DESCRIPTION
       "Allows a cost to be assigned to a peer.  
        If an end station can be reached through more
        than one peer, the cost of each peer will be considered when
        a circuit is established.
        A lower cost indicates that peer will be the
        preferred choice if there is more than one path to the
        destination."
    SYNTAX     INTEGER (1..5)

KeepaliveInterval ::= TEXTUAL-CONVENTION
    STATUS  current
    DESCRIPTION
       "The keepalive parameter refers to how often DLSw peers
        send peer keep alives to each other.  These periodic messages
        allow DLSw to keep track of the state of all peers.
        The keepalive interval is measured in seconds.
        If set to zero, no keepalives are sent."
    SYNTAX     INTEGER (0..1200)

TCPQueueMax ::= TEXTUAL-CONVENTION
    STATUS  current
    DESCRIPTION
       "For DLSw over TCP encapsulation, packets may be queued
        due to congestion of the TCP network.  The TCPQueueMax
        is used to set the output queue maximum of the underlying
        TCP connection."
    SYNTAX     INTEGER (25..2000)

-- *******************************************************************
-- DLSw Transport Domain definitions
-- *******************************************************************

-- The Domain definition allows the DLSw peer encapsulation method
-- to be distinguished for conceptual rows within the peer tables
-- defined in both CISCO-DLSW-EXT-MIB and DLSW-MIB (RFC 2024).

-- These tables include dlswTConnConfigTable and dlswTConnOperTable
-- in DLSW-MIB (RFC 2024), which are augmented in this MIB 
-- by cdeTConnConfigTable and cdeTConnOperTable, respectively.
--
-- The domain is simply an Object Identifier of the table which
-- provides specific information about that type of peer encapsulation.
-- It allows a management station to obtain further information about
-- a conceptual row in the TConn table, since the domain specifies
-- the type of encapsulation used by the peer.
--
-- DLSW-MIB defines only a dlswTCPDomain which represents 
-- a peer encapsulation type of TCP/IP.

-- An additional peer encapsulation type is FST, Fast Sequenced Transport,
-- and its domain is defined here.  

cdeFSTDomain               OBJECT IDENTIFIER ::= { cdeDomains 1 }

-- Another type of peer encapsulation is DLSw over Direct interface
-- using hdlc, and its domain is defined here.

cdeDirectHdlcDomain        OBJECT IDENTIFIER ::= { cdeDomains 2 }

-- Another type of peer encapsulation is DLSw over Direct interface
-- using Frame Relay, and its domain is defined here.

cdeDirectFrameRelayDomain  OBJECT IDENTIFIER ::= { cdeDomains 3 }

-- another type of peer encapsulation is DLSw Lite-also known as 
-- Logical Link Control, Type2 (LLC2), and its domain is defined here. 

cdeLlc2Domain              OBJECT IDENTIFIER ::= { cdeDomains 4 }

--
-- Cisco DLSw Extension Node Objects
--

cdeNodeTAddr  OBJECT-TYPE
    SYNTAX     TAddress
    MAX-ACCESS read-write
    STATUS     current
    DESCRIPTION
       "The local peer IP address; required for Fast-Sequenced
        Transport (FST) and TCP.  If no local peer IP address
        is configured then this object will be the empty string."
    DEFVAL      { ''H }     -- the empty string
    ::= { cdeNode 1 }

cdeNodeGroup  OBJECT-TYPE
    SYNTAX     INTEGER (0..255)
    MAX-ACCESS read-write
    STATUS     current
    DESCRIPTION
       "Peer group number for this router.
        Peer groups are arbitrary groups of routers with one or
        more designated border peers.  Border peers form peer
        connections with every router in their group and with
        border peers in other groups. The role of a border peer
        is to forward explorers on behalf of other routers. 
        A value of zero means no group has been set and the
        DLSw is not a group member."
    DEFVAL      { 0 }
    ::= { cdeNode 2 }

cdeNodeBorder  OBJECT-TYPE
    SYNTAX     TruthValue
    MAX-ACCESS read-write
    STATUS     current
    DESCRIPTION
       "This variable indicates if this DLSw is capable of
        operating as a border peer.  True indicates that it is
        capable, false indicates that it is not.

        Border peers form peer connections with every router in
        their group and with border peers in other groups. The
        role of a border peer is to forward explorers on behalf
        of other DLSw routers."
    DEFVAL      { false }
    ::= { cdeNode 3 }

cdeNodeCost  OBJECT-TYPE
    SYNTAX     Cost
    MAX-ACCESS read-write
    STATUS     current
    DESCRIPTION
       "Peer cost advertised to remote peers in the capabilities
        exchange.  If an end station can be reached through more 
        than one peer, the cost of each peer will be considered when
        a circuit is established.  
        A lower cost indicates that peer will be the 
        preferred choice if there is more than one path to the
        destination.  A value of zero means no cost has been set
        and that cost will not be considered during circuit
        establishment."
    DEFVAL     { 3 }
    ::= { cdeNode 4 }

cdeNodeKeepaliveInterval  OBJECT-TYPE
    SYNTAX     KeepaliveInterval
    UNITS      "Seconds"
    MAX-ACCESS read-write
    STATUS     current
    DESCRIPTION
       "Default remote peer keepalive interval in seconds.
        The keepalive parameter refers to how often DLSw peers
        send peer keep alives to each other.  These periodic messages 
        allow DLSw to keep track of the state of all peers.
        If set to zero, no keepalives are sent."
    DEFVAL     { 30 }
    ::= { cdeNode 5 }

cdeNodePassiveConnect  OBJECT-TYPE
    SYNTAX     TruthValue
    MAX-ACCESS read-write
    STATUS     current
    DESCRIPTION
       "This variable indicates if DLSw will not initiate
        remote peer connections to configured peers.  True
        indicates that it will not initiate remote peer connections,
        false indicates that it will initiate remote peer connections.
        In other words a passive peer will wait for the remote peer
        to initiate a peer connection"
    DEFVAL      { false }
    ::= { cdeNode 6 }

cdeNodeBiuSegment  OBJECT-TYPE
    SYNTAX     TruthValue
    MAX-ACCESS read-write
    STATUS     current
    DESCRIPTION
       "This variable indicates if DLSw will spoof the maximum
        receivable Basic Information Unit (frame) size in XID so that
        each end station sends the largest frame it can.  True indicates
        that it will spoof, false indicates that it will not."
    DEFVAL      { false }
    ::= { cdeNode 7 }

cdeNodeInitPacingWindow  OBJECT-TYPE
    SYNTAX     INTEGER (1..2000)
    UNITS      "packets"
    MAX-ACCESS read-write
    STATUS     current
    DESCRIPTION
       "Initial pacing window size.  This is the starting size of the
        pacing window.  DLSw uses an adaptive pacing
        flow control algorithm that automatically adjusts to congestion
        levels in the network.  Pacing windows are used to control
        how many packets may be sent to a peer before acknowlegement."
    DEFVAL     { 20 }
    ::= { cdeNode 8 }

cdeNodeMaxPacingWindow  OBJECT-TYPE
    SYNTAX     INTEGER (1..2000)
    UNITS      "packets"
    MAX-ACCESS read-write
    STATUS     current
    DESCRIPTION
       "Maximum pacing window size.  This is the largest size that
        the pacing window will grow to.  DLSw uses an adaptive pacing
        flow control algorithm that automatically adjusts to congestion
        levels in the network.  Pacing windows are used to control
        how many packets may be sent to a peer before acknowlegement."
    DEFVAL     { 50 }
    ::= { cdeNode 9 }

cdeNodePromiscuous  OBJECT-TYPE
    SYNTAX     TruthValue
    MAX-ACCESS read-write
    STATUS     current
    DESCRIPTION
       "This variable indicates if DLSw will accept connections from
        non-configured remote peers.  Promiscuous routers will
        accept peer connection requests from routers that are
        not preconfigured.  This feature allows central site routers
        to remain unchanged when branch offices are added or deleted.
        It also minimizes required coordination of configurations.
        True indicates that it will accept connections,
        false indicates that it will not."
    DEFVAL     { false }
    ::= { cdeNode 10 }

cdeNodePromPeerDefaultsCost  OBJECT-TYPE
    SYNTAX     Cost
    MAX-ACCESS read-write
    STATUS     current
    DESCRIPTION
       "This variable indicates the cost that will be used with
        promiscuous peers.
        If an end station can be reached through more
        than one peer, the cost of each peer will be considered when
        a circuit is established.
        A lower cost indicates that peer will be the
        preferred choice if there is more than one path to the
        destination."
    DEFVAL     { 3 }
    ::= { cdeNode 11 }

cdeNodePromPeerDefaultsDestMac  OBJECT-TYPE
    SYNTAX     MacAddressNC
    MAX-ACCESS read-write
    STATUS     current
    DESCRIPTION
       "Permits the promiscuous peer connection to be established
        only when there is an explorer frame destined for the
        specified 48-bit MAC address.  If no default destination mac 
        is configured then this object will be the empty string."
    DEFVAL      { ''H }     -- the empty string
    ::= { cdeNode 12 }

cdeNodePromPeerDefaultsKeepaliveInterval  OBJECT-TYPE
    SYNTAX     KeepaliveInterval
    UNITS      "Seconds"
    MAX-ACCESS read-write
    STATUS     current
    DESCRIPTION
       "Default promiscuous peer keepalive interval in seconds.
        The keepalive parameter refers to how often DLSw peers
        send peer keep alives to each other.  These periodic messages
        allow DLSw to keep track of the state of all peers.
        If set to zero, no keepalives are sent."
    DEFVAL     { 30 }
    ::= { cdeNode 13 }

cdeNodePromPeerDefaultsLFSize  OBJECT-TYPE
    SYNTAX     LFSize
    UNITS      "bytes"
    MAX-ACCESS read-write
    STATUS     current
    DESCRIPTION
       "The default Largest Frame Size associated with the
        default promiscuous peer transport connection.
        In other words its the largest size of the INFO field
        (including DLC header, not including any MAC-level or framing
        octets)."
    DEFVAL     { lfs17749 }
    ::= { cdeNode 14 }

cdeNodePromPeerDefaultsTCPQueueMax  OBJECT-TYPE
    SYNTAX     TCPQueueMax
    UNITS      "packets"
    MAX-ACCESS read-write
    STATUS     current
    DESCRIPTION
       "Default promiscuous peer maximum output TCP queue size.
        For DLSw over TCP encapsulation, packets may be queued
        due to congestion of the TCP network.  This variable
        is used to set the output queue maximum of the underlying
        TCP connection, by default on a promiscuous
        peer transport connection."
    DEFVAL      { 200 }
    ::= { cdeNode 15 }

cdeNodePeerOnDemandDefaultsCost  OBJECT-TYPE
    SYNTAX     Cost
    MAX-ACCESS read-write
    STATUS     current
    DESCRIPTION
       "This variable indicates the cost that will be used with
        peer on demand peers.
        If an end station can be reached through more
        than one peer, the cost of each peer will be considered when
        a circuit is established.
        A lower cost indicates that peer will be the
        preferred choice if there is more than one path to the
        destination."
    DEFVAL     { 3 }
    ::= { cdeNode 16 }

cdeNodePeerOnDemandDefaultsFst  OBJECT-TYPE
    SYNTAX     TruthValue
    MAX-ACCESS read-write
    STATUS     current
    DESCRIPTION
       "This variable indicates if Fast-Sequenced Transport (FST)
        will be for peer on demand peers.  True indicates that
        FST will be used, false indicates that it will not."
    DEFVAL      { false }
    ::= { cdeNode 17 }

cdeNodePeerOnDemandDefaultsInactivityInterval  OBJECT-TYPE
    SYNTAX     INTEGER (0..1440)
    UNITS      "Minutes"
    MAX-ACCESS read-write
    STATUS     current
    DESCRIPTION
       "This variable indicates the length of time a peer on demand 
        connection can be idle before shutting down this peer
        on demand connection.  If set to zero, the peer on demand 
        connection will not be closed due to inactivity."
    DEFVAL     { 10 }
    ::= { cdeNode 18 }

cdeNodePeerOnDemandDefaultsKeepaliveInterval  OBJECT-TYPE
    SYNTAX     KeepaliveInterval
    UNITS      "Seconds"
    MAX-ACCESS read-write
    STATUS     current
    DESCRIPTION
       "Default peer on demand keepalive interval in seconds.
        The keepalive parameter refers to how often DLSw peers
        send peer keep alives to each other.  These periodic messages
        allow DLSw to keep track of the state of all peers.
        If set to zero, no keepalives are sent."
    DEFVAL     { 30 }
    ::= { cdeNode 19 }

cdeNodePeerOnDemandDefaultsLFSize  OBJECT-TYPE
    SYNTAX     LFSize
    MAX-ACCESS read-write
    STATUS     current
    DESCRIPTION
       "The default Largest Frame Size associated with the
        default peer on demand transport connections.
        In other words its the largest size of the INFO field
        (including DLC header, not including any MAC-level or framing
        octets)."
    DEFVAL     { lfs17749 }
    ::= { cdeNode 20 }

cdeNodePeerOnDemandDefaultsPriority  OBJECT-TYPE
    SYNTAX     TruthValue
    MAX-ACCESS read-write
    STATUS     current
    DESCRIPTION
       "This variable indicates if circuit prioritization will be used
        for peer-on-demand peers.  True indicates that circuit
        prioritization specified by the dlswCircuitPriority object
        in the DLSW-MIB (RFC 2024) will be used, false indicates that
        there will be no circuit prioritization."
    DEFVAL     { false }
    ::= { cdeNode 21 }

cdeNodePeerOnDemandDefaultsTCPQueueMax  OBJECT-TYPE
    SYNTAX     TCPQueueMax
    UNITS      "packets"
    MAX-ACCESS read-write
    STATUS     current
    DESCRIPTION
       "Default peer-on-demand Maximum output TCP queue size.
        For DLSw over TCP encapsulation, packets may be queued
        due to congestion of the TCP network.  This variable
        is used to set the output queue maximum of the underlying
        TCP connection, by default on a peer on demand 
        transport connection."
    DEFVAL     { 200 }
    ::= { cdeNode 22 }

--
-- Cisco DLSw Extension Transport Connection MIB-Group
--
-- an extended collection of objects providing information about
-- DLSw transport connections and peer associations

--
-- Cisco DLSw Extension Transport Connection Configuration Table
--

cdeTConnConfigTable OBJECT-TYPE
    SYNTAX     SEQUENCE OF CdeTConnConfigEntry
    MAX-ACCESS not-accessible
    STATUS     current
    DESCRIPTION
       "This table defines the peer transport connections
        that will be initiated or accepted by this
        DLSw.  Structure of masks allows wildcard
        definition for a collection of transport
        connections by a conceptual row.  For a
        specific transport connection, there may
        be multiple conceptual rows that match the
        transport address.  The `best' match will be
        the one to determine the characteristics
        of the transport connection.

        This table augments dlswTConnConfigTable."
    ::= { cdeTConn 1 }

cdeTConnConfigEntry OBJECT-TYPE
    SYNTAX     CdeTConnConfigEntry
    MAX-ACCESS not-accessible
    STATUS     current
    DESCRIPTION
       "A list of objects that define specific configuration for
        a DLSw peer transport connection." 
    AUGMENTS { dlswTConnConfigEntry } 
    ::= { cdeTConnConfigTable 1 }

CdeTConnConfigEntry ::= SEQUENCE {
    cdeTConnConfigTDomainType               TDomainType,
    cdeTConnConfigLocalAck                  TruthValue,
    cdeTConnConfigCost                      Cost,
    cdeTConnConfigLFSize                    LFSize,
    cdeTConnConfigKeepaliveInterval         KeepaliveInterval,
    cdeTConnConfigBackup                    TruthValue,
    cdeTConnConfigBackupTAddr               TAddress,
    cdeTConnConfigBackupLinger              TruthValue,
    cdeTConnConfigBackupLingerInterval      INTEGER,
    cdeTConnConfigPriority                  TruthValue,
    cdeTConnConfigDestMac                   MacAddressNC,
    cdeTConnConfigDynamic                   TruthValue,
    cdeTConnConfigDynamicNoLlc              INTEGER,
    cdeTConnConfigDynamicInactivityInterval INTEGER
}

cdeTConnConfigTDomainType  OBJECT-TYPE
    SYNTAX     TDomainType
    MAX-ACCESS read-create
    STATUS     current
    DESCRIPTION
       "The type of DLSw encapsulation in use on this peer connection."
    DEFVAL     { tcp }
    ::= { cdeTConnConfigEntry 1 }

cdeTConnConfigLocalAck  OBJECT-TYPE
    SYNTAX     TruthValue
    MAX-ACCESS read-create
    STATUS     current
    DESCRIPTION
       "Reflects whether the peer connection is locally acknowledged.
        Locally acknoledgement means terminating the DLC connections
        at the router, eliminating the requirement for link-layer
        acknowledgements and keepalive messages to flow across the
        WAN.  In addition because link-layer frames are acknowledged
        locally, link-layer time-outs should not occur.

        In general ciscoDlswTConnConfigLocalAck will be true when the
        domain type is tcp, false when the domain type is fst,
        direct-hdlc, or direct-frame-relay.

        Configuring the remote-peer as pass-thru, the remote peer
        will not use local acknowlegement."
    DEFVAL { true }
    ::= { cdeTConnConfigEntry 2 }

cdeTConnConfigCost  OBJECT-TYPE
    SYNTAX     Cost
    MAX-ACCESS read-create
    STATUS     current
    DESCRIPTION
       "The cost associated with the transport connection,
        assigned to this conceptual row representing a peer.
        If an end station can be reached through more
        than one peer, the cost of each peer will be considered when
        a circuit is established.
        A lower cost indicates that peer will be the
        preferred choice if there is more than one path to the
        destination."
    DEFVAL     { 3 }
    ::= { cdeTConnConfigEntry 3 }

cdeTConnConfigLFSize  OBJECT-TYPE
    SYNTAX     LFSize
    MAX-ACCESS read-create
    STATUS     current
    DESCRIPTION
       "The Largest Frame Size associated with the transport connection.
        In other words its the largest size of the INFO field
        (including DLC header, not including any MAC-level or framing
        octets)."
    DEFVAL     { lfs17749 }
    ::= { cdeTConnConfigEntry 4 }

cdeTConnConfigKeepaliveInterval  OBJECT-TYPE
    SYNTAX     KeepaliveInterval
    UNITS      "Seconds"
    MAX-ACCESS read-create
    STATUS     current
    DESCRIPTION
       "The amount of time between keepalive messages on a transport
        connection.
        The keepalive parameter refers to how often DLSw peers
        send peer keep alives to each other.  These periodic messages
        allow DLSw to keep track of the state of all peers.
        If set to zero, no keepalives are sent."
    DEFVAL     { 30 }
    ::= { cdeTConnConfigEntry 5 }

cdeTConnConfigBackup  OBJECT-TYPE
    SYNTAX     TruthValue
    MAX-ACCESS read-create
    STATUS     current
    DESCRIPTION
       "This variable indicates if this peer is defined
        as a backup to an existing peer.  A backup peer is used
        to provide an alternate path in case an existing peer becomes
        unavailable.  A backup peer will not enter the connected
        state until the primary peer that it backs up becomes
        disconnected.
        True indicates that this conecptual row is a backup peer
        to a pre-existing peer, false indicates this peer is not
        a backup peer."
    DEFVAL     { false }
    ::= { cdeTConnConfigEntry 6 }

cdeTConnConfigBackupTAddr  OBJECT-TYPE
    SYNTAX     TAddress
    MAX-ACCESS read-create
    STATUS     current
    DESCRIPTION
       "The primary peer's IP address that this entry backs up.
        Valid only when ciscoDlswTConnConfigBackup is true."
    DEFVAL      { ''H }     -- the empty string
    ::= { cdeTConnConfigEntry 7 }

cdeTConnConfigBackupLinger  OBJECT-TYPE
    SYNTAX     TruthValue
    MAX-ACCESS read-create
    STATUS     current
    DESCRIPTION
       "This variable indicates whether the backup peer will
        remain connected after the primary peer connection has
        been re-established.
        True indicates that the backup peer will remain connected after
        the primary peer connection has been re-established, for the
        length of time specified in cdeTConnConfigBackupLingerInterval.
        False indicates that the backup peer will remain connected until
        all circuits on the backup peer connection have been disconnected."
    DEFVAL     { false }
    ::= { cdeTConnConfigEntry 8 }

cdeTConnConfigBackupLingerInterval  OBJECT-TYPE
    SYNTAX     INTEGER (0..1440)
    UNITS      "Minutes"
    MAX-ACCESS read-create
    STATUS     current
    DESCRIPTION
       "This variable indicates the length of time the backup peer
        remains connected after the primary peer connection has
        been re-established.  If this variable is zero, the backup peer
        will be disconnected immediately after the primary peer connection
        has been re-established.  If greater than zero the backup will 
        stay connected for the number of minutes indicated by this variable,
        after the primary peer connection has been re-established.
        Note that the linger interval is only used when
        cdeTConnConfigBackupLinger is true."
    DEFVAL     { 0 }
    ::= { cdeTConnConfigEntry 9 }

cdeTConnConfigPriority  OBJECT-TYPE
    SYNTAX     TruthValue
    MAX-ACCESS read-create
    STATUS     current
    DESCRIPTION
       "Indicator of whether this peer connection supports priority.
        When priority is configured for the remote peer,
        DLSw+ will automatically activate four TCP connections to that
        remote peer (ports 2065, 1981, 1982, and 1983). Priority only
        needs to be configured if you need to prioritize between SNA
        and NetBIOS, or within SNA by LOCADDR or MAC/SAP pair
        (known as SAP prioritization). In addition, this granular packet
        classification is only possible when TCP encapsulation is selected
        for a specific remote peer. By default DLSw+ assigns certain
        traffic to specific TCP ports."
    DEFVAL     { false }
    ::= { cdeTConnConfigEntry 10 }

cdeTConnConfigDestMac  OBJECT-TYPE
    SYNTAX     MacAddressNC
    MAX-ACCESS read-create
    STATUS     current
    DESCRIPTION
       "Permits the peer connection to be established only when there is an
        explorer frame destined for the specified 48-bit MAC address.

        If no expolorer traffic with a destination address of 
        cdeTConnConfigDestMac is received by DLSw, 
        the peer reprented by this conceptual row will not be connected."
    DEFVAL      { ''H }     -- the empty string
    ::= { cdeTConnConfigEntry 11 }

cdeTConnConfigDynamic  OBJECT-TYPE
    SYNTAX     TruthValue
    MAX-ACCESS read-create
    STATUS     current
    DESCRIPTION
       "Indicates the peer connection is to be established only
        when there is DLSw+ data to send."
    DEFVAL     { false }
    ::= { cdeTConnConfigEntry 12 }

cdeTConnConfigDynamicNoLlc  OBJECT-TYPE
    SYNTAX     INTEGER (1..300)
    UNITS      "Minutes"
    MAX-ACCESS read-create
    STATUS     current
    DESCRIPTION
       "This variable indicates the length of time a dynamic peer
        remains connected after all LLC2 circuits are gone."
    DEFVAL     { 5 }
    ::= { cdeTConnConfigEntry 13 }

cdeTConnConfigDynamicInactivityInterval  OBJECT-TYPE
    SYNTAX     INTEGER (0..300)
    UNITS      "Minutes"
    MAX-ACCESS read-create
    STATUS     current
    DESCRIPTION
       "Indicates the length of time a connection can be idle before
        closing the dynamic peer connection.  If set to zero, the dynamic 
        peer connection will not be closed due to inactivity."
    DEFVAL     { 0 }
    ::= { cdeTConnConfigEntry 14 }

--
-- Cisco DLSw Extension Transport Connection Operation Table
--

cdeTConnOperTable OBJECT-TYPE
    SYNTAX     SEQUENCE OF CdeTConnOperEntry
    MAX-ACCESS not-accessible
    STATUS     current
    DESCRIPTION
       "A list of peer transport connections.
        Each connected peer will create a conceptual row in the table.
        When the peer disconnects, the row will be deleted from the table.
        This table augments dlswTConnOperTable."
    ::= { cdeTConn 2 }

cdeTConnOperEntry OBJECT-TYPE
    SYNTAX     CdeTConnOperEntry
    MAX-ACCESS not-accessible
    STATUS     current
    DESCRIPTION
       "A list of objects that contain spefific operational 
        information for a DLSw peer transport connection."
    AUGMENTS { dlswTConnOperEntry }
    ::= { cdeTConnOperTable 1 }

CdeTConnOperEntry ::= SEQUENCE {
    cdeTConnOperPartnerCost              Cost,
    cdeTConnOperPartnerPriority          TruthValue,
    cdeTConnOperPartnerBorderPeer        TruthValue,
    cdeTConnOperPartnerGroupNum          INTEGER,
    cdeTConnOperTDomainType              TDomainType
}

cdeTConnOperPartnerCost  OBJECT-TYPE
    SYNTAX     Cost
    MAX-ACCESS read-only
    STATUS     current
    DESCRIPTION
       "The partner's cost on this peer connection, as received
        through capabilities exchange.
        If an end station can be reached through more
        than one peer, the cost of each peer will be considered when
        a circuit is established.
        A lower cost indicates that peer will be the
        preferred choice if there is more than one path to the
        destination."
    DEFVAL     { 3 }
    ::= { cdeTConnOperEntry 1 }

cdeTConnOperPartnerPriority  OBJECT-TYPE
    SYNTAX     TruthValue
    MAX-ACCESS read-only
    STATUS     current
    DESCRIPTION
       "The partner's priority setting on this peer connection,
        as received through capabilities exchange.
        When priority is enabled for the remote peer,
        DLSw+ will automatically activate four TCP connections to that
        remote peer (ports 2065, 1981, 1982, and 1983). Priority only
        needs to be configured if you need to prioritize between SNA
        and NetBIOS, or within SNA by LOCADDR or MAC/SAP pair
        (known as SAP prioritization). In addition, this granular packet
        classification is only possible when TCP encapsulation is selected
        for a specific remote peer. By default DLSw+ assigns certain
        traffic to specific TCP ports."
    ::= { cdeTConnOperEntry 2 }

cdeTConnOperPartnerBorderPeer  OBJECT-TYPE
    SYNTAX     TruthValue
    MAX-ACCESS read-only
    STATUS     current
    DESCRIPTION
       "This variable indicates if the partner DLSw is capable of
        operating as a border peer, as received through capabilities
        exchange.  True indicates that it is
        capable, false indicates that it is not.

        Border peers form peer connections with every router in
        their group and with border peers in other groups. The
        role of a border peer is to forward explorers on behalf
        of other DLSw routers."
    ::= { cdeTConnOperEntry 3 }

cdeTConnOperPartnerGroupNum  OBJECT-TYPE
    SYNTAX     INTEGER (0..255)
    MAX-ACCESS read-only
    STATUS     current
    DESCRIPTION
       "This variable indicates the partner's group number, as
        received through capabilities exchange.
        Peer groups are arbitrary groups of routers with one or
        more designated border peers.  Border peers form peer
        connections with every router in their group and with
        border peers in other groups. The role of a border peer
        is to forward explorers on behalf of other routers.
        A value of zero means no group has been set and the
        DLSw is not a group member."
    ::= { cdeTConnOperEntry 4 }

cdeTConnOperTDomainType  OBJECT-TYPE
    SYNTAX     TDomainType
    MAX-ACCESS read-only
    STATUS     current
    DESCRIPTION
       "The type of DLSw encapsulation in use on this peer connection."
    ::= { cdeTConnOperEntry 5 }

-- *******************************************************************
-- Transport Connection Specific
-- *******************************************************************
cdeTConnSpecific OBJECT IDENTIFIER ::= { cdeTConn 3 }
cdeTConnTcp      OBJECT IDENTIFIER ::= { cdeTConnSpecific 1 }
cdeTConnDirect   OBJECT IDENTIFIER ::= { cdeTConnSpecific 2 }

--
-- Cisco DLSw Extension TCP Transport Connection Specific Configuration
--

cdeTConnTcpConfigTable OBJECT-TYPE
    SYNTAX     SEQUENCE OF CdeTConnTcpConfigEntry
    MAX-ACCESS not-accessible
    STATUS     current
    DESCRIPTION
       "This table defines the TCP transport connections that
        will be either initiated by or accepted by this DSLw.
        It augments the entries in dlswTConnConfigTable whose
        domain is dlswTCPDomain.  In other words for each conceptual row
        in the dlswTConnConfigTable, if the dlswTConnConfigTDomain is
        dlswTCPDomain, that conceptual row will be augmented by this
        table.

        dlswTCPDomain, dlswTConnConfigTable, and dlswTConnConfigTDomain
        are all imported from DLSW-MIB (RFC 2024).

        This table augments dlswTConnTcpConfigTable."
    ::= { cdeTConnTcp 1 }

cdeTConnTcpConfigEntry OBJECT-TYPE
    SYNTAX     CdeTConnTcpConfigEntry
    MAX-ACCESS not-accessible
    STATUS     current
    DESCRIPTION
       "A list of objects that define spefific configuration for
        a DLSw peer transport connection within the dlswTCPDomain.
        dlswTCPDomain is imported from DLSW-MIB (RFC 2024)."
    AUGMENTS { dlswTConnTcpConfigEntry }
    ::= { cdeTConnTcpConfigTable 1 }

CdeTConnTcpConfigEntry ::= SEQUENCE {
    cdeTConnTcpConfigQueueMax           TCPQueueMax
}

cdeTConnTcpConfigQueueMax  OBJECT-TYPE
    SYNTAX     TCPQueueMax
    UNITS      "packets"
    MAX-ACCESS read-create
    STATUS     current
    DESCRIPTION
       "Maximum output TCP queue size for this remote peer.
        For DLSw over TCP encapsulation, packets may be queued
        due to congestion of the TCP network.  This variable
        is used to set the output queue maximum of the underlying
        TCP connection for the peer represented by the conceptual row."
    DEFVAL     { 200 }
    ::= { cdeTConnTcpConfigEntry 1 }

--
-- Cisco DLSw Extension Direct Transport Connection Specific Configuration
--

cdeTConnDirectConfigTable  OBJECT-TYPE
    SYNTAX     SEQUENCE OF CdeTConnDirectConfigEntry
    MAX-ACCESS not-accessible
    STATUS     current
    DESCRIPTION
       "This table contains direct peer media-specific
        configuration information. 
        An entry is maintained for every peer in the 
        cdeTConnConfigTable whose domain is either cdeDirectHdlcDomain,
        cdeDirectFrameRelayDomain, or cdeLlc2Domain.

        In other words, for each conceptual row
        in the dlswTConnConfigTable, if the dlswTConnConfigTDomain is
        either cdeDirectHdlcDomain, cdeDirectFrameRelayDomain, or
        cdeLlc2Domain, there will be an entry in this table.

        dlswTConnConfigTable, and dlswTConnConfigTDomain
        are imported from DLSW-MIB (RFC 2024)."
    ::= { cdeTConnDirect 1 }

cdeTConnDirectConfigEntry  OBJECT-TYPE
    SYNTAX     CdeTConnDirectConfigEntry
    MAX-ACCESS not-accessible
    STATUS     current
    DESCRIPTION
       "Each conceptual row defines parameters that are
        specific to peer transport connections whose domain is
        either cdeDirectHdlcDomain, cdeDirectFrameRelayDomain, or
        cdeLlc2Domain."
    INDEX   { dlswTConnConfigIndex }
    ::= { cdeTConnDirectConfigTable 1 }

CdeTConnDirectConfigEntry ::= SEQUENCE {
    cdeTConnDirectConfigIfIndex            InterfaceIndex,
    cdeTConnDirectConfigMediaEncap         INTEGER,
    cdeTConnDirectConfigFrameRelayDlci     DlciNumber
    }

cdeTConnDirectConfigIfIndex  OBJECT-TYPE
    SYNTAX     InterfaceIndex
    MAX-ACCESS read-create
    STATUS     current
    DESCRIPTION
       "The IfEntry index of the local interface,
        on which the direct peer can be reached."
    ::= { cdeTConnDirectConfigEntry 1 }

cdeTConnDirectConfigMediaEncap  OBJECT-TYPE
    SYNTAX     INTEGER  {
        directHdlc             (1),
        directFrameRelay       (2),
        llc2                   (3)
    }
    MAX-ACCESS read-create
    STATUS     current
    DESCRIPTION
       "The type of media encapsulation to be used on this 
        peer connection.  When using DLSw Direct-encapsulation or
        DLSw Lite (Frame Relay) encapsulation, the peer transport
        connection is defined as either directHdlc or directFrameRelay,
        respectively.

        Hdlc peer transport encapsulation does not support
        local acknowledgment of frames.

        Logical Link Control, Type2 (LLC2) peer transport
        encapsulation -for transport across a point-to-point
        connection (currently only Frame Relay is supported) provides
        local acknowledgment and reliable transport."
    DEFVAL      { directHdlc }
    ::= { cdeTConnDirectConfigEntry 2 }

cdeTConnDirectConfigFrameRelayDlci  OBJECT-TYPE
    SYNTAX     DlciNumber
    MAX-ACCESS read-create
    STATUS     current
    DESCRIPTION
       "The Data Link Connection Identifier for the virtual
        circuit on this interface.  This object will only
        be valid if the value of
        cdeTConnDirectConfigMediaEncap is llc2."
    DEFVAL      { 0 }
    ::= { cdeTConnDirectConfigEntry 3 }

--
-- Cisco DLSw Extension Interface Table
--

cdeIfTable  OBJECT-TYPE
    SYNTAX     SEQUENCE OF CdeIfEntry
    MAX-ACCESS not-accessible
    STATUS     current
    DESCRIPTION
       "The list of interfaces on which DLSw is active.

        This table augments dlswIfTable."
    ::= { cdeInterface 1 }

cdeIfEntry OBJECT-TYPE
    SYNTAX     CdeIfEntry
    MAX-ACCESS not-accessible
    STATUS     current
    DESCRIPTION
       "Each conceptual row represents an interface."
    AUGMENTS { dlswIfEntry }
    ::= { cdeIfTable 1 }

CdeIfEntry ::= SEQUENCE {
    cdeIfType           DlcType
}

cdeIfType  OBJECT-TYPE
    SYNTAX     DlcType
    MAX-ACCESS read-only
    STATUS     current
    DESCRIPTION
       "The DLC protocol in use on this DLSw interface."
    ::= { cdeIfEntry 1 }

--
-- Cisco DLSw Extension Circuit Table
--

cdeCircuitTable  OBJECT-TYPE
    SYNTAX     SEQUENCE OF CdeCircuitEntry
    MAX-ACCESS not-accessible
    STATUS     current
    DESCRIPTION
       "A list of circuits.  Each new circuit will create a conceptual row 
        in the table.
        When the circuit disconnects, the row will be deleted from the table.
        End station 1 (S1) and End station 2 (S2) are used to
        represent the two end stations of the circuit.
        S1 is always an end station which is locally attached.
        S2 may be locally attached or remote.  

        This table augments the dlswCircuitTable."
    ::= { cdeCircuit 1 }

cdeCircuitEntry OBJECT-TYPE
    SYNTAX     CdeCircuitEntry
    MAX-ACCESS not-accessible
    STATUS     current
    DESCRIPTION
       "A list of objects that contain specific 
        information for a DLSw circuit."
    AUGMENTS { dlswCircuitEntry }
    ::= { cdeCircuitTable 1 }

CdeCircuitEntry ::= SEQUENCE {
    cdeCircuitS1Name               DisplayString(SIZE (0..17)),
    cdeCircuitS2Name               DisplayString(SIZE (0..17)),
    cdeCircuitS1IdBlock            DisplayString(SIZE (0..3)),
    cdeCircuitS1IdNum              DisplayString(SIZE (0..5))
}

cdeCircuitS1Name  OBJECT-TYPE
    SYNTAX     DisplayString(SIZE (0..17))
    MAX-ACCESS read-only
    STATUS     current
    DESCRIPTION
       "Represents the PU Name of End Station 1 (S1), if available."
    ::= { cdeCircuitEntry 1 }

cdeCircuitS2Name  OBJECT-TYPE
    SYNTAX     DisplayString(SIZE (0..17))
    MAX-ACCESS read-only
    STATUS     current
    DESCRIPTION
       "Represents the PU Name of End Station 2 (S2), if available."
    ::= { cdeCircuitEntry 2 }

cdeCircuitS1IdBlock OBJECT-TYPE
    SYNTAX     DisplayString  (SIZE (0..3))
    MAX-ACCESS read-only
    STATUS     current
    DESCRIPTION
       "The block number is the first three digits of the SNA Node id of
        End Station 1 (S1), if available.  These 3 hexadecimal digits
        identify the product."
    ::= { cdeCircuitEntry 3 }

cdeCircuitS1IdNum OBJECT-TYPE
    SYNTAX     DisplayString  (SIZE (0..5))
    MAX-ACCESS read-only
    STATUS     current
    DESCRIPTION
       "The ID number is the last 5 digits of the SNA Node id of End
        Station 1 (S1), if available.  These 5 hexadecimal digits are
        administratively defined and combined with the 3 digit
        block number form the Node id.  This Node id is used to
        identify the local node and is included in SNA XIDs."
    ::= { cdeCircuitEntry 4 }

--
-- Cisco DLSw Extension Fast Cache Table
--

cdeFastTable  OBJECT-TYPE
    SYNTAX     SEQUENCE OF CdeFastEntry
    MAX-ACCESS not-accessible
    STATUS     current
    DESCRIPTION
       "A table containing fast cache entries.
        The table contains cache information for FST peers or
        direct encapsulation peers (without local acknowledgement enabled).

        When using these encapsulation types, a fast-switching
        cache must be built. The first frame between two end
        stations will be process switched, and during this
        process an entry will be made in the fast-switching
        cache so that subsequent frames between those end
        stations may be fast switched.

        End station 1 (S1) and End station 2 (S2) are used to
        represent the two end stations of the faat cache entry.
        S1 is always an end station which is locally attached.
        S2 is always an end station which is remote."
    ::= { cdeFast 1 }

cdeFastEntry  OBJECT-TYPE
    SYNTAX     CdeFastEntry
    MAX-ACCESS not-accessible
    STATUS     current
    DESCRIPTION
       "A list of objects that define specific information
        for a DLSw fast cache entry."
    INDEX   { cdeFastS1Mac,
              cdeFastS1Sap,
              cdeFastS2Mac,
              cdeFastS2Sap }
    ::= { cdeFastTable 1 }

CdeFastEntry ::= SEQUENCE {
    cdeFastS1Mac                MacAddressNC,
    cdeFastS1Sap                SAPType,
    cdeFastS2Mac                MacAddressNC,
    cdeFastS2Sap                SAPType,
    cdeFastS1IfIndex            InterfaceIndex,
    cdeFastS1RouteInfo          OCTET STRING,
    cdeFastS1CacheId            OCTET STRING,
    cdeFastS2TDomain            OBJECT IDENTIFIER,
    cdeFastS2TAddress           TAddress,
    cdeFastS2CacheId            OCTET STRING,
    cdeFastOrigin               INTEGER,
    cdeFastTimeToLive           TimeTicks
    }

cdeFastS1Mac  OBJECT-TYPE
    SYNTAX     MacAddressNC
    MAX-ACCESS not-accessible
    STATUS     current
    DESCRIPTION
       "The MAC Address of End Station 1 (S1) used for this cache entry."
    ::= { cdeFastEntry 1 }

cdeFastS1Sap  OBJECT-TYPE
    SYNTAX     SAPType
    MAX-ACCESS not-accessible
    STATUS     current
    DESCRIPTION
       "The SAP at End Station 1 (S1) used for this cache entry."
    ::= { cdeFastEntry 2 }

cdeFastS2Mac  OBJECT-TYPE
    SYNTAX     MacAddressNC
    MAX-ACCESS not-accessible
    STATUS     current
    DESCRIPTION
       "The MAC Address of End Station 2 (S2) used for this cache entry."
    ::= { cdeFastEntry 3 }

cdeFastS2Sap  OBJECT-TYPE
    SYNTAX     SAPType
    MAX-ACCESS not-accessible
    STATUS     current
    DESCRIPTION
       "The SAP at End Station 2 (S2) used for this cache entry."
    ::= { cdeFastEntry 4 }

cdeFastS1IfIndex  OBJECT-TYPE
    SYNTAX     InterfaceIndex
    MAX-ACCESS read-only
    STATUS     current
    DESCRIPTION
       "The ifEntry index of the local interface through which S1
        can be reached."
    ::= { cdeFastEntry 5 }

cdeFastS1RouteInfo  OBJECT-TYPE
    SYNTAX     OCTET STRING (SIZE (0..30))
    MAX-ACCESS read-only
    STATUS     current
    DESCRIPTION
       "If source-route bridging is in use between the DLSw
        and S1, this is the routing information field
        describing the path between the two devices.
        Otherwise the value will be an OCTET STRING of
        zero length."
    ::= { cdeFastEntry 6 }

cdeFastS1CacheId  OBJECT-TYPE
    SYNTAX     OCTET STRING (SIZE(8))
    MAX-ACCESS read-only
    STATUS     current
    DESCRIPTION
       "The Cache ID assigned by this DLSw to this fast cache entry.
        Every Fast cache entry will have a unique id.
        A management station could use this object by periodically
        polling this table, and determine whether the same cache 
        entries were present or absent."
    ::= { cdeFastEntry 7 }

cdeFastS2TDomain  OBJECT-TYPE
    SYNTAX     OBJECT IDENTIFIER
    MAX-ACCESS read-only
    STATUS     current
    DESCRIPTION
       "This object contains the transport domain of the peer
        transport protocol that the fast cache entry is running
        over."
    ::= { cdeFastEntry 8 }

cdeFastS2TAddress  OBJECT-TYPE
    SYNTAX     TAddress
    MAX-ACCESS read-only
    STATUS     current
    DESCRIPTION
       "This object contains the transport address of the partner DLSw."
    ::= { cdeFastEntry 9 }

cdeFastS2CacheId  OBJECT-TYPE
    SYNTAX     OCTET STRING (SIZE(8))
    MAX-ACCESS read-only
    STATUS     current
    DESCRIPTION
       "The Cache ID assigned to this fast cache entry by the partner
        DLSw.
        Every Fast cache entry will have a unique id.
        A management station could use this object by periodically
        polling this table, and determine whether the same cache
        entries were present or absent."
    ::= { cdeFastEntry 10 }

cdeFastOrigin  OBJECT-TYPE
    SYNTAX     INTEGER  {
        s1             (1),
        s2             (2)
    }
    MAX-ACCESS read-only
    STATUS     current
    DESCRIPTION
       "This object specifies which of the two end stations
        initiated the establishment of this circuit."
    ::= { cdeFastEntry 11 }

cdeFastTimeToLive  OBJECT-TYPE
    SYNTAX     TimeTicks
    UNITS      "hundredths of a second"
    MAX-ACCESS read-only
    STATUS     current
    DESCRIPTION
       "The amount of time (in hundredths of a second) remaining
        before this fast cache entry will be removed from the table.
        After 5 minutes of inactivity, the fast cache entry will be
        deleted."
    ::= { cdeFastEntry 12 }

--
-- Cisco DLSw Extension Trap Control
--

cdeTrapCntlTConn  OBJECT-TYPE
    SYNTAX     TruthValue
    MAX-ACCESS read-write
    STATUS     current
    DESCRIPTION
       "Indicates whether DLSw is permitted to emit transport
        connection up and down traps.  With the value of `true'
        DLSw will emit traps when connections enter `connected'
        and `disconnected' states.  With the value of `false'
        DLSw will not emit traps when connections enter
        `connected' and `disconnected' states.
        The changes take effect immediately."
    DEFVAL     { false }
    ::= { cdeTrapControl 1 }

cdeTrapCntlCircuit  OBJECT-TYPE
    SYNTAX     TruthValue
    MAX-ACCESS read-write
    STATUS     current
    DESCRIPTION
       "Indicates whether the DLSw is permitted to generate
        circuit up and down traps.  With the value of `true'
        the DLSw will emit traps when circuits enter `connected'
        and `disconnected' states.  With the value of `false'
        the DLSw will not emit traps when circuits enter
        `connected' and `disconnected' states.
        The changes take effect immediately."
    DEFVAL     { false }
    ::= { cdeTrapControl 2 }

-- *******************************************************************
-- NOTIFICATIONS, i.e., TRAP DEFINITIONS
-- *******************************************************************
cdeTrapsPrefix              OBJECT IDENTIFIER ::= { ciscoDlswExtMIB 2 }
cdeTraps                    OBJECT IDENTIFIER ::= { cdeTrapsPrefix 0}

--
-- This section defines the well-known notifications sent by
-- DLSW agents.
-- Care must be taken to insure that no particular notification
-- is sent to a single receiving entity more often than once
-- every five seconds.
--
-- Traps include:
-- (1) Transport connection up/down
-- (2) Circuit up/down

cdeTrapTConnUpDown NOTIFICATION-TYPE
    OBJECTS { dlswTConnOperState }
    STATUS     current
    DESCRIPTION
       "This trap is sent each time a transport connection
        changes state to `connected' or `disconnected'.
        The emission of this trap
        is controlled by cdeTrapCntlTConn."
    ::= { cdeTraps 1 }

cdeTrapCircuitUpDown NOTIFICATION-TYPE
    OBJECTS { dlswCircuitState }
    STATUS     current
    DESCRIPTION
       "This trap is sent each time a circuit changes 
        state to `connected' or `disconnected'.
        the emission of this trap is controlled by
        cdeTrapCntlCircuit."
    ::= { cdeTraps 2 }

-- *************************************************************************
-- * Conformance Information
-- *************************************************************************

cdeMIBConformance   OBJECT IDENTIFIER ::= { ciscoDlswExtMIB 3 }
cdeMIBCompliances   OBJECT IDENTIFIER ::= { cdeMIBConformance 1 }
cdeMIBGroups        OBJECT IDENTIFIER ::= { cdeMIBConformance 2 }

-- *************************************************************************
-- * Compliance Statements
-- *************************************************************************

cdeMIBCompliance MODULE-COMPLIANCE
	STATUS  current
	DESCRIPTION
		"The compliance statement for all Cisco DLSw+
                 implementations."
	MODULE  -- this module
        MANDATORY-GROUPS { cdeMIBNodeGroup,
                           cdeMIBTConnConfigGroup,
                           cdeMIBTConnOperGroup,
                           cdeMIBTConnTcpConfigGroup,
                           cdeMIBTConnDirectConfigGroup,
                           cdeMIBInterfaceGroup,
                           cdeMIBCircuitGroup,
                           cdeMIBFastGroup,
                           cdeTrapControlGroup
                          }

        OBJECT      cdeNodeTAddr
        MIN-ACCESS  read-only
        DESCRIPTION "Write access not required"

        OBJECT      cdeNodeGroup
        MIN-ACCESS  read-only
        DESCRIPTION "Write access not required"

        OBJECT      cdeNodeBorder
        MIN-ACCESS  read-only
        DESCRIPTION "Write access not required"

        OBJECT      cdeNodeCost
        MIN-ACCESS  read-only
        DESCRIPTION "Write access not required"

        OBJECT      cdeNodeKeepaliveInterval
        MIN-ACCESS  read-only
        DESCRIPTION "Write access not required"

        OBJECT      cdeNodePassiveConnect
        MIN-ACCESS  read-only
        DESCRIPTION "Write access not required"

        OBJECT      cdeNodeBiuSegment
        MIN-ACCESS  read-only
        DESCRIPTION "Write access not required"

        OBJECT      cdeNodeInitPacingWindow
        MIN-ACCESS  read-only
        DESCRIPTION "Write access not required"

        OBJECT      cdeNodeMaxPacingWindow
        MIN-ACCESS  read-only
        DESCRIPTION "Write access not required"

        OBJECT      cdeNodePromiscuous
        MIN-ACCESS  read-only
        DESCRIPTION "Write access not required"

        OBJECT      cdeNodePromPeerDefaultsCost
        MIN-ACCESS  read-only
        DESCRIPTION "Write access not required"

        OBJECT      cdeNodePromPeerDefaultsDestMac
        MIN-ACCESS  read-only
        DESCRIPTION "Write access not required"

        OBJECT      cdeNodePromPeerDefaultsKeepaliveInterval
        MIN-ACCESS  read-only
        DESCRIPTION "Write access not required"

        OBJECT      cdeNodePromPeerDefaultsLFSize
        MIN-ACCESS  read-only
        DESCRIPTION "Write access not required"

        OBJECT      cdeNodePromPeerDefaultsTCPQueueMax
        MIN-ACCESS  read-only
        DESCRIPTION "Write access not required"

        OBJECT      cdeNodePeerOnDemandDefaultsCost
        MIN-ACCESS  read-only
        DESCRIPTION "Write access not required"

        OBJECT      cdeNodePeerOnDemandDefaultsFst
        MIN-ACCESS  read-only
        DESCRIPTION "Write access not required"

        OBJECT      cdeNodePeerOnDemandDefaultsInactivityInterval
        MIN-ACCESS  read-only
        DESCRIPTION "Write access not required"

        OBJECT      cdeNodePeerOnDemandDefaultsKeepaliveInterval
        MIN-ACCESS  read-only
        DESCRIPTION "Write access not required"

        OBJECT      cdeNodePeerOnDemandDefaultsLFSize
        MIN-ACCESS  read-only
        DESCRIPTION "Write access not required"

        OBJECT      cdeNodePeerOnDemandDefaultsPriority
        MIN-ACCESS  read-only
        DESCRIPTION "Write access not required"

        OBJECT      cdeNodePeerOnDemandDefaultsTCPQueueMax
        MIN-ACCESS  read-only
        DESCRIPTION "Write access not required"

        OBJECT      cdeTConnConfigTDomainType
        MIN-ACCESS  read-only
        DESCRIPTION "Write access not required"

        OBJECT      cdeTConnConfigLocalAck
        MIN-ACCESS  read-only
        DESCRIPTION "Write access not required"

        OBJECT      cdeTConnConfigCost
        MIN-ACCESS  read-only
        DESCRIPTION "Write access not required"

        OBJECT      cdeTConnConfigLFSize
        MIN-ACCESS  read-only
        DESCRIPTION "Write access not required"

        OBJECT      cdeTConnConfigKeepaliveInterval
        MIN-ACCESS  read-only
        DESCRIPTION "Write access not required"

        OBJECT      cdeTConnConfigBackup
        MIN-ACCESS  read-only
        DESCRIPTION "Write access not required"

        OBJECT      cdeTConnConfigBackupTAddr
        MIN-ACCESS  read-only
        DESCRIPTION "Write access not required"

        OBJECT      cdeTConnConfigBackupLinger
        MIN-ACCESS  read-only
        DESCRIPTION "Write access not required"

        OBJECT      cdeTConnConfigBackupLingerInterval
        MIN-ACCESS  read-only
        DESCRIPTION "Write access not required"

        OBJECT      cdeTConnConfigPriority
        MIN-ACCESS  read-only
        DESCRIPTION "Write access not required"

        OBJECT      cdeTConnConfigDestMac
        MIN-ACCESS  read-only
        DESCRIPTION "Write access not required"

        OBJECT      cdeTConnConfigDynamic
        MIN-ACCESS  read-only
        DESCRIPTION "Write access not required"

        OBJECT      cdeTConnConfigDynamicNoLlc
        MIN-ACCESS  read-only
        DESCRIPTION "Write access not required"

        OBJECT      cdeTConnConfigDynamicInactivityInterval
        MIN-ACCESS  read-only
        DESCRIPTION "Write access not required"

        OBJECT      cdeTConnTcpConfigQueueMax
        MIN-ACCESS  read-only
        DESCRIPTION "Write access not required"

        OBJECT      cdeTConnDirectConfigIfIndex
        MIN-ACCESS  read-only
        DESCRIPTION "Write access not required"

        OBJECT      cdeTConnDirectConfigMediaEncap
        MIN-ACCESS  read-only
        DESCRIPTION "Write access not required"

        OBJECT      cdeTConnDirectConfigFrameRelayDlci
        MIN-ACCESS  read-only
        DESCRIPTION "Write access not required"

        OBJECT      cdeTrapCntlTConn
        MIN-ACCESS  read-only
        DESCRIPTION "Write access not required"

        OBJECT      cdeTrapCntlCircuit
        MIN-ACCESS  read-only
        DESCRIPTION "Write access not required"
	::= { cdeMIBCompliances 1 }

-- units of conformance

cdeMIBNodeGroup OBJECT-GROUP
    OBJECTS { 
              cdeNodeTAddr,
              cdeNodeGroup,
              cdeNodeBorder,
              cdeNodeCost,
              cdeNodeKeepaliveInterval,
              cdeNodePassiveConnect,
              cdeNodeBiuSegment,
              cdeNodeInitPacingWindow,
              cdeNodeMaxPacingWindow,
              cdeNodePromiscuous,
              cdeNodePromPeerDefaultsCost,
              cdeNodePromPeerDefaultsDestMac,
              cdeNodePromPeerDefaultsKeepaliveInterval,
              cdeNodePromPeerDefaultsLFSize,
              cdeNodePromPeerDefaultsTCPQueueMax,
              cdeNodePeerOnDemandDefaultsCost,
              cdeNodePeerOnDemandDefaultsFst,
              cdeNodePeerOnDemandDefaultsInactivityInterval,
              cdeNodePeerOnDemandDefaultsKeepaliveInterval,
              cdeNodePeerOnDemandDefaultsLFSize,
              cdeNodePeerOnDemandDefaultsPriority,
              cdeNodePeerOnDemandDefaultsTCPQueueMax
            }
    STATUS  current
    DESCRIPTION
            "Conformance group for DLSw Node general information."
    ::= { cdeMIBGroups 1 }

cdeMIBTConnConfigGroup OBJECT-GROUP
    OBJECTS {
              cdeTConnConfigTDomainType,
              cdeTConnConfigLocalAck,
              cdeTConnConfigCost,
              cdeTConnConfigLFSize,
              cdeTConnConfigKeepaliveInterval,
              cdeTConnConfigBackup,
              cdeTConnConfigBackupTAddr,
              cdeTConnConfigBackupLinger,
              cdeTConnConfigBackupLingerInterval,
              cdeTConnConfigPriority,
              cdeTConnConfigDestMac,
              cdeTConnConfigDynamic,
              cdeTConnConfigDynamicNoLlc,
              cdeTConnConfigDynamicInactivityInterval
            }
    STATUS  current
    DESCRIPTION
       "Conformance group for the configuration of
        transport connections."
    ::= { cdeMIBGroups 2 }

cdeMIBTConnOperGroup OBJECT-GROUP
    OBJECTS {
              cdeTConnOperPartnerCost,
              cdeTConnOperPartnerPriority,
              cdeTConnOperPartnerBorderPeer,
              cdeTConnOperPartnerGroupNum,
              cdeTConnOperTDomainType
            }
    STATUS current
    DESCRIPTION
       "Conformance group for operation information for
        transport connections."
    ::= { cdeMIBGroups 3 }

cdeMIBTConnTcpConfigGroup OBJECT-GROUP
    OBJECTS {
              cdeTConnTcpConfigQueueMax
            }
    STATUS current
    DESCRIPTION
       "Conformance group for configuration information for
        transport connections using TCP."
    ::= { cdeMIBGroups 4 }

cdeMIBTConnDirectConfigGroup OBJECT-GROUP
    OBJECTS {
              cdeTConnDirectConfigIfIndex,
              cdeTConnDirectConfigMediaEncap,
              cdeTConnDirectConfigFrameRelayDlci
            }
    STATUS current
    DESCRIPTION
       "Conformance group for configuration information for
        transport connections using Direct or FST."
    ::= { cdeMIBGroups 5 }

cdeMIBInterfaceGroup OBJECT-GROUP
    OBJECTS {
              cdeIfType
            }
    STATUS current
    DESCRIPTION
       "Conformance group for DLSw interfaces."
    ::= { cdeMIBGroups 6 }

cdeMIBCircuitGroup OBJECT-GROUP
    OBJECTS {
              cdeCircuitS1Name,
              cdeCircuitS2Name,
              cdeCircuitS1IdBlock,
              cdeCircuitS1IdNum
            }
    STATUS current
    DESCRIPTION
       "Conformance group for DLSw circuits."
    ::= { cdeMIBGroups 7 }

cdeMIBFastGroup OBJECT-GROUP
    OBJECTS {
              cdeFastS1IfIndex,
              cdeFastS1RouteInfo,
              cdeFastS1CacheId,
              cdeFastS2TDomain,
              cdeFastS2TAddress,
              cdeFastS2CacheId,
              cdeFastOrigin,
              cdeFastTimeToLive
            }
    STATUS current
    DESCRIPTION
       "Conformance group for DLSw Fast Cache entries."
    ::= { cdeMIBGroups 8 }

cdeTrapControlGroup OBJECT-GROUP
    OBJECTS {
              cdeTrapCntlTConn,
              cdeTrapCntlCircuit
            }
    STATUS current
    DESCRIPTION
       "Conformance group for DLSw Trap Control."
     ::= { cdeMIBGroups 9 }

END
