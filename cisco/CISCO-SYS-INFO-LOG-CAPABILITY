CISCO-SYS-INFO-LOG-CAPABILITY DEFINITIONS ::= BEGIN

IMPORTS
        MODULE-IDENTITY, Unsigned32
                FROM SNMPv2-SMI
        AGENT-CAPABILITIES
                FROM SNMPv2-CONF
        SnmpAdminString
                FROM SNMP-FRAMEWORK-MIB
        ciscoAgentCapability
                FROM CISCO-SMI;

ciscoSysInfoLogCapability MODULE-IDENTITY
        LAST-UPDATED    "200508240000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                 CISCO-SYS-INFO-LOG-MIB."

        REVISION        "200508240000Z"
        DESCRIPTION
                "Added capability statement 
                 ciscoSysInfoLogCapCatOSV08R0501.

                 Added VARIATION for csilServerProtocol in 
                 capability statement 
                 ciscoSysInfoLogCapCatOSV08R0101."

        REVISION        "200308010000Z"
        DESCRIPTION
                "Initial version of this MIB module."
        ::= { ciscoAgentCapability 321 }

ciscoSysInfoLogCapCatOSV08R0101 AGENT-CAPABILITIES
    PRODUCT-RELEASE      "Cisco CatOS 8.1(1)."
    STATUS               current
    DESCRIPTION          "CISCO-SYS-INFO-LOG-MIB capabilities."

    SUPPORTS             CISCO-SYS-INFO-LOG-MIB
        INCLUDES         { csilGlobalConfigGroup,
                           csilServerConfigGroup,
                           csilCommandConfigGroup,
                           csilNotifControlGroup,
                           csilLoggingFailNotifGroup }

        VARIATION        csilMaxServerAllowed
            SYNTAX       Unsigned32(1)
            DESCRIPTION  "Only support one logging server."

        VARIATION        csilServerAddressType
            SYNTAX       INTEGER { ipv4(1) }
            DESCRIPTION  "Only support IPv4 addresses."

        VARIATION        csilServerProfileIndex
            SYNTAX       Unsigned32(1)
            DESCRIPTION  "Only support one profile on a server."

        VARIATION        csilServerLoggingFileName
            SYNTAX       SnmpAdminString (SIZE (1..64))
            DESCRIPTION  "Only support file name not exceed 64
                          characters."

        VARIATION        csilServerRcpUserName
            SYNTAX       SnmpAdminString (SIZE (1..40))
            DESCRIPTION  "Only support user name not exceed 40
                          characters. Can not be set as 'root'."

        VARIATION        csilServerInterval
            SYNTAX       Unsigned32 (1..64800)
            DESCRIPTION  "Only support the maximum interval of 45 days."

        VARIATION        csilServerRowStatus
            SYNTAX       INTEGER {active(1)}
            DESCRIPTION  "Only support the value active(1)."

        VARIATION        csilMaxCommandPerProfile
            SYNTAX       Unsigned32(15)
            DESCRIPTION  "Only support maximum 15 commands per profile."

        VARIATION        csilCommandString
            SYNTAX       SnmpAdminString (SIZE (1..48))
            DESCRIPTION  "Only support commands not exceed 48 
                          characters."

        VARIATION        csilServerProtocol
            SYNTAX       INTEGER { tftp(1), rcp(2) }
            DESCRIPTION  "The enumerated values supported are all those
                          defined at the time this clause was written."
    ::= { ciscoSysInfoLogCapability 1 }

ciscoSysInfoLogCapCatOSV08R0501 AGENT-CAPABILITIES
    PRODUCT-RELEASE      "Cisco CatOS 8.5(1)."
    STATUS               current
    DESCRIPTION          "CISCO-SYS-INFO-LOG-MIB capabilities."

    SUPPORTS             CISCO-SYS-INFO-LOG-MIB
        INCLUDES         { csilGlobalConfigGroup, 
                           csilServerConfigGroup,
                           csilCommandConfigGroup,
                           csilNotifControlGroup,
                           csilLoggingFailNotifGroup }

        VARIATION        csilMaxServerAllowed
            SYNTAX       Unsigned32(1)
            DESCRIPTION  "Only limited set of values are supported."

        VARIATION        csilServerAddressType
            SYNTAX       INTEGER { ipv4(1) }
            DESCRIPTION  "Only limited set of values are supported."

        VARIATION        csilServerProfileIndex
            SYNTAX       Unsigned32(1)
            DESCRIPTION  "Only limited set of values are supported."

        VARIATION        csilServerLoggingFileName
            SYNTAX       SnmpAdminString (SIZE (1..64))
            DESCRIPTION  "Only limited set of values are supported."

        VARIATION        csilServerRcpUserName
            SYNTAX       SnmpAdminString (SIZE (1..40))
            DESCRIPTION  "Only limited set of values are supported.
                          User name can not be set to 'root'."

        VARIATION        csilServerInterval
            SYNTAX       Unsigned32 (1..64800)
            DESCRIPTION  "Only limited set of values are supported."

        VARIATION        csilServerRowStatus
            SYNTAX       INTEGER {active(1)}
            DESCRIPTION  "Only limited set of values are supported."

        VARIATION        csilMaxCommandPerProfile
            SYNTAX       Unsigned32(15)
            DESCRIPTION  "Only limited set of values are supported."

        VARIATION        csilCommandString
            SYNTAX       SnmpAdminString (SIZE (1..48))
            DESCRIPTION  "Only limited set of values are supported."

        VARIATION        csilServerProtocol
            SYNTAX       INTEGER { tftp(1), rcp(2), ftp(3) }
            DESCRIPTION  "The enumerated values supported are all those
                          defined at the time this clause was written."
    ::= { ciscoSysInfoLogCapability 2 }
END
