ALTIGA-NAT-STATS-MIB DEFINITIONS ::= BEGIN

   IMPORTS
      MODULE-IDENTITY, OBJECT-TYPE, IpAddress, Integer32, Counter32, Unsigned32
         FROM SNMPv2-SMI
      OBJECT-GROUP, MODULE-COMPLIANCE
         FROM SNMPv2-CONF
      alStatsNat, alNatGroup
         FROM ALTIGA-MIB
      alNatMibModule
         FROM ALTIGA-GLOBAL-REG;

   altigaNatStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"
      DESCRIPTION
         "The Altiga NAT Statistics MIB models counters and objects that are
          of management interest for NAT.

          Acronyms
          The following acronyms are used in this document:

            MIB:        Management Information Base

            NAT:        Network Address Translation
         "

        REVISION "200209051300Z"
        DESCRIPTION
                "Added module compliance."

        REVISION "200207100000Z"
        DESCRIPTION
                "Updated with new header"
      ::= { alNatMibModule 2 }

-- +++++++++++++++++++++++++++++++++++++++++++++++++++++++
-- MIB Objects
-- +++++++++++++++++++++++++++++++++++++++++++++++++++++++

alStatsNatGlobal  OBJECT IDENTIFIER ::= { alStatsNat 1 }

alNatStatsPacketsIn     OBJECT-TYPE
   SYNTAX         Counter32
   MAX-ACCESS     read-only
   STATUS         current
   DESCRIPTION    
          "The total number of inbound packets that have been translated."
   ::= { alStatsNatGlobal 1 }

alNatStatsPacketsOut            OBJECT-TYPE
   SYNTAX         Counter32
   MAX-ACCESS     read-only
   STATUS         current
   DESCRIPTION    
          "The total number of outbound packets that have been translated."
   ::= { alStatsNatGlobal 2 }

alNatStatsTotalTranslations     OBJECT-TYPE
   SYNTAX         Counter32
   MAX-ACCESS     read-only
   STATUS         current
   DESCRIPTION    
          "The total number of sessions that have been established."
   ::= { alStatsNatGlobal 3 }

alNatStatsActiveTranslations    OBJECT-TYPE
   SYNTAX         Counter32
   MAX-ACCESS     read-only
   STATUS         current
   DESCRIPTION    
          "The active number of sessions that are established."
   ::= { alStatsNatGlobal 4 }

alNatStatsMaxTranslations       OBJECT-TYPE
   SYNTAX         Counter32
   MAX-ACCESS     read-only
   STATUS         current
   DESCRIPTION    
          "The maximum number of sessions that have been established at any one time."
   ::= { alStatsNatGlobal 5 }

alNatTranslationTable      OBJECT-TYPE
   SYNTAX            SEQUENCE OF AlNatTranslationEntry
   MAX-ACCESS        not-accessible
   STATUS            current
   DESCRIPTION
      "List of active NAT sessions."
   ::= { alStatsNat 2 }

alNatTranslationEntry      OBJECT-TYPE
   SYNTAX            AlNatTranslationEntry
   MAX-ACCESS        not-accessible
   STATUS            current
   DESCRIPTION 
          "An entry in the alNatTranslationTable."
   INDEX       { alNatTranslationSrcAddress,
                     alNatTranslationSrcPort,
                     alNatTranslationDestAddress,
                     alNatTranslationDestPort}
   ::= { alNatTranslationTable 1 }

AlNatTranslationEntry ::= SEQUENCE {
   alNatTranslationSrcAddress       IpAddress,
   alNatTranslationSrcPort          Integer32,
   alNatTranslationDestAddress      IpAddress,
   alNatTranslationDestPort         Integer32,
   alNatTranslationAddress    IpAddress,
   alNatTranslationPort       Integer32,
   alNatTranslationAge           Unsigned32,
   alNatTranslationType          INTEGER,
   alNatTranslationDirection  INTEGER,
   alNatTranslationBytes      Counter32,
   alNatTranslationPackets    Counter32
}

alNatTranslationSrcAddress OBJECT-TYPE
   SYNTAX         IpAddress
   MAX-ACCESS     read-only
   STATUS         current
   DESCRIPTION
          "The internal source address to be translated."
   ::= { alNatTranslationEntry 1 }

alNatTranslationSrcPort    OBJECT-TYPE
   SYNTAX         Integer32 (0..65535)
   MAX-ACCESS     read-only
   STATUS         current
   DESCRIPTION
          "The internal source port to be translated."
   ::= { alNatTranslationEntry 2 }

alNatTranslationDestAddress   OBJECT-TYPE
   SYNTAX         IpAddress
   MAX-ACCESS     read-only
   STATUS         current
   DESCRIPTION
          "The external destination address."
   ::= { alNatTranslationEntry 3 }

alNatTranslationDestPort   OBJECT-TYPE
   SYNTAX         Integer32 (0..65535)
   MAX-ACCESS     read-only
   STATUS         current
   DESCRIPTION
          "The external destinatin port."
   ::= { alNatTranslationEntry 4 }

alNatTranslationAddress    OBJECT-TYPE
   SYNTAX         IpAddress
   MAX-ACCESS     read-only
   STATUS         current
   DESCRIPTION 
          "The translated internal source address."
   ::= { alNatTranslationEntry 5 }

alNatTranslationPort    OBJECT-TYPE
   SYNTAX         Integer32 (0..65535)
   MAX-ACCESS     read-only
   STATUS         current
   DESCRIPTION
          "The translated internal source port."
   ::= { alNatTranslationEntry 6 }

alNatTranslationAge     OBJECT-TYPE
   SYNTAX         Unsigned32
   MAX-ACCESS     read-only
   STATUS         current
   DESCRIPTION 
               "The age of this entry in seconds."
   ::= { alNatTranslationEntry 7 }

alNatTranslationType    OBJECT-TYPE
   SYNTAX         INTEGER {
               unknown(0),
               portMapTcp (1),
               portMapUdp (2),
               portMapTcpUdp(3),
               noPortMap (4),
               ftpProxy (8),
               tftpProxy (16),
               nbnsTcpProxy (32),
               nbnsUdpProxy (64),
               nbdgsvcProxy (128),
               h225TcpProxy (256),
               h245Proxy(512),
               rasProxy (1024),
               ilsProxy (2048),
               all(4095)
            }
   MAX-ACCESS     read-only
   STATUS         current
   DESCRIPTION
          "The type of this entry."
   ::= { alNatTranslationEntry 8 }

alNatTranslationDirection  OBJECT-TYPE
   SYNTAX         INTEGER {
               inbound (1),
               outbound (2)
               }
   MAX-ACCESS     read-only
   STATUS         current
   DESCRIPTION    
          "The direction that this rule acts upon."
   ::= { alNatTranslationEntry 9 }

alNatTranslationBytes      OBJECT-TYPE
   SYNTAX         Counter32
   MAX-ACCESS     read-only
   STATUS         current
   DESCRIPTION    
          "The total number of bytes that have been translated."
   ::= { alNatTranslationEntry 10 }

alNatTranslationPackets    OBJECT-TYPE
   SYNTAX         Counter32
   MAX-ACCESS     read-only
   STATUS         current
   DESCRIPTION    
          "The total number of packets that have been translated."
   ::= { alNatTranslationEntry 11 }

alNatAllTranslationTable      OBJECT-TYPE
   SYNTAX            SEQUENCE OF AlNatAllTranslationEntry
   MAX-ACCESS        not-accessible
   STATUS            current
   DESCRIPTION
      "List of active NAT sessions."
   ::= { alStatsNat 3 }

alNatAllTranslationEntry      OBJECT-TYPE
   SYNTAX            AlNatAllTranslationEntry
   MAX-ACCESS        not-accessible
   STATUS            current
   DESCRIPTION 
          "An entry in the alNatAllTranslationTable."
   INDEX       { alNatAllTranslationSrcAddress,
                     alNatAllTranslationSrcPort,
                     alNatAllTranslationDestAddress,
                     alNatAllTranslationDestPort,
                  alNatAllTranslationType }
   ::= { alNatAllTranslationTable 1 }

AlNatAllTranslationEntry ::= SEQUENCE {
   alNatAllTranslationSrcAddress       IpAddress,
   alNatAllTranslationSrcPort          Integer32,
   alNatAllTranslationDestAddress      IpAddress,
   alNatAllTranslationDestPort         Integer32,
   alNatAllTranslationAddress    IpAddress,
   alNatAllTranslationPort       Integer32,
   alNatAllTranslationAge           Unsigned32,
   alNatAllTranslationType          INTEGER,
   alNatAllTranslationDirection  INTEGER,
   alNatAllTranslationBytes      Counter32,
   alNatAllTranslationPackets    Counter32
}

alNatAllTranslationSrcAddress OBJECT-TYPE
   SYNTAX         IpAddress
   MAX-ACCESS     read-only
   STATUS         current
   DESCRIPTION
          "The internal source address to be translated."
   ::= { alNatAllTranslationEntry 1 }

alNatAllTranslationSrcPort    OBJECT-TYPE
   SYNTAX         Integer32 (0..65535)
   MAX-ACCESS     read-only
   STATUS         current
   DESCRIPTION
          "The internal source port to be translated."
   ::= { alNatAllTranslationEntry 2 }

alNatAllTranslationDestAddress   OBJECT-TYPE
   SYNTAX         IpAddress
   MAX-ACCESS     read-only
   STATUS         current
   DESCRIPTION
          "The external destination address."
   ::= { alNatAllTranslationEntry 3 }

alNatAllTranslationDestPort   OBJECT-TYPE
   SYNTAX         Integer32 (0..65535)
   MAX-ACCESS     read-only
   STATUS         current
   DESCRIPTION
          "The external destinatin port."
   ::= { alNatAllTranslationEntry 4 }

alNatAllTranslationAddress    OBJECT-TYPE
   SYNTAX         IpAddress
   MAX-ACCESS     read-only
   STATUS         current
   DESCRIPTION 
          "The translated internal source address."
   ::= { alNatAllTranslationEntry 5 }

alNatAllTranslationPort    OBJECT-TYPE
   SYNTAX         Integer32 (0..65535)
   MAX-ACCESS     read-only
   STATUS         current
   DESCRIPTION
          "The translated internal source port."
   ::= { alNatAllTranslationEntry 6 }

alNatAllTranslationAge     OBJECT-TYPE
   SYNTAX         Unsigned32
   MAX-ACCESS     read-only
   STATUS         current
   DESCRIPTION 
               "The age of this entry in seconds."
   ::= { alNatAllTranslationEntry 7 }

alNatAllTranslationType    OBJECT-TYPE
   SYNTAX         INTEGER {
               unknown(0),
               portMapTcp (1),
               portMapUdp (2),
               portMapTcpUdp(3),
               noPortMap (4),
               ftpProxy (8),
               tftpProxy (16),
               nbnsTcpProxy (32),
               nbnsUdpProxy (64),
               nbdgsvcProxy (128),
               h225TcpProxy (256),
               h245Proxy(512),
               rasProxy (1024),
               ilsProxy (2048),
               all(4095)
            }
   MAX-ACCESS     read-only
   STATUS         current
   DESCRIPTION
          "The type of this entry."
   ::= { alNatAllTranslationEntry 8 }

alNatAllTranslationDirection  OBJECT-TYPE
   SYNTAX         INTEGER {
               inbound (1),
               outbound (2)
               }
   MAX-ACCESS     read-only
   STATUS         current
   DESCRIPTION    
          "The direction that this rule acts upon."
   ::= { alNatAllTranslationEntry 9 }

alNatAllTranslationBytes      OBJECT-TYPE
   SYNTAX         Counter32
   MAX-ACCESS     read-only
   STATUS         current
   DESCRIPTION    
          "The total number of bytes that have been translated."
   ::= { alNatAllTranslationEntry 10 }

alNatAllTranslationPackets    OBJECT-TYPE
   SYNTAX         Counter32
   MAX-ACCESS     read-only
   STATUS         current
   DESCRIPTION    
          "The total number of packets that have been translated."
   ::= { alNatAllTranslationEntry 11 }

altigaNatStatsMibConformance OBJECT IDENTIFIER ::= { altigaNatStatsMibModule 1 }
altigaNatStatsMibCompliances OBJECT IDENTIFIER ::= { altigaNatStatsMibConformance 1 }

altigaNatStatsMibCompliance MODULE-COMPLIANCE
   STATUS         current
   DESCRIPTION
      "The compliance statement for agents which 
       implement the Altiga NAT Statistics MIB."
   MODULE
   MANDATORY-GROUPS { 
      altigaNatStatsGroup
   }
   ::= { altigaNatStatsMibCompliances 1 }

altigaNatStatsGroup  OBJECT-GROUP
   OBJECTS
   {
      alNatStatsPacketsIn,
      alNatStatsPacketsOut,
      alNatStatsTotalTranslations,
      alNatStatsActiveTranslations,
      alNatStatsMaxTranslations,
      alNatTranslationSrcAddress,
      alNatTranslationSrcPort,
      alNatTranslationDestAddress,
      alNatTranslationDestPort,
      alNatTranslationAddress,
      alNatTranslationPort,
      alNatTranslationAge,
      alNatTranslationType,
      alNatTranslationDirection,
      alNatTranslationBytes,
      alNatTranslationPackets,
      alNatAllTranslationSrcAddress,
      alNatAllTranslationSrcPort,
      alNatAllTranslationDestAddress,
      alNatAllTranslationDestPort,
      alNatAllTranslationAddress,
      alNatAllTranslationPort,
      alNatAllTranslationAge,
      alNatAllTranslationType,
      alNatAllTranslationDirection,
      alNatAllTranslationBytes,
      alNatAllTranslationPackets
   }
   STATUS current
   DESCRIPTION
          "The objects for NAT statistics"
   ::= { alNatGroup 2 }
END
