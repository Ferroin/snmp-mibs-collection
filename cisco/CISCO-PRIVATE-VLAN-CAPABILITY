CISCO-PRIVATE-VLAN-CAPABILITY DEFINITIONS ::= BEGIN

IMPORTS
        MODULE-IDENTITY
                FROM SNMPv2-SMI
        AGENT-CAPABILITIES
                FROM SNMPv2-CONF
        ciscoAgentCapability
                FROM CISCO-SMI;

ciscoPrivateVlanCapability MODULE-IDENTITY
        LAST-UPDATED    "200403310000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of
                CISCO-PRIVATE-VLAN-MIB."

        REVISION        "200403310000Z"
        DESCRIPTION
                "Initial version of this MIB module."
        ::= { ciscoAgentCapability 402 }

cPrivateVlanCapV12R0111ECat6K AGENT-CAPABILITIES
    PRODUCT-RELEASE     "Cisco IOS 12.1(11E) on Catalyst 6000/6500
                         and Cisco 7600 series devices."
    STATUS              current
    DESCRIPTION         "CISCO-PRIVATE-VLAN-MIB capabilities."

    SUPPORTS            CISCO-PRIVATE-VLAN-MIB
        INCLUDES        { cpvlanVlanGroup, cpvlanPrivatePortGroup,
                          cpvlanPromPortGroup, cpvlanPromPort4kGroup,
                          cpvlanPortModeGroup, cpvlanSVIMappingGroup }
        VARIATION       cpvlanVlanPrivateVlanType
            SYNTAX      INTEGER { normal(1), primary(2),
                                  isolated(3), community(4) }
            DESCRIPTION "Only support normal, primary, isolated, and
                         community."
    ::= { ciscoPrivateVlanCapability 1 }

cPrivateVlanCapCatOSV08R0101 AGENT-CAPABILITIES
    PRODUCT-RELEASE     "Cisco CatOS 8.1(1)."
    STATUS              current
    DESCRIPTION         "CISCO-PRIVATE-VLAN-MIB capabilities."

    SUPPORTS            CISCO-PRIVATE-VLAN-MIB
        INCLUDES        { cpvlanVlanGroup, cpvlanPrivatePortGroup,
                          cpvlanPromPortGroup, cpvlanPromPort4kGroup }
    ::= { ciscoPrivateVlanCapability 2 }

END
