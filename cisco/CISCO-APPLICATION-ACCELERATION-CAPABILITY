CISCO-APPLICATION-ACCELERATION-CAPABILITY DEFINITIONS ::= BEGIN

IMPORTS
    MODULE-IDENTITY
        FROM SNMPv2-SMI
    AGENT-CAPABILITIES
        FROM SNMPv2-CONF
    ciscoAgentCapability
        FROM CISCO-SMI;

ciscoAppAccCapability MODULE-IDENTITY
    LAST-UPDATED    "200807290000Z"
    ORGANIZATION    "Cisco Systems, Inc."
    CONTACT-INFO
            "Cisco Systems
            Customer Service

            Postal: 170 West Tasman Drive
            San Jose, CA  95134
            USA

            Tel: +1 800 553-NETS

            E-mail: cs-avs@cisco.com"
    DESCRIPTION
        "The capabilities description of
        CISCO-APPLICATION-ACCELERATION-MIB."
    REVISION        "200807290000Z"
    DESCRIPTION
        "Added capability statement
        ciscoAppAccCapc4710aceVA1R700 for ACE 4710 Application 
        Control Engine Appliance."
    ::= { ciscoAgentCapability 567 }

ciscoAppAccCapc4710aceVA1R700 AGENT-CAPABILITIES
    PRODUCT-RELEASE "ACSW (Application Control Software) A1(7) for ACE 
                4710 Application Control Engine Appliance."
    STATUS          current
    DESCRIPTION
        "CISCO-APPLICATION-ACCELERATION-MIB capabilities."

    SUPPORTS        CISCO-APPLICATION-ACCELERATION-MIB
    INCLUDES        { caaMIBStatsGroup }
    VARIATION       caaState
    ACCESS          not-implemented
    DESCRIPTION
        "Not supported."

    VARIATION       caaRequests
    ACCESS          not-implemented
    DESCRIPTION
        "Not supported."

    VARIATION       caaLastRestartedTime
    ACCESS          not-implemented
    DESCRIPTION
        "Not supported."

    VARIATION       caaRequestSize
    ACCESS          not-implemented
    DESCRIPTION
        "Not supported."
    ::= { ciscoAppAccCapability 1 }

END
