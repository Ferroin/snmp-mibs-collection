CISCO-FLEX-LINKS-CAPABILITY DEFINITIONS ::= BEGIN

IMPORTS
        MODULE-IDENTITY,
        Unsigned32
                FROM SNMPv2-SMI
        RowStatus
                FROM SNMPv2-TC
        AGENT-CAPABILITIES
                FROM SNMPv2-CONF
        ciscoAgentCapability
                FROM CISCO-SMI;

ciscoFlexLinksCapability MODULE-IDENTITY
        LAST-UPDATED    "201005180000Z"
        ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com"
        DESCRIPTION
                "The capabilities description of CISCO-FLEX-LINKS-MIB."
        REVISION        "201005180000Z"
        DESCRIPTION
                "Added cFlexLinksCapV12R0254SGPCat4K.

                 Updated cFlexLinksCapV12R0218SXFPCat6k with
                 VARIATION clause of cflIfConfigStatus."
        REVISION        "200507280000Z"
        DESCRIPTION
                "Added cFlexLinksCapV12R0218SXFPCat6k."
        REVISION        "200506220000Z"
        DESCRIPTION
                "Initial version of this MIB module."
        ::= { ciscoAgentCapability 444 }

ciscoFlexLinksCapCatOSV08R0501 AGENT-CAPABILITIES
    PRODUCT-RELEASE     "Cisco CatOS 8.5(1)."
    STATUS              current
    DESCRIPTION         "CISCO-FLEX-LINKS-MIB capabilities."

    SUPPORTS            CISCO-FLEX-LINKS-MIB
        INCLUDES        { ciscoFlexLinksIfConfigGroup,
                          ciscoFlexLinksIfStatusGroup,
                          ciscoFlexLinksEnableNotifGroup,
                          ciscoFlexLinksNotifGroup
                        }

        VARIATION       cflIfConfigStorageType
            ACCESS      read-only
            DESCRIPTION "Unable to set this on CatOS."
    ::= { ciscoFlexLinksCapability 1 }

cFlexLinksCapV12R0218SXFPCat6k AGENT-CAPABILITIES
    PRODUCT-RELEASE     "Cisco IOS 12.2(18)SXF on Catalyst 6000/6500
                         and Cisco 7600 series devices."
    STATUS              current
    DESCRIPTION         "CISCO-FLEX-LINKS-MIB capabilities."

    SUPPORTS            CISCO-FLEX-LINKS-MIB
        INCLUDES        { ciscoFlexLinksIfConfigGroup,
                          ciscoFlexLinksIfStatusGroup,
                          ciscoFlexLinksEnableNotifGroup,
                          ciscoFlexLinksNotifGroup
                        }

        VARIATION       cflIfConfigStorageType
            ACCESS      read-only
            DESCRIPTION "Write access is not supported."

        VARIATION       cflIfConfigStatus
            SYNTAX      RowStatus  {
                            active(1),
                            createAndGo(4),
                            destroy(6)
                        }
            DESCRIPTION "Only limited set of enumerated values
                        is supported."
    ::= { ciscoFlexLinksCapability 2 }

cFlexLinksCapV12R0254SGPCat4K AGENT-CAPABILITIES
    PRODUCT-RELEASE     "Cisco IOS 12.2(54)SG on CAT4K family switches."
    STATUS              current
    DESCRIPTION         "CISCO-FLEX-LINKS-MIB capabilities."

    SUPPORTS            CISCO-FLEX-LINKS-MIB
        INCLUDES        { ciscoFlexLinksIfConfigGroup,
                          ciscoFlexLinksIfStatusGroup,
                          ciscoFlexLinksEnableNotifGroup,
                          ciscoFlexLinksNotifGroup,
                          ciscoFlexLinksMmuPrimaryVlanGroup,
                          ciscoFlexLinksPreemptionGroup,
                          ciscoFlexLinksPreferVlanGroup
                        }

        VARIATION       cflIfConfigStorageType
            ACCESS      read-only
            DESCRIPTION "Write access is not supported."

        VARIATION       cflIfConfigStatus
            SYNTAX      RowStatus  {
                            active(1),
                            createAndGo(4),
                            destroy(6)
                        }
            DESCRIPTION "Only limited set of enumerated values
                        is supported."

        VARIATION       cflIfConfigPreemptionDelay
            SYNTAX      Unsigned32 ( 1..300 )
            DESCRIPTION "Only limited set of values is supported."
    ::= { ciscoFlexLinksCapability 3 }

END
