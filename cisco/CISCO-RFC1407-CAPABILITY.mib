CISCO-RFC1407-CAPABILITY DEFINITIONS ::= BEGIN

IMPORTS
	MODULE-IDENTITY
		FROM SNMPv2-SMI
	AGENT-CAPABILITIES
		FROM SNMPv2-CONF
	ciscoAgentCapability
		FROM CISCO-SMI;

ciscoRFC1407Capability MODULE-IDENTITY
		LAST-UPDATED	"200108170000Z"
		ORGANIZATION    "Cisco Systems, Inc."
		CONTACT-INFO
			"	Cisco Systems
				Customer Service

			Postal:	170 West Tasman Drive
				San Jose, CA  95134
				USA

			   Tel:	+1 800 553-NETS

			E-mail:	cs-snmp@cisco.com"
		DESCRIPTION
			"Agent capabilities for RFC1407-MIB (DS3 MIB)"
                REVISION        "200108170000Z"
                DESCRIPTION
                        "Support SET operation for dsx3LoopbackConfig object."
		REVISION	"9606190000Z"
		DESCRIPTION
			"Initial version of this MIB module."
		::= { ciscoAgentCapability 102 }

ciscoRFC1407CapabilityV11R02 AGENT-CAPABILITIES

PRODUCT-RELEASE "Cisco IOS 11.2"
STATUS		current
DESCRIPTION	"ds3 capabilities"

SUPPORTS	RFC1407-MIB
INCLUDES	{ ds3Group }

               -- the DS3/E3 Configuration

VARIATION	dsx3LineCoding
ACCESS		read-only
DESCRIPTION	"Unable to create or modify"

VARIATION	dsx3SendCode
ACCESS		read-only 
DESCRIPTION	"Unable to create or modify"

VARIATION	dsx3LoopbackConfig
ACCESS		read-only
DESCRIPTION	"Unable to create or modify"

VARIATION	dsx3CircuitIdentifier
ACCESS		read-only
DESCRIPTION	"Unable to create or modify"

          -- the DS3/E3 Current is supported

          -- the DS3/E3 Interval is supported

          -- the DS3/E3 Total is supported

VARIATION	dsx3FarEndLineIndex
ACCESS		not-implemented
DESCRIPTION	"Table for dsx3FarEndConfigEntry not supported"

VARIATION	dsx3FarEndEquipCode
ACCESS		not-implemented
DESCRIPTION	"Table for dsx3FarEndConfigEntry not supported"

VARIATION	dsx3FarEndLocationIDCode
ACCESS		not-implemented
DESCRIPTION	"Table for dsx3FarEndConfigEntry not supported"

VARIATION	dsx3FarEndFrameIDCode
ACCESS		not-implemented
DESCRIPTION	"Table for dsx3FarEndConfigEntry not supported"

VARIATION	dsx3FarEndUnitCode
ACCESS		not-implemented
DESCRIPTION	"Table for dsx3FarEndConfigEntry not supported"

VARIATION	dsx3FarEndFacilityIDCode
ACCESS		not-implemented
DESCRIPTION	"Table for dsx3FarEndConfigEntry not supported"

VARIATION	dsx3FarEndCurrentIndex
ACCESS		not-implemented
DESCRIPTION	"Table for Dsx3FarEndCurrentEntry not supported"

VARIATION	dsx3FarEndTimeElapsed
ACCESS		not-implemented
DESCRIPTION	"Table for Dsx3FarEndCurrentEntry not supported"

VARIATION	dsx3FarEndValidIntervals
ACCESS		not-implemented
DESCRIPTION	"Table for Dsx3FarEndCurrentEntry not supported"

VARIATION	dsx3FarEndCurrentCESs
ACCESS		not-implemented
DESCRIPTION	"Table for Dsx3FarEndCurrentEntry not supported"

VARIATION	dsx3FarEndCurrentCSESs
ACCESS		not-implemented
DESCRIPTION	"Table for Dsx3FarEndCurrentEntry not supported"

VARIATION	dsx3FarEndCurrentCCVs
ACCESS		not-implemented
DESCRIPTION	"Table for Dsx3FarEndCurrentEntry not supported"

VARIATION	dsx3FarEndCurrentUASs
ACCESS		not-implemented
DESCRIPTION	"Table for Dsx3FarEndCurrentEntry not supported"

VARIATION	dsx3FarEndIntervalIndex
ACCESS		not-implemented
DESCRIPTION	"Table for Dsx3FarEndIntervalEntry not supported"

VARIATION	dsx3FarEndIntervalNumber
ACCESS		not-implemented
DESCRIPTION	"Table for Dsx3FarEndIntervalEntry not supported"

VARIATION	dsx3FarEndIntervalCESs
ACCESS		not-implemented
DESCRIPTION	"Table for Dsx3FarEndIntervalEntry not supported"

VARIATION	dsx3FarEndIntervalCSESs
ACCESS		not-implemented
DESCRIPTION	"Table for Dsx3FarEndIntervalEntry not supported"

VARIATION	dsx3FarEndIntervalCCVs
ACCESS		not-implemented
DESCRIPTION	"Table for Dsx3FarEndIntervalEntry not supported"

VARIATION	dsx3FarEndIntervalUASs
ACCESS		not-implemented
DESCRIPTION	"Table for Dsx3FarEndIntervalEntry not supported"

VARIATION	dsx3FarEndTotalIndex
ACCESS		not-implemented
DESCRIPTION	"Table for Dsx3FarEndTotalEntry not supported"

VARIATION	dsx3FarEndTotalCESs
ACCESS		not-implemented
DESCRIPTION	"Table for Dsx3FarEndTotalEntry not supported"

VARIATION	dsx3FarEndTotalCSESs
ACCESS		not-implemented
DESCRIPTION	"Table for Dsx3FarEndTotalEntry not supported"

VARIATION	dsx3FarEndTotalCCVs
ACCESS		not-implemented
DESCRIPTION	"Table for Dsx3FarEndTotalEntry not supported"

VARIATION	dsx3FarEndTotalUASs
ACCESS		not-implemented
DESCRIPTION	"Table for Dsx3FarEndTotalEntry not supported"
	::= { ciscoRFC1407Capability 1 }

ciscoRFC1407CapabilityV122R12 AGENT-CAPABILITIES

PRODUCT-RELEASE "Cisco IOS 12.2(12)T"
STATUS          current
DESCRIPTION     "ds3 capabilities"

SUPPORTS        RFC1407-MIB
INCLUDES        { ds3Group }

               -- the DS3/E3 Configuration

VARIATION       dsx3LineCoding
ACCESS          read-only
DESCRIPTION     "Unable to create or modify"

VARIATION       dsx3SendCode
ACCESS          read-only 
DESCRIPTION     "Unable to create or modify"

VARIATION       dsx3CircuitIdentifier
ACCESS          read-only
DESCRIPTION     "Unable to create or modify"

          -- the DS3/E3 Current is supported

          -- the DS3/E3 Interval is supported

          -- the DS3/E3 Total is supported

VARIATION       dsx3FarEndLineIndex
ACCESS          not-implemented
DESCRIPTION     "Table for dsx3FarEndConfigEntry not supported"

VARIATION       dsx3FarEndEquipCode
ACCESS          not-implemented
DESCRIPTION     "Table for dsx3FarEndConfigEntry not supported"

VARIATION       dsx3FarEndLocationIDCode
ACCESS          not-implemented
DESCRIPTION     "Table for dsx3FarEndConfigEntry not supported"

VARIATION       dsx3FarEndFrameIDCode
ACCESS          not-implemented
DESCRIPTION     "Table for dsx3FarEndConfigEntry not supported"

VARIATION       dsx3FarEndUnitCode
ACCESS          not-implemented
DESCRIPTION     "Table for dsx3FarEndConfigEntry not supported"

VARIATION       dsx3FarEndFacilityIDCode
ACCESS          not-implemented
DESCRIPTION     "Table for dsx3FarEndConfigEntry not supported"

VARIATION       dsx3FarEndCurrentIndex
ACCESS          not-implemented
DESCRIPTION     "Table for Dsx3FarEndCurrentEntry not supported"

VARIATION       dsx3FarEndTimeElapsed
ACCESS          not-implemented
DESCRIPTION     "Table for Dsx3FarEndCurrentEntry not supported"

VARIATION       dsx3FarEndValidIntervals
ACCESS          not-implemented
DESCRIPTION     "Table for Dsx3FarEndCurrentEntry not supported"

VARIATION       dsx3FarEndCurrentCESs
ACCESS          not-implemented
DESCRIPTION     "Table for Dsx3FarEndCurrentEntry not supported"

VARIATION       dsx3FarEndCurrentCSESs
ACCESS          not-implemented
DESCRIPTION     "Table for Dsx3FarEndCurrentEntry not supported"

VARIATION       dsx3FarEndCurrentCCVs
ACCESS          not-implemented
DESCRIPTION     "Table for Dsx3FarEndCurrentEntry not supported"

VARIATION       dsx3FarEndCurrentUASs
ACCESS          not-implemented
DESCRIPTION     "Table for Dsx3FarEndCurrentEntry not supported"

VARIATION       dsx3FarEndIntervalIndex
ACCESS          not-implemented
DESCRIPTION     "Table for Dsx3FarEndIntervalEntry not supported"

VARIATION       dsx3FarEndIntervalNumber
ACCESS          not-implemented
DESCRIPTION     "Table for Dsx3FarEndIntervalEntry not supported"

VARIATION       dsx3FarEndIntervalCESs
ACCESS          not-implemented
DESCRIPTION     "Table for Dsx3FarEndIntervalEntry not supported"

VARIATION       dsx3FarEndIntervalCSESs
ACCESS          not-implemented
DESCRIPTION     "Table for Dsx3FarEndIntervalEntry not supported"

VARIATION       dsx3FarEndIntervalCCVs
ACCESS          not-implemented
DESCRIPTION     "Table for Dsx3FarEndIntervalEntry not supported"

VARIATION       dsx3FarEndIntervalUASs
ACCESS          not-implemented
DESCRIPTION     "Table for Dsx3FarEndIntervalEntry not supported"

VARIATION       dsx3FarEndTotalIndex
ACCESS          not-implemented
DESCRIPTION     "Table for Dsx3FarEndTotalEntry not supported"

VARIATION       dsx3FarEndTotalCESs
ACCESS          not-implemented
DESCRIPTION     "Table for Dsx3FarEndTotalEntry not supported"

VARIATION       dsx3FarEndTotalCSESs
ACCESS          not-implemented
DESCRIPTION     "Table for Dsx3FarEndTotalEntry not supported"

VARIATION       dsx3FarEndTotalCCVs
ACCESS          not-implemented
DESCRIPTION     "Table for Dsx3FarEndTotalEntry not supported"

VARIATION       dsx3FarEndTotalUASs
ACCESS          not-implemented
DESCRIPTION     "Table for Dsx3FarEndTotalEntry not supported"
	::= { ciscoRFC1407Capability 2 }
END
