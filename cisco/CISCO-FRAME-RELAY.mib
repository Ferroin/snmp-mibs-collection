CISCO-FRAME-RELAY-MIB DEFINITIONS ::= BEGIN

IMPORTS
        MODULE-IDENTITY,
        OBJECT-TYPE,
        Counter32,
        Integer32,
        IpAddress
                FROM SNMPv2-SMI
        MODULE-COMPLIANCE,
        OBJECT-GROUP
                FROM SNMPv2-CONF
        TEXTUAL-CONVENTION,
        DisplayString,
        TruthValue
                FROM SNMPv2-TC
        ciscoMgmt
                FROM CISCO-SMI
        InterfaceIndex
                FROM IF-MIB
        ifIndex
               FROM RFC1213-MIB
        frDlcmiEntry,
        frCircuitEntry,
        frCircuitIfIndex,
        frCircuitDlci
                FROM RFC1315-MIB;

-- All table indicies in this MIB that involve interface index and
-- DLCI are derived from frCircuitIfIndex and frCircuitDlci 
-- respectively from RFC 1315.

ciscoFrameRelayMIB     MODULE-IDENTITY
        LAST-UPDATED   "200010130000Z"
        ORGANIZATION   "Cisco Systems, Inc."
        CONTACT-INFO
                "       Cisco Systems
                        Customer Service

                Postal: 170 W Tasman Drive
                        San Jose, CA  95134
                        USA

                   Tel: +1 800 553-NETS

                E-mail: cs-framerelay@cisco.com"
        DESCRIPTION
                "Cisco Frame Relay MIB"

        REVISION        "200010130000Z"
        DESCRIPTION
                "(1) Added objects of FR Switching, FR Fragmentation 
                and FR/ATM Interworking.
                (2) Objects for per PVC I/O rate is added to 
                cfrExtCircuitTable"

        REVISION        "200005220000Z"
        DESCRIPTION
                "(1) Added  ELMI subgroup for ELMI objects."

        REVISION        "200005160000Z"
        DESCRIPTION
                "(1) Added Traffic Shaping parameter objects to
                cfrExtCircuitTable.
                (2) Deprecated cfrSvcMinThruputOut and 
                cfrSvcMinThruputIn. Added cfrExtCircuitMinThruputOut 
                and cfrExtCircuitMinThruputIn in cfrExtCircuitTable 
                inorder to make them applicable to both PVC/SVC. 
                (3) Added cfrExtCircuitBandwidth object to 
                cfrExtCircuitTable."

        REVISION        "200004260000Z"
        DESCRIPTION
                "(1) add an integer value for cfrMapPayloadCompressType;
                (2) reword the Description statements for 
                      { cfrMapPayloadCompressType,
                      cfrExtCircuitUncompressIns,
                      cfrExtCircuitUncompressOuts }
                so that they are not limited to software compression."

        REVISION        "9908210000Z"
        DESCRIPTION
                "(1) Added cfrExtCircuitUncompressOuts and
                cfrExtCircuitUncompressIns to the circuit subgroup;
                (2) Added cfrMapRtpHdrCompress and cfrMapPayloadCompressType
                to the mapping subgroup;
                (3) cfrMapPayloadCompress becomes deprecated, obsoleted
                by cfrMapPayloadCompressType;
                (4) frCircuitSentOctets and frCircuitReceivedOctets
                per RFC1315 will reflect the number of bytes in Frame Relay
                frames sent to and received from the physical layer. Same
                effect is applied to ifOutOctets and ifInOctets as well
                when ifIndex refers to a Frame Relay subinterface."

        REVISION        "9608150000Z"
        DESCRIPTION
                "Initial version of this MIB module."
        ::= { ciscoMgmt 49 }

ciscoFrMIBObjects OBJECT IDENTIFIER ::= { ciscoFrameRelayMIB 1 }

-- Subgroups:
-- The objects include four subgroups on the topics of
--        o LMI (Local Management Interface, see ANSI T1.617 Annex D and
--          the Frame Relay Specification with Extensions by DEC,
--          NT, StrataCom, and Cisco.),
--        o Virtual circuits,
--        o Circuit mapping information, 
--        o SVC (switched virtual circuits, see CCITT/ITU Q.933 and 
--           Q.922.),
--        o ELMI (Enhanced Link Management Interface) objects,
--        o Fragmentation objects,
--        o Frame Relay/ATM Network Interworking objects,
--        o Frame Relay/ATM PVC Service Interworking objects, and
--        o Frame Relay Switching objects.

cfrLmiObjs        OBJECT IDENTIFIER ::= { ciscoFrMIBObjects 1 }

cfrCircuitObjs    OBJECT IDENTIFIER ::= { ciscoFrMIBObjects 2 }

cfrMapObjs        OBJECT IDENTIFIER ::= { ciscoFrMIBObjects 3 }

cfrSvcObjs        OBJECT IDENTIFIER ::= { ciscoFrMIBObjects 4 }

cfrElmiObjs       OBJECT IDENTIFIER ::= { ciscoFrMIBObjects 5 }

cfrFragObjs       OBJECT IDENTIFIER ::= { ciscoFrMIBObjects 6 }

cfrConnectionObjs  OBJECT IDENTIFIER ::= { ciscoFrMIBObjects 7 }

DlciNumber ::= TEXTUAL-CONVENTION
        STATUS  current
        DESCRIPTION
                "Numerical format of Data Link Connection Identifier
                (DLCI) in decimal, identical to the 'DLCI' as INTEGER
                of 0..DLCINumber in RFC1315. The maximum value depends
                on Frame Relay implementation, which is currently set
                to be 1023 for 2-octet address format per UNI
                Implementation Agreement FRF.1."
        SYNTAX        INTEGER (0..1023)

CfrMapProtocols ::= TEXTUAL-CONVENTION
        STATUS  current
        DESCRIPTION
                "Cisco link types (network protocols) that run
                over Frame Relay. Associated values, except for
                wildcard, match assigned values of internal software
                respectively."
        SYNTAX  INTEGER
        {
                arp(1),
                serialArp(6),
                ip(7),
                xns(10),
                novell(11),
                apollo(12),
                vines(13),
                appletalk(16),
                ieeeSpanning(18),
                decnet(22),
                clns(25),
                rsrb(37),
                bridge(38),
                stun(39),
                frArp(40),
                uncompressedTcp(47),
                compressedTcp(48),
                llc2(49),
                frSwitch(53),
                dlsw(63),
                nhrp(74),
                compressedRtp(83),
                wildcard(999)        -- either means no applicable type for
                                -- the circuit or means point-to-point
        }

-- LMI sub-group {

cfrLmiTable OBJECT-TYPE
        SYNTAX      SEQUENCE OF CfrLmiEntry
        MAX-ACCESS  not-accessible
        STATUS      current
        DESCRIPTION
                "Table of Frame Relay LMI information that are
                either supplemental to the frDlcmiTable of RFC 1315
                or specific to Cisco's implementation."
        REFERENCE
                "American National Standard T1.617-1991, Annex D"
        ::= { cfrLmiObjs 1 }

cfrLmiEntry OBJECT-TYPE
        SYNTAX      CfrLmiEntry
        MAX-ACCESS  not-accessible
        STATUS      current
        DESCRIPTION
                "Each entry of the table contains information
                of Frame Relay LMI over one physical interface.
                They are mostly FR generic and some Cisco specific."
        AUGMENTS { frDlcmiEntry }
        ::= { cfrLmiTable 1 }

CfrLmiEntry ::=
        SEQUENCE {
            cfrLmiLinkstatus             INTEGER,
            cfrLmiLinkType               INTEGER,
            cfrLmiEnquiryIns             Counter32,
            cfrLmiEnquiryOuts            Counter32,
            cfrLmiStatusIns              Counter32,
            cfrLmiStatusOuts             Counter32,
            cfrLmiUpdateStatusIns        Counter32,
            cfrLmiUpdateStatusOuts       Counter32,
            cfrLmiStatusTimeouts         Counter32,
            cfrLmiStatusEnqTimeouts      Counter32,
            cfrLmiN392Dce                INTEGER,
            cfrLmiN393Dce                INTEGER,
            cfrLmiT392Dce                INTEGER
        }

-- Note: for LMI type, i.e. ANSI or Cisco, see frDlcmiState
-- of RFC 1315. Also, for LMI parameters for DTE not listed here,
-- e.g. T391, N391, N392, and N393, see RFC 1315.
--
-- Although based on the current logic the value for
-- cfrLmiDLstatus is equivalent to ifOperStatus, the object
-- remains herein for future possible development change.

cfrLmiLinkstatus OBJECT-TYPE
        SYNTAX  INTEGER {
                    up(1),
                    down(2)
                }
        MAX-ACCESS  read-only
        STATUS      current
        DESCRIPTION
                "Data link status via LMI."
        ::= { cfrLmiEntry 1 }

cfrLmiLinkType OBJECT-TYPE
        SYNTAX  INTEGER {
                    dte(1),
                    dce(2),
                    nni(3)
                }
        MAX-ACCESS  read-only
        STATUS      current
        DESCRIPTION
                "Frame Relay link type."
        ::= { cfrLmiEntry 2 }

cfrLmiEnquiryIns OBJECT-TYPE
        SYNTAX      Counter32
        UNITS       "messages"
        MAX-ACCESS  read-only
        STATUS      current
        DESCRIPTION
                "Number of Status Enquiry messages received."
        ::= { cfrLmiEntry 3 }

cfrLmiEnquiryOuts OBJECT-TYPE
        SYNTAX      Counter32
        UNITS       "messages"
        MAX-ACCESS  read-only
        STATUS      current
        DESCRIPTION
                "Number of Status Enquiry messages sent."
        ::= { cfrLmiEntry 4 }

cfrLmiStatusIns OBJECT-TYPE
        SYNTAX      Counter32
        UNITS       "messages"
        MAX-ACCESS  read-only
        STATUS      current
        DESCRIPTION
                "Number of Status messages received."
        ::= { cfrLmiEntry 5 }

cfrLmiStatusOuts OBJECT-TYPE
        SYNTAX      Counter32
        UNITS       "messages"
        MAX-ACCESS  read-only
        STATUS      current
        DESCRIPTION
                "Number of Status messages sent."
        ::= { cfrLmiEntry 6 }

cfrLmiUpdateStatusIns OBJECT-TYPE
        SYNTAX      Counter32
        UNITS       "messages"
        MAX-ACCESS  read-only
        STATUS      current
        DESCRIPTION
                "Number of Update Status messages received."
        ::= { cfrLmiEntry 7 }

cfrLmiUpdateStatusOuts OBJECT-TYPE
        SYNTAX      Counter32
        UNITS       "messages"
        MAX-ACCESS  read-only
        STATUS      current
        DESCRIPTION
                "Number of Update Status messages sent"
        ::= { cfrLmiEntry 8 }

cfrLmiStatusTimeouts OBJECT-TYPE
        SYNTAX      Counter32
        UNITS       "times"
        MAX-ACCESS  read-only
        STATUS      current
        DESCRIPTION
                "Number of times when timeout occurred on waiting
                for Status message"
        ::= { cfrLmiEntry 9 }

cfrLmiStatusEnqTimeouts OBJECT-TYPE
        SYNTAX      Counter32
        UNITS       "times"
        MAX-ACCESS  read-only
        STATUS      current
        DESCRIPTION
                "Number of times when timeout occurred on waiting
                for Status Enquiry message"
        ::= { cfrLmiEntry 10 }

cfrLmiN392Dce OBJECT-TYPE
        SYNTAX      INTEGER (0..10)
        MAX-ACCESS  read-only
        STATUS      current
        DESCRIPTION
                "LMI error threshold for DCE interface.
                For DTE, value becomes 0."
        ::= { cfrLmiEntry 11 }

cfrLmiN393Dce OBJECT-TYPE
        SYNTAX      INTEGER (0..10)
        MAX-ACCESS  read-only
        STATUS      current
        DESCRIPTION
                "LMI monitored event count for DCE interface.
                For DTE, value becomes zero (0)."
        ::= { cfrLmiEntry 12 }

cfrLmiT392Dce OBJECT-TYPE
        SYNTAX      INTEGER (0..30)
        UNITS       "seconds"
        MAX-ACCESS  read-only
        STATUS      current
        DESCRIPTION
                "DCE polling verification timer for DCE interface
                For DTE, the value becomes zero (0)."
        ::= { cfrLmiEntry 13 }

-- end LMI subgroup }

-- Circut sub-group {

cfrCircuitTable OBJECT-TYPE
        SYNTAX      SEQUENCE OF CfrCircuitEntry
        MAX-ACCESS  not-accessible
        STATUS      current
        DESCRIPTION
                "Table of descriptive and statistics information
                that are generic to Frame Relay virtual circuits."
        ::= { cfrCircuitObjs 1 }

cfrCircuitEntry OBJECT-TYPE
        SYNTAX      CfrCircuitEntry
        MAX-ACCESS  not-accessible
        STATUS      current
        DESCRIPTION
                "Each entry of the table contains information of a
                circuit that are not included in frCircuitTable of
                RFC1315 but are generic to Frame Relay."
        AUGMENTS { frCircuitEntry }
                -- indexed by { frCircuitIfIndex, frCircuitDlci }
        ::= { cfrCircuitTable 1 }

CfrCircuitEntry ::=
        SEQUENCE {
            cfrCircuitDEins              Counter32,
            cfrCircuitDEouts             Counter32,
            cfrCircuitDropPktsOuts       Counter32,
            cfrCircuitType               INTEGER
        }

cfrCircuitDEins OBJECT-TYPE
        SYNTAX      Counter32
        UNITS       "packets"
        MAX-ACCESS  read-only
        STATUS      current
        DESCRIPTION
                "Number of packets received with the Discarded
                Eligibility indictor (the DE bit) set."
        ::= { cfrCircuitEntry 1 }

cfrCircuitDEouts OBJECT-TYPE
        SYNTAX      Counter32
        UNITS       "packets"
        MAX-ACCESS  read-only
        STATUS      current
        DESCRIPTION
                "Number of packets transmitted with DE bit set."
        ::= { cfrCircuitEntry 2 }

cfrCircuitDropPktsOuts OBJECT-TYPE
        SYNTAX      Counter32
        UNITS       "packets"
        MAX-ACCESS  read-only
        STATUS      current
        DESCRIPTION
                "Number of discarded packets that were to be sent."
        ::= { cfrCircuitEntry 3 }

cfrCircuitType OBJECT-TYPE
        SYNTAX  INTEGER
                {
                    pvc(1),        -- permanent virtual circuit
                    svc(2)        -- switched virtual circuit
                }
        MAX-ACCESS  read-only
        STATUS      current
        DESCRIPTION
                "Basic circuit type"
        ::= { cfrCircuitEntry 4 }

-- Cisco specific circuit information:

cfrExtCircuitTable  OBJECT-TYPE
        SYNTAX      SEQUENCE OF CfrExtCircuitEntry
        MAX-ACCESS  not-accessible
        STATUS      current
        DESCRIPTION
                "Table of Cisco implementation specific FR
                circuit information. This is a Cisco extension
                for the frCircuitTable of RFC 1315."
        ::= { cfrCircuitObjs 2 }

cfrExtCircuitEntry  OBJECT-TYPE
        SYNTAX      CfrExtCircuitEntry
        MAX-ACCESS  not-accessible
        STATUS      current
        DESCRIPTION
                "Each entry of the table contains information
                of a Frame Relay virtual circuit that are specific
                to Cisco implementation."
        AUGMENTS { frCircuitEntry }
                -- indexed by { frCircuitIfIndex, frCircuitDlci }
        ::= { cfrExtCircuitTable 1 }

CfrExtCircuitEntry ::=
        SEQUENCE {
            cfrExtCircuitIfName             DisplayString,
            cfrExtCircuitIfType             INTEGER,
            cfrExtCircuitSubifIndex         InterfaceIndex,
            cfrExtCircuitMapStatus          INTEGER,
            cfrExtCircuitCreateType         INTEGER,
            cfrExtCircuitMulticast          TruthValue,
            cfrExtCircuitRoutedDlci         DlciNumber,
            cfrExtCircuitRoutedIf           InterfaceIndex,
            cfrExtCircuitUncompressIns      Counter32,
            cfrExtCircuitUncompressOuts     Counter32,
            cfrExtCircuitFECNOuts           Counter32,
            cfrExtCircuitBECNOuts           Counter32,
            cfrExtCircuitMinThruputOut      Integer32,
            cfrExtCircuitMinThruputIn       Integer32,
            cfrExtCircuitBcastPktOuts       Counter32,
            cfrExtCircuitBcastByteOuts      Counter32,
            cfrExtCircuitBandwidth          Integer32,
            cfrExtCircuitShapeByteLimit     Integer32,
            cfrExtCircuitShapeInterval      Integer32,
            cfrExtCircuitShapeByteIncrement Integer32,
            cfrExtCircuitShapePkts          Counter32,
            cfrExtCircuitShapeBytes         Counter32,
            cfrExtCircuitShapePktsDelay     Counter32,
            cfrExtCircuitShapeBytesDelay    Counter32,
            cfrExtCircuitShapeActive        TruthValue,
            cfrExtCircuitShapeAdapting      INTEGER,
            cfrExtCircuitTxDataRate         INTEGER,
            cfrExtCircuitTxPktRate          INTEGER,
            cfrExtCircuitRcvDataRate        INTEGER,
            cfrExtCircuitRcvPktRate         INTEGER
        }

cfrExtCircuitIfName  OBJECT-TYPE
        SYNTAX       DisplayString
        MAX-ACCESS   read-only
        STATUS       current
        DESCRIPTION
                "The textual name of the main interface or the 
                subinterface that this DLCI is associated with.
                This is the same name string of an interface used
                in the configuration and all console displays,
                such as 'serial 0', 'serial 3/0.3', etc."
        ::= { cfrExtCircuitEntry 1 }

cfrExtCircuitIfType  OBJECT-TYPE
        SYNTAX  INTEGER {
                  mainInterface(1),
                  pointToPoint(2),        -- subinterface
                  multipoint(3)           -- subinterface
                }
        MAX-ACCESS  read-only
        STATUS      current
        DESCRIPTION
                "Type of the subinterface this DLCI is associated
                with, if configured."
        ::= { cfrExtCircuitEntry 2 }

cfrExtCircuitSubifIndex OBJECT-TYPE
        SYNTAX      InterfaceIndex
        MAX-ACCESS  read-only
        STATUS      current
        DESCRIPTION
                "For value greater than zero (0), it indicates
                the network management interface index
                for the subinterface associated with
                this DLCI. Value 0 means the DLCI is not
                associated with any subinterface." 
        ::= { cfrExtCircuitEntry 3 }

cfrExtCircuitMapStatus OBJECT-TYPE
        SYNTAX      INTEGER (0..2047)
        MAX-ACCESS  read-only
        STATUS      current
        DESCRIPTION
                "The mapping protocols (internally considered as
                the 'link type') applied on this circuit.
                The value ranges from 0 to 2047.
                For point-to-point DLCI, the value stays zero.
                Otherwise, the value is a sum. It initially takes
                the value zero, then, for each type of Protocol,
                2 raised to a power is added to the sum.
                The following table presents respective power and
                equivalent value for each applicable type:

                        Protocol        Power    Value
                        --------        -----    -----
                        IP              0        1
                        IPX             1        2
                        Appletalk       2        4
                        XNS             3        8
                        VINES           4        16
                        DECnet          5        32
                        CLNS            6        64
                        Bridging        7        128
                        RSRB            8        256
                        STUN            9        512
                        LLC2            10       1024

                For example, value 3 means the circuit's mapping
                protocols include IP and IPX. (3 = 2**1 + 2**0,
                where 0 corresponds to IP and 1 to IPX.) Value 0
                means there is currently no mapping protocol for
                the circuit.
                See cfrMapTable for more mapping information."
        ::= { cfrExtCircuitEntry 4 }

cfrExtCircuitCreateType OBJECT-TYPE
        SYNTAX  INTEGER
                {
                    dynamic(1),      -- PVC established through LMI
                                     -- or an SVC established through
                                     -- SVC signalling
                    static(2)        -- circuit was configured
                }
        MAX-ACCESS  read-only
        STATUS      current
        DESCRIPTION
                "Identify the last source of the circuit's creation."
        ::= { cfrExtCircuitEntry 5 }

cfrExtCircuitMulticast  OBJECT-TYPE
        SYNTAX      TruthValue
        MAX-ACCESS  read-only
        STATUS      current
        DESCRIPTION
                "Indicate if this DLCI is a multicast DLCI."
        ::= { cfrExtCircuitEntry 6 }

cfrExtCircuitRoutedDlci OBJECT-TYPE
        SYNTAX      DlciNumber
        MAX-ACCESS  read-only
        STATUS      current
        DESCRIPTION
                "The routed DLCI to pair up with this DLCI
                for switching function. NOTE: Value zero (0)
                indicates that there is no such routed DLCI
                corresponding to this DLCI."
        ::= { cfrExtCircuitEntry 7 }

cfrExtCircuitRoutedIf OBJECT-TYPE
        SYNTAX      InterfaceIndex
        MAX-ACCESS  read-only
        STATUS      current
        DESCRIPTION
                "The interface for the routed DLCI that pairs up
                with this DLCI for switching. Value greater than 0
                is the InterfaceIndex for that interface. Value
                zero (0) indicates that there is no such routed DLCI
                corresponding to this DLCI."
        ::= { cfrExtCircuitEntry 8 }

cfrExtCircuitUncompressIns OBJECT-TYPE
        SYNTAX      Counter32
        UNITS       "octets"
        MAX-ACCESS  read-only
        STATUS      current
        DESCRIPTION
                "Number of inbound octets of the data packets,
                accounted at Frame Relay level after FRF.9
                payload decompression is applied. In the case of
                non-FRF.9, this value could be identical to
                frCircuitReceivedOctets, unless otherwise noted."
        ::= { cfrExtCircuitEntry 9 }

cfrExtCircuitUncompressOuts OBJECT-TYPE
        SYNTAX      Counter32
        UNITS       "octets"
        MAX-ACCESS  read-only
        STATUS      current
        DESCRIPTION
                "Number of outbound octets of the data packets,
                accounted at Frame Relay level before FRF.9
                payload compression is applied. In the case of
                non-FRF.9, this value could be identical to
                frCircuitSentOctets, unless otherwise noted."
        ::= { cfrExtCircuitEntry 10 }

cfrExtCircuitFECNOuts OBJECT-TYPE
        SYNTAX      Counter32
        MAX-ACCESS  read-only
        STATUS      current
        DESCRIPTION
                "Total number of frames sent out to the network 
                indicating forward congestion."
        ::= { cfrExtCircuitEntry 11 }

cfrExtCircuitBECNOuts OBJECT-TYPE
        SYNTAX      Counter32
        MAX-ACCESS  read-only
        STATUS      current
        DESCRIPTION
                "Total number of frames sent out to the network 
                indicating backward congestion."
        ::= { cfrExtCircuitEntry 12 }

cfrExtCircuitMinThruputOut OBJECT-TYPE
        SYNTAX      Integer32 (9600..1544000)
        UNITS       "bits per second"
        MAX-ACCESS  read-only
        STATUS      current
        DESCRIPTION
                "Circuit's outgoing minimal Throughput based on 
                configuration."
        ::= { cfrExtCircuitEntry 13 }

cfrExtCircuitMinThruputIn  OBJECT-TYPE
        SYNTAX      Integer32 (9600..1544000)
        UNITS       "bits per second"
        MAX-ACCESS  read-only
        STATUS      current
        DESCRIPTION
                "Circuit's incoming minimal Throughput based on
                configuration."
        ::= { cfrExtCircuitEntry 14 }

cfrExtCircuitBcastPktOuts OBJECT-TYPE
        SYNTAX      Counter32
        MAX-ACCESS  read-only
        STATUS      current
        DESCRIPTION
                "Total number of broadcast packets sent out to the 
                 network."
        ::= { cfrExtCircuitEntry 15 }

cfrExtCircuitBcastByteOuts OBJECT-TYPE
        SYNTAX      Counter32
        MAX-ACCESS  read-only
        STATUS      current
        DESCRIPTION
                "Total number of bytes sent out to the network in 
                broadcast packets."
        ::= { cfrExtCircuitEntry 16 }

cfrExtCircuitBandwidth OBJECT-TYPE
        SYNTAX      Integer32 (0..16777215)
        UNITS       "bits per second"
        MAX-ACCESS  read-only
        STATUS      current
        DESCRIPTION
                "Bandwidth of the virtual circuit, acquired from 
                Cisco typed LMI Full Status message."
        ::= { cfrExtCircuitEntry 17 }

cfrExtCircuitShapeByteLimit OBJECT-TYPE
        SYNTAX      Integer32 (125..2147483647)
        UNITS       "octets"
        MAX-ACCESS  read-only
        STATUS      current
        DESCRIPTION
                "Maximum number of tokens a token bucket can hold in any
                time interval in case of traffic shaping."
        ::= { cfrExtCircuitEntry 18 }

cfrExtCircuitShapeInterval OBJECT-TYPE
        SYNTAX      Integer32 (10..125)
        UNITS       "milliseconds"
        MAX-ACCESS  read-only
        STATUS      current
        DESCRIPTION
                "Committed rate measurement interval."
        ::= { cfrExtCircuitEntry 19 }

cfrExtCircuitShapeByteIncrement OBJECT-TYPE
        SYNTAX      Integer32 (125..2147483647)
        UNITS       "octets"
        MAX-ACCESS  read-only
        STATUS      current
        DESCRIPTION
                "Number of tokens added into the token bucket per time
                interval in case of traffic shaping."
        ::= { cfrExtCircuitEntry 20 }

cfrExtCircuitShapePkts OBJECT-TYPE
        SYNTAX      Counter32
        MAX-ACCESS  read-only
        STATUS      current
        DESCRIPTION
                "Total number of packets that went through traffic 
                shaping."
        ::= { cfrExtCircuitEntry 21 }

cfrExtCircuitShapeBytes OBJECT-TYPE
        SYNTAX      Counter32
        UNITS       "octets"
        MAX-ACCESS  read-only
        STATUS      current
        DESCRIPTION
                "Total number of bytes that went through traffic 
                shaping."
        ::= { cfrExtCircuitEntry 22 }

cfrExtCircuitShapePktsDelay OBJECT-TYPE
        SYNTAX      Counter32
        MAX-ACCESS  read-only
        STATUS      current
        DESCRIPTION
                "Total number of packets that were delayed by the 
                traffic shaper."
        ::= { cfrExtCircuitEntry 23 }

cfrExtCircuitShapeBytesDelay OBJECT-TYPE
        SYNTAX      Counter32
        UNITS       "octets"
        MAX-ACCESS  read-only
        STATUS      current
        DESCRIPTION
                "Total number of bytes that were delayed by the 
                traffic shaper."
        ::= { cfrExtCircuitEntry 24 }

cfrExtCircuitShapeActive OBJECT-TYPE
        SYNTAX      TruthValue
        MAX-ACCESS  read-only
        STATUS      current
        DESCRIPTION
                "Shows whether shaping is active or not."
        ::= { cfrExtCircuitEntry 25 }

cfrExtCircuitShapeAdapting  OBJECT-TYPE
        SYNTAX  INTEGER {
                  none(1),
                  becn(2),
                  foreSight(3)
                }
        MAX-ACCESS  read-only
        STATUS      current
        DESCRIPTION
                "Type of Adaptive Shaping configured.
                none(1)      - No adaptive shaping configured
                becn(2)      - Backward Explicit Congestion Notification
                foreSight(3) - ForeSight is the network traffic control 
                               software used in Cisco WAN switches"
        ::= { cfrExtCircuitEntry 26 }

cfrExtCircuitTxDataRate OBJECT-TYPE
        SYNTAX       INTEGER (1..45000000)
        MAX-ACCESS   read-only
        STATUS       current
        DESCRIPTION
               "The average rate (bytes/second) at which data is 
               transmitted in this circuit. "
        ::= { cfrExtCircuitEntry 27 }

cfrExtCircuitTxPktRate OBJECT-TYPE
        SYNTAX       INTEGER (1..45000000)
        MAX-ACCESS   read-only
        STATUS       current
        DESCRIPTION
              "The average number of packets sent in a second in this 
              circuit."
        ::= { cfrExtCircuitEntry 28 }

cfrExtCircuitRcvDataRate OBJECT-TYPE
        SYNTAX       INTEGER (1..45000000)
        MAX-ACCESS   read-only
        STATUS       current
        DESCRIPTION
               "The average rate (bytes/second) at which data is 
               received in this circuit. "
        ::= { cfrExtCircuitEntry 29 }

cfrExtCircuitRcvPktRate OBJECT-TYPE
        SYNTAX       INTEGER (1..45000000)
        MAX-ACCESS   read-only
        STATUS       current
        DESCRIPTION
               "The average number of packets received in a second in 
               this circuit. "
       ::= { cfrExtCircuitEntry 30 }

-- end circuit subgroup }

-- Mapping sub-group {

cfrMapTable OBJECT-TYPE
        SYNTAX      SEQUENCE OF CfrMapEntry
        MAX-ACCESS  not-accessible
        STATUS      current
        DESCRIPTION
                "Table of protocols and addresses mapping
                information of FR virtual circuit."
        ::= { cfrMapObjs 1 }

cfrMapEntry OBJECT-TYPE
        SYNTAX      CfrMapEntry
        MAX-ACCESS  not-accessible
        STATUS     current
        DESCRIPTION
                "Each entry of the table contains one mapping 
                information of a Frame Relay virtual circuit."
        INDEX { frCircuitIfIndex, frCircuitDlci, cfrMapIndex } 
        ::= { cfrMapTable 1 }

CfrMapEntry ::=
        SEQUENCE {
            cfrMapIndex                 INTEGER,
            cfrMapProtocol              CfrMapProtocols,
            cfrMapAddress               OCTET STRING (SIZE(0..64)),
            cfrMapType                  INTEGER,
            cfrMapEncaps                INTEGER,
            cfrMapBroadcast             TruthValue,
            cfrMapPayloadCompress       TruthValue,
            cfrMapTcpHdrCompress        INTEGER,
            cfrMapRtpHdrCompress        INTEGER,
            cfrMapPayloadCompressType   INTEGER
        }

cfrMapIndex OBJECT-TYPE
        SYNTAX      INTEGER (1..999)
        MAX-ACCESS  read-only
        STATUS      current
        DESCRIPTION
                "An arbitrary Index to the mapping information
                associated with a certain circuit. The maximum
                value is arbitrarily picked which is considered
                sufficient for usual configuration."
        ::= { cfrMapEntry 1 }

cfrMapProtocol OBJECT-TYPE
        SYNTAX      CfrMapProtocols
        MAX-ACCESS  read-only
        STATUS      current
        DESCRIPTION
                "Mapping protocol for this circuit."
        ::= { cfrMapEntry 2 }

cfrMapAddress OBJECT-TYPE
        SYNTAX      OCTET STRING (SIZE(0..64))
        MAX-ACCESS  read-only
        STATUS      current
        DESCRIPTION
                "Mapping protocol address at remote end for
                this DLCI.
                NOTE: For point-to-point DLCI, the string is fixed
                to be point-to-point."
        ::= { cfrMapEntry 3 }

cfrMapType OBJECT-TYPE
        SYNTAX  INTEGER
                {
                    static(1),
                    dynamic(2),
                    svc(3)
                }
        MAX-ACCESS  read-only
        STATUS      current
        DESCRIPTION
                "Type for the map creation."
        ::= { cfrMapEntry 4 }

cfrMapEncaps OBJECT-TYPE
        SYNTAX  INTEGER
                {
                    ietf(1),    -- following IETF specifications
                                -- (RFC 1490 as up to date)
                    cisco(2)
                }
        MAX-ACCESS  read-only
        STATUS      current
        DESCRIPTION
                "Indication of the encapsulation type for this
                mapping protocol."
        ::= { cfrMapEntry 5 }

cfrMapBroadcast OBJECT-TYPE
        SYNTAX      TruthValue
        MAX-ACCESS  read-only
        STATUS      current
        DESCRIPTION
                "Broadcast enabled or disabled."
        ::= { cfrMapEntry 6 }

cfrMapPayloadCompress OBJECT-TYPE
        SYNTAX      TruthValue
        MAX-ACCESS  read-only
        STATUS      deprecated
                    -- obsoleted by cfrMapPayloadCompressType
        DESCRIPTION
                "Indicate if payload compression is enabled."
        ::= { cfrMapEntry 7 }

cfrMapTcpHdrCompress OBJECT-TYPE
        SYNTAX  INTEGER
                {
                    inapplicable(1),
                    passive(2),
                    active(3)
                }
        MAX-ACCESS  read-only
        STATUS      current
        DESCRIPTION
                "TCP header compression type, if applicable."
        ::= { cfrMapEntry 8 }

cfrMapRtpHdrCompress OBJECT-TYPE
        SYNTAX  INTEGER
                {
                    inapplicable(1),
                    passive(2),
                    active(3)
                }
        MAX-ACCESS  read-only
        STATUS      current
        DESCRIPTION
                "RTP header compression type, if applicable.
                The value 'passive' means that the header of an
                outgoing RTP/IP packet is compressed only if an
                incoming RTP/IP packet had a compressed header.
                The value 'active' means the header of every outgoing
                RTP/IP packet is compressed."
        ::= { cfrMapEntry 9 }

cfrMapPayloadCompressType OBJECT-TYPE
        SYNTAX  INTEGER
             {
                inapplicable(1),
                cisco(2),         -- Cisco proprietary FR packet-
                                  -- by-packet payload compression
                frf9Software(3),  -- FRF.9 software payload compression
                frf9Hardware(4)   -- FRF.9 hardware payload compression
             }
        MAX-ACCESS  read-only
        STATUS      current
        DESCRIPTION
                "FR payload compression type, if applicable.
                FRF.9 is the Frame Relay Forum Implementation Agreement
                on FR payload compression. The compression can be done
                by either software or hardware (when equipped with the
                supporting hardware), depending on configuration."
        REFERENCE
                "Frame Relay Forum document number FRF.9"
        ::= { cfrMapEntry 10 }

-- end mapping subgroup }

-- SVC sub-group {
--        containing SVC spcific information

cfrSvcTable OBJECT-TYPE
        SYNTAX      SEQUENCE OF CfrSvcEntry
        MAX-ACCESS  not-accessible
        STATUS      current
        DESCRIPTION
                "Table of FR SVC specific, descriptive
                and statistics information."
        ::= { cfrSvcObjs 1 }

cfrSvcEntry OBJECT-TYPE
        SYNTAX      CfrSvcEntry
        MAX-ACCESS  not-accessible
        STATUS      current
        DESCRIPTION
                "Each entry of the table contains circuit information
                specific to a Frame Relay Switched Virtual Circuit."
        INDEX { frCircuitIfIndex, frCircuitDlci } 
        ::= { cfrSvcTable 1 }

CfrSvcEntry ::=
        SEQUENCE {
            cfrSvcAddrLocal           OCTET STRING (SIZE(0..64)),
            cfrSvcAddrRemote          OCTET STRING (SIZE(0..64)),
            cfrSvcThroughputIn        Integer32,
            cfrSvcMinThruputOut       Integer32,
            cfrSvcMinThruputIn        Integer32,
            cfrSvcCommitBurstIn       Integer32,
            cfrSvcExcessBurstIn       Integer32,
            cfrSvcIdleTime            Integer32
        }

-- For circuit (DLCI) outbound throughput and outbound Committed 
-- and Excess Burst size, please refer to the following from
-- RFC1315 respectively:
--        frCircuitThroughput, 
--        frCircuitCommittedBurst, and
--        frCircuitExcessBurst

cfrSvcAddrLocal OBJECT-TYPE
        SYNTAX      OCTET STRING (SIZE(0..64))
        MAX-ACCESS  read-only
        STATUS      current
        DESCRIPTION
                "Local E.164/X.125 address for the circuit."
        ::= { cfrSvcEntry 1 }

cfrSvcAddrRemote OBJECT-TYPE
        SYNTAX      OCTET STRING (SIZE(0..64))
        MAX-ACCESS  read-only
        STATUS      current
        DESCRIPTION
                "Remote E.164/X.125 address for the circuit."
        ::= { cfrSvcEntry 2 }

cfrSvcThroughputIn OBJECT-TYPE
        SYNTAX      Integer32 (9600..1544000)
        UNITS       "bits per second"
        MAX-ACCESS  read-only
        STATUS      current
        DESCRIPTION
                "Circuit's incoming throughput. For outgoing 
                throughput (commonly referred to as CIR) see
                frCircuitThroughput per RFC1315."
        ::= { cfrSvcEntry 3 }

cfrSvcMinThruputOut OBJECT-TYPE
        SYNTAX      Integer32 (9600..1544000)
        UNITS       "bits per second"
        MAX-ACCESS  read-only
        STATUS      deprecated -- deprecated by 
                               -- cfrExtCircuitMinThruputOut
        DESCRIPTION
                "Circuit's outgoing minimal Throughput."
        ::= { cfrSvcEntry 4 }

cfrSvcMinThruputIn  OBJECT-TYPE
        SYNTAX      Integer32 (9600..1544000)
        UNITS       "bits per second"
        MAX-ACCESS  read-only
        STATUS      deprecated -- deprecated by 
                               -- cfrExtCircuitMinThruputIn
        DESCRIPTION
                "Circuit's incoming minimal Throughput."
        ::= { cfrSvcEntry 5 }

cfrSvcCommitBurstIn OBJECT-TYPE
        SYNTAX      Integer32 (9600..1544000)
        MAX-ACCESS  read-only
        STATUS      current
        DESCRIPTION
                "Circuit's incoming Committed Burst Rate.
                See ANSI and/or ITU specifications for
                definition and calculations. For outgoing
                CBR, see frCircuitCommittedBurst per RFC 1315."
        ::= { cfrSvcEntry 6 }

cfrSvcExcessBurstIn OBJECT-TYPE
        SYNTAX      Integer32 (9600..2440000)
        MAX-ACCESS  read-only
        STATUS      current
        DESCRIPTION
                "Circuit's incoming Excess Burst Rate.
                See ANSI and/or ITU specifications for
                definition and calculations. For outgoing
                EBR, see frCircuitExcessBurst per RFC 1315."
        ::= { cfrSvcEntry 7 }

cfrSvcIdleTime      OBJECT-TYPE
        SYNTAX      Integer32
        UNITS       "seconds"
        MAX-ACCESS  read-only
        STATUS      current
        DESCRIPTION
                "Circuit's idle time period. If expires, the
                circuit is cleared."
        ::= { cfrSvcEntry 8 }

-- end SVC subgroup }

-- Enhanced Link Management Interface(ELMI) sub-group {
-- ELMI is the protocol that learns QOS parameters(CIR,Bc,Be etc)
-- of a VC from the switch.
-- This sub group contains ELMI specific information.

cfrElmiIpAddr      OBJECT-TYPE
        SYNTAX     IpAddress
        MAX-ACCESS read-only
        STATUS     current
        DESCRIPTION
                "This object represents the Management address of the
                 device used for address registration. 
                 Network management station can send management
                 messages to this IP address. This can be 
                 user configured address or the address of one of the
                 interfaces on the device. If address registration is
                 disabled then this will have a value of 0.0.0.0. 
                 This object is accessible only if the ELMI protocol 
                 is supported on the device"
        ::= { cfrElmiObjs 1 }

cfrElmiTable       OBJECT-TYPE
        SYNTAX     SEQUENCE OF CfrElmiEntry
        MAX-ACCESS not-accessible
        STATUS     current
        DESCRIPTION
                "Table of CISCO Frame Relay ELMI information that is
                 specific to CISCO implementation"
        ::= { cfrElmiObjs 2 }

cfrElmiEntry       OBJECT-TYPE
        SYNTAX     CfrElmiEntry
        MAX-ACCESS not-accessible
        STATUS     current
        DESCRIPTION
                "Each entry of the table contains information about a
                 physical interface. The table can be accessible only
                 if the device supports ELMI protocol and if LMI is
                 enabled on the interface."
        INDEX { ifIndex }
        ::= { cfrElmiTable 1 }

CfrElmiEntry ::=
        SEQUENCE {
            cfrElmiLinkStatus
                INTEGER,
            cfrElmiArStatus
                INTEGER,
            cfrElmiRemoteStatus
                INTEGER
        }

cfrElmiLinkStatus  OBJECT-TYPE
        SYNTAX     INTEGER {
                       enabled(1),
                       disabled(2)
                   }
        MAX-ACCESS read-only
        STATUS     current
        DESCRIPTION
                "This variable states whether Enhanced Link Management
                 Interface(ELMI) protocol is enabled or not on a 
                 frame relay interface."
        ::= { cfrElmiEntry 1 }

cfrElmiArStatus    OBJECT-TYPE
        SYNTAX     INTEGER {
                       enabled(1),
                       disabled(2)
                   }
        MAX-ACCESS read-only
        STATUS     current
        DESCRIPTION
                "This variable states whether the Enhanced Link
                 Management Interface(ELMI) address registration(AR)
                 mechanism is enabled or not on a frame relay 
                 interface. A value of 1 indicates ELMI AR is 
                 supported on the interface. A value of 2 indicates
                 ELMI AR is supported but the user disabled the
                 exchange of IP address and ifIndex with the
                 neighboring device. This object doesn't have any
                 significance if cfrElmiLinkStatus is disabled
                 on the interface."
        ::= { cfrElmiEntry 2 }

cfrElmiRemoteStatus OBJECT-TYPE
        SYNTAX      INTEGER {
                        enabled(1),
                        disabled(2)
                    }
        MAX-ACCESS  read-only
        STATUS      current
        DESCRIPTION
                "This variable states the Enhanced Link 
                 Management(ELMI) status on the other end of the
                 interface. If cfrElmiLinkStatus is enabled on the
                 other end a value of 1 will be returned,
                 else 2 will be returned. This object doesn't have any
                 significance if cfrElmiLinkStatus is disabled on the
                 interface"
        ::= { cfrElmiEntry 3 }

cfrElmiNeighborTable    OBJECT-TYPE
        SYNTAX          SEQUENCE OF CfrElmiNeighborEntry
        MAX-ACCESS      not-accessible
        STATUS          current
        DESCRIPTION
                "Table of CISCO Frame Relay Neighbor ELMI information
                 that is specific to CISCO implementation."
        ::= { cfrElmiObjs 3 }

cfrElmiNeighborEntry OBJECT-TYPE
        SYNTAX       CfrElmiNeighborEntry
        MAX-ACCESS   not-accessible
        STATUS       current
        DESCRIPTION
                "Each entry of the table contains information of the
                 neighboring device connected to a physical interface.
                 The entry will be present only if ELMI is enabled on
                 the neighboring device interface. If the value of the
                 cfrElmiRemoteStatus in the cfrElmiEntry is 1 then a 
                 valid entry exists for the interface. If ELMI is not 
                 supported on the remote end then, the neighbor 
                 information for the interface will not be present"
        INDEX { ifIndex }
        ::= { cfrElmiNeighborTable 1 }

CfrElmiNeighborEntry ::=
        SEQUENCE {
            cfrElmiNeighborArStatus
                INTEGER,
            cfrElmiNeighborIpAddress
                IpAddress,
            cfrElmiNeighborIfIndex
                InterfaceIndex,
            cfrElmiNeighborVendorName
                DisplayString,
            cfrElmiNeighborPlatformName
                DisplayString,
            cfrElmiNeighborDeviceName
                DisplayString
        }

cfrElmiNeighborArStatus OBJECT-TYPE
        SYNTAX          INTEGER {
                            notsupported(1),
                            enabled(2),
                            disabled(3)
                        }
        MAX-ACCESS      read-only
        STATUS          current
        DESCRIPTION
                "This variable indicates the status of ELMI Address 
                 registration(AR) on the neighboring device. A value 
                 of 1 indicates ELMI AR is not supported on the 
                 neighboring device. A value of 2 indicates ELMI AR is
                 enabled on the interface. A value of 3 indicates AR is
                 supported, but user disabled the exchange of IP 
                 address and ifIndex with the neighbor."
        ::= { cfrElmiNeighborEntry 1 }

cfrElmiNeighborIpAddress OBJECT-TYPE
        SYNTAX           IpAddress
        MAX-ACCESS       read-only
        STATUS           current
        DESCRIPTION
                "The Management IP address of the neighboring device 
                 to which the other end of this interface is 
                 connected. Network management system can use this
                 address to send management messages to the device.
                 If address registration is not supported on the
                 remote end then the value will be 0.0.0.0.
                 NMS uses this object in the topology discovery of the
                 network."
        ::= { cfrElmiNeighborEntry 2 }

cfrElmiNeighborIfIndex   OBJECT-TYPE
        SYNTAX           InterfaceIndex
        MAX-ACCESS       read-only
        STATUS           current
        DESCRIPTION
                "The Interface index of the neighboring device to 
                 which this interface is connected. If the value of
                 cfrElmiNeighborArStatus is 2 then this will have a
                 valid value. If the value of cfrElmiNeighborArStatus
                 is 3 or 1 then value of this object will be 0. NMS
                 uses this object in the topology discovery of the
                 network."
        ::= { cfrElmiNeighborEntry 3 }

cfrElmiNeighborVendorName OBJECT-TYPE
        SYNTAX            DisplayString
        MAX-ACCESS        read-only
        STATUS            current
        DESCRIPTION
                "Vendor name of the neighboring device to which the
                 other end of this interface is connected."
        ::= { cfrElmiNeighborEntry 4 }

cfrElmiNeighborPlatformName OBJECT-TYPE
        SYNTAX              DisplayString
        MAX-ACCESS          read-only
        STATUS              current
        DESCRIPTION
                "Platform name of the neighboring device to which the
                 other end of this interface is connected."
        ::= { cfrElmiNeighborEntry 5 }

cfrElmiNeighborDeviceName   OBJECT-TYPE
        SYNTAX              DisplayString
        MAX-ACCESS          read-only
        STATUS              current
        DESCRIPTION
                "Device name of the neighboring device to which the
                 other end of this interface is connected."
        ::= { cfrElmiNeighborEntry 6 }

-- end ELMI sub-group }

-- Fragmentation sub-group {

cfrFragTable OBJECT-TYPE
        SYNTAX      SEQUENCE OF CfrFragEntry
        MAX-ACCESS  not-accessible
        STATUS      current
        DESCRIPTION
                "Table of Frame Relay Fragmentation information. 
                These are specific to Cisco's implementation."
        ::= { cfrFragObjs 1 }

cfrFragEntry OBJECT-TYPE
        SYNTAX      CfrFragEntry
        MAX-ACCESS  not-accessible
        STATUS      current
        DESCRIPTION
                "Each entry of the table contains details of 
                fragmentation configured on  this circuit. "
        INDEX { frCircuitIfIndex, frCircuitDlci}
        ::= { cfrFragTable 1 }

CfrFragEntry ::=
        SEQUENCE {
            cfrFragSize                       INTEGER,
            cfrFragType                       DisplayString,
            cfrFragInPkts                     Counter32,
            cfrFragOutPkts                    Counter32,
            cfrFragInOctets                   Counter32,
            cfrFragOutOctets                  Counter32,
            cfrFragNotInPkts                  Counter32,
            cfrFragNotOutPkts                 Counter32,
            cfrFragNotInOctets                Counter32,
            cfrFragNotOutOctets               Counter32,
            cfrFragAssembledInPkts            Counter32,
            cfrFragAssembledInOctets          Counter32,
            cfrFragPreOutPkts                 Counter32,
            cfrFragPreOutOctets               Counter32,
            cfrFragDroppedReAssembledInPkts   Counter32,
            cfrFragDroppedFragmentedOutPkts   Counter32,
            cfrFragTimeoutsIn                 INTEGER,
            cfrFragOutOfSeqFragPkts           Counter32,
            cfrFragUnexpectedBBitSetPkts      Counter32,
            cfrFragSeqMissedPkts              Counter32,
            cfrFragInterleavedOutPkts         Counter32
        }

cfrFragSize OBJECT-TYPE
        SYNTAX      INTEGER (16..1600)
        UNITS       "octets"
        MAX-ACCESS  read-only
        STATUS      current
        DESCRIPTION
                "cfrFragSize defines the payload size of a fragment 
                and it excludes the FR headers and any FR fragmentation
                header."
        ::= { cfrFragEntry 1 }
cfrFragType OBJECT-TYPE
        SYNTAX  DisplayString
        MAX-ACCESS  read-only
        STATUS      current
        DESCRIPTION
                "Fragmentation type configured by the user. The types
                supported are end-to-end, VoFR-cisco and VoFR."
        ::= { cfrFragEntry 2 }

cfrFragInPkts  OBJECT-TYPE
        SYNTAX      Counter32
        UNITS       "packets"
        MAX-ACCESS  read-only
        STATUS      current
        DESCRIPTION
                "Total number of frames received that have a 
                fragmentation header."
        ::= { cfrFragEntry 3 }

cfrFragOutPkts OBJECT-TYPE
        SYNTAX      Counter32
        UNITS       "packets"
        MAX-ACCESS  read-only
        STATUS      current
        DESCRIPTION
                "Total number of fragments that are transmitted with a
                fragmenation header."
        ::= { cfrFragEntry 4 }

cfrFragInOctets OBJECT-TYPE
        SYNTAX      Counter32
        UNITS       "octets"
        MAX-ACCESS  read-only
        STATUS      current
        DESCRIPTION
                "Total number of bytes received in frames that have a 
                fragmentation header. The number of bytes include the
                FR header." 
        ::= { cfrFragEntry 5}

cfrFragOutOctets OBJECT-TYPE
        SYNTAX      Counter32
        UNITS       "octets"
        MAX-ACCESS  read-only
        STATUS      current
        DESCRIPTION
                "Total number of bytes that are transmitted in frames
                with a fragmenation header. The number of bytes also
                includes the FR header." 
        ::= { cfrFragEntry 6}

cfrFragNotInPkts OBJECT-TYPE
        SYNTAX      Counter32
        UNITS       "packets"
        MAX-ACCESS  read-only
        STATUS      current
        DESCRIPTION
                "Total number of frames received that do not require 
                reassembly and therefore will not contain the 
                fragmentation header. This counter is valid only when
                end-to-end fragmentation type is set." 
        ::= { cfrFragEntry 7}

cfrFragNotOutPkts  OBJECT-TYPE
        SYNTAX      Counter32
        UNITS       "packets"
        MAX-ACCESS  read-only
        STATUS      current
        DESCRIPTION
                "Total number of frames transmitted without fragmenting
                and therefore will not contain the fragmentation header.
                This counter is valid only when end-to-end fragmentation
                type is set." 
        ::= { cfrFragEntry 8}

cfrFragNotInOctets  OBJECT-TYPE
        SYNTAX      Counter32
        UNITS       "octets"
        MAX-ACCESS  read-only
        STATUS      current
        DESCRIPTION
                "Total number of bytes received in frames that do not 
                require reassembly and therefore will not contain the 
                fragmentation header. This counter is valid only when
                end-to-end fragmentation type is set." 
        ::= { cfrFragEntry 9}

cfrFragNotOutOctets OBJECT-TYPE
        SYNTAX      Counter32
        UNITS       "octets"
        MAX-ACCESS  read-only
        STATUS      current
        DESCRIPTION
                "Total number of bytes transmitted in frames that are
                not fragmented and therefore will not contain the 
                fragmentation header. This counter is valid only when 
                end-to-end fragmentation type is set." 
        ::= { cfrFragEntry 10}

cfrFragAssembledInPkts OBJECT-TYPE
        SYNTAX      Counter32
        UNITS       "packets"
        MAX-ACCESS  read-only
        STATUS      current
        DESCRIPTION
                "Total number of fully reassembled frames. It also 
                counts the number of packets received without FR 
                fragmentation header (i.e. in un-fragmentated pkts)."
        ::= { cfrFragEntry 11}

cfrFragAssembledInOctets OBJECT-TYPE
        SYNTAX      Counter32
        UNITS       "octets"
        MAX-ACCESS  read-only
        STATUS      current
        DESCRIPTION
                "Total number of bytes received in fully reassembled 
                frames. It also counts the number of packets received
                without FR fragmentation header (i.e.in un-fragmentated
                pkts)."
        ::= { cfrFragEntry 12}

cfrFragPreOutPkts OBJECT-TYPE
        SYNTAX      Counter32
        UNITS       "packets"
        MAX-ACCESS  read-only
        STATUS      current
        DESCRIPTION
                "Total number of frames fragmented and trasmitted. It 
                also counts the number of packets trasmitted without FR
                fragmentation header (i.e. in un-fragmentated pkts)."
        ::= { cfrFragEntry 13}

cfrFragPreOutOctets OBJECT-TYPE
        SYNTAX      Counter32
        UNITS       "octets"
        MAX-ACCESS  read-only
        STATUS      current
        DESCRIPTION
                "Total number of bytes transmitted in fragmented frames.
                It also counts the number of bytes trasmitted in frames
                without FR fragmentation header (i.e. in un-fragmentated
                pkts)."
        ::= { cfrFragEntry 14}

cfrFragDroppedReAssembledInPkts OBJECT-TYPE
        SYNTAX      Counter32
        UNITS       "packets"
        MAX-ACCESS  read-only
        STATUS      current
        DESCRIPTION
                "Number of received fragments dropped for reasons such
                as : running out of memory, receiving segments out of 
                sequence, receiving an unexpected frame with a B bit 
                set, timing out on a reassembling frame." 
        ::= { cfrFragEntry 15}

cfrFragDroppedFragmentedOutPkts OBJECT-TYPE
        SYNTAX      Counter32
        UNITS       "packets"
        MAX-ACCESS  read-only
        STATUS      current
        DESCRIPTION
                "Number of fragments dropped because of running 
                out of memory." 
        ::= { cfrFragEntry 16}

cfrFragTimeoutsIn OBJECT-TYPE
        SYNTAX      INTEGER (0..1000)
        MAX-ACCESS  read-only
        STATUS      current
        DESCRIPTION
                "Number of reassemble timer timeouts for this circuit.
                A frame requiring more than two minutes to fully 
                reassemble is dropped and timeout will be incremented
                by one." 
        ::= { cfrFragEntry 17}

cfrFragOutOfSeqFragPkts OBJECT-TYPE
        SYNTAX      Counter32
        UNITS       "packets"
        MAX-ACCESS  read-only
        STATUS      current
        DESCRIPTION
                "Indicates the total number of packets received with an
                unexpected sequence number. All fragments being 
                reassembled are dropped. Start a new packet with the
                received segment only if the B bit is set on the 
                segment. Otherwise the new segment is also dropped." 
        ::= { cfrFragEntry 18}

cfrFragUnexpectedBBitSetPkts OBJECT-TYPE
        SYNTAX      Counter32
        UNITS       "packets"
        MAX-ACCESS  read-only
        STATUS      current
        DESCRIPTION
                "Number of fragments received in this circuit with 
                a B bit set. All fragments being reassembled are dropped
                and a new packet is started with this segment." 
        ::= { cfrFragEntry 19}

cfrFragSeqMissedPkts OBJECT-TYPE
        SYNTAX      Counter32
        UNITS       "packets"
        MAX-ACCESS  read-only
        STATUS      current
        DESCRIPTION
                "Number of fragments received in this circuit with 
                skipped sequence number."
        ::= { cfrFragEntry 20}

cfrFragInterleavedOutPkts OBJECT-TYPE
        SYNTAX      Counter32
        UNITS       "packets"
        MAX-ACCESS  read-only
        STATUS      current
        DESCRIPTION
                "Number of packets that have been interleaved between 
                segments." 
        ::= { cfrFragEntry 21}

-- end Fragmentation sub-group }

-- Connect sub-group {

cfrConnectionTable OBJECT-TYPE
        SYNTAX      SEQUENCE OF CfrConnectionEntry
        MAX-ACCESS  not-accessible
        STATUS      current
        DESCRIPTION
                "Table of Frame Relay/Frame Relay and Frame Relay/ATM
                Network/Service Interworking connection information. 
                These are specific to Cisco's implementation."
        ::= { cfrConnectionObjs 1 }

cfrConnectionEntry OBJECT-TYPE
        SYNTAX      CfrConnectionEntry
        MAX-ACCESS  not-accessible
        STATUS      current
        DESCRIPTION
                "Each entry of the table contains information of a
                connection that is established for Frame Relay/Frame 
                Relay and Frame Relay/ATM Network/Service Interworking."
        INDEX { frCircuitIfIndex, frCircuitDlci}
        ::= { cfrConnectionTable 1 }

CfrConnectionEntry ::=
        SEQUENCE {
            cfrConnName               DisplayString,
            cfrConnID                 INTEGER,
            cfrConnState              DisplayString,
            cfrConnSegment1Name       DisplayString,
            cfrConnSegment1VCGroup    DisplayString,
            cfrConnSegment1Dlci       DlciNumber,
            cfrConnSegment2Name       DisplayString, 
            cfrConnSegment2Vpi        INTEGER,
            cfrConnSegment2Vci        INTEGER,
            cfrConnServiceTranslation INTEGER,
            cfrConnFrSscsDlci         DlciNumber,
            cfrConnEfciBit            INTEGER,
            cfrConnDeBit              INTEGER,
            cfrConnClpBit             INTEGER
        }

cfrConnName OBJECT-TYPE
        SYNTAX       DisplayString
        MAX-ACCESS   read-only
        STATUS       current        
        DESCRIPTION
               "The textual name of a for FR/FR or FR/ATM  
               Network/Service Interworking connection."
        ::= { cfrConnectionEntry 1 }

cfrConnID OBJECT-TYPE
        SYNTAX       INTEGER (1..2000)
        MAX-ACCESS   read-only
        STATUS       current
        DESCRIPTION
               "The numerical identifier of a FR/FR or FR/ATM  
               Network/Service Interworking connection."
        ::= { cfrConnectionEntry 2 }

cfrConnState OBJECT-TYPE
        SYNTAX      DisplayString
        MAX-ACCESS  read-only
        STATUS      current
        DESCRIPTION
                "Status of a FR/FR or FR/ATM  Network/Service 
                Interworking connection."
        ::= { cfrConnectionEntry 3}

cfrConnSegment1Name OBJECT-TYPE
        SYNTAX       DisplayString
        MAX-ACCESS   read-only
        STATUS       current
        DESCRIPTION
               "The textual name used to identify the first segment of 
               a FR/FR or FR/ATM  Network/Service Interworking 
               connection."
        ::= { cfrConnectionEntry 4}

cfrConnSegment1VCGroup OBJECT-TYPE
        SYNTAX       DisplayString
        MAX-ACCESS   read-only
        STATUS       current
        DESCRIPTION
               "The textual name used to identify the VC-Group in the
               first segment of a Frame Relay/ATM  Network Interworking
               (FRF.5)connection. 
               This field is not applicabe in case of,
                        FRF.8 (Frame Relay/ATM  Service Interworking)
                        and
                        FR-FR connectione. "
       ::= { cfrConnectionEntry 5}

cfrConnSegment1Dlci OBJECT-TYPE
        SYNTAX       DlciNumber
        MAX-ACCESS   read-only
        STATUS       current
        DESCRIPTION
               "The DLCI used as the first segment of a FR-FR or FR-ATM
               Network/Service Interworking connection."
        ::= { cfrConnectionEntry 6}

cfrConnSegment2Name OBJECT-TYPE
        SYNTAX       DisplayString
        MAX-ACCESS   read-only
        STATUS       current
        DESCRIPTION
               "The interface on which second segment of a FR-FR or 
               FR-ATM  Network/Service Interworking connection is 
               configured."
        ::= { cfrConnectionEntry 7}

cfrConnSegment2Vpi OBJECT-TYPE
        SYNTAX       INTEGER (0..4095)
        MAX-ACCESS   read-only
        STATUS       current
        DESCRIPTION
               "The value of  VPI, in the ATM connection, used as the
               second segment of a FR-ATM  Network/Service Interworking
               connection. In case of FR-FR connection, the same will 
               be used to display the DLCI used as the second segment."
        ::= { cfrConnectionEntry 8}

cfrConnSegment2Vci OBJECT-TYPE
        SYNTAX       INTEGER (0..4095)
        MAX-ACCESS   read-only
        STATUS       current
        DESCRIPTION
               "The value of  VCI, in the ATM connection, used as the
               second segment of a FR-ATM  Network/Service Interworking
               connection. In case of FR-FR connection, this is not 
               supported."
       ::= { cfrConnectionEntry 9}

cfrConnServiceTranslation OBJECT-TYPE
        SYNTAX       INTEGER {
                        serviceTranslationEnabled(1),
                        serviceTranslationNotEnabled(2)
                     }
        MAX-ACCESS   read-only
        STATUS       current
        DESCRIPTION
               "Shows whether Service Translation Mode is supported or
               not. Translation Mode is the interworking of 
               internetworking (routed and/or bridged) protocols used 
               in FR-ATM  Service PVC Interworking(FRF.8).
               This is not supported in case of FRF.5 (FR-ATM network
               Interworking) and FR-FR connections."
       ::= { cfrConnectionEntry 10}

cfrConnFrSscsDlci OBJECT-TYPE
        SYNTAX       DlciNumber
        MAX-ACCESS   read-only
        STATUS       current        
        DESCRIPTION
               "The DLCI value used at the FR-SSCS layer. This is one of
               connection multiplexing methods used in Frame Relay/ATM  
               Network Interworking.
               Not supported in case of FRF.8 (FR-ATM Service PVC 
               Interworking) and FR-FR connections"
        ::= { cfrConnectionEntry 11}

cfrConnEfciBit OBJECT-TYPE
        SYNTAX       INTEGER  {
                         mapFecn(1),
                         notMapFecn(2)
                     }
        MAX-ACCESS   read-only
        STATUS       current
        DESCRIPTION
               "Shows whether the FECN field in the FR frame is mapped 
               to the ATM EFCI field of every cell generated out of the 
               FR frame. This is used to indicate congestion in FR to
               ATM direction in case of Frame Relay/ATM  Service PVC 
               Interworking.
               Not supported in FRF.5 (Frame Relay/ATM Network 
               Interworking and FR-FR connections."
::= { cfrConnectionEntry 12}

cfrConnDeBit OBJECT-TYPE
        SYNTAX       INTEGER {
                         noMapClp(1),
                         mapClp(2),
                         setDe0(3),
                         setDe1(4)
                     }
        MAX-ACCESS   read-only
        STATUS       current
        DESCRIPTION
               "The method of operation for loss priority mapping in the
               B-ISDN to FR direction..
               Not supported in case of FR-FR connection."
        ::= { cfrConnectionEntry 13}

cfrConnClpBit OBJECT-TYPE
        SYNTAX  INTEGER {
                  setClpTo0AndCopyDeToFrsscsDe(1),
                  setClpTo1AndCopyDeToFrsscsDe(2),
                  copyDeToFrsscsDeAndClp(3),
                  copyDeToClp(4),
                  setClp1(5),
                  setClp0(6)
                }
        MAX-ACCESS   read-only
        STATUS       current
        DESCRIPTION
               "The method of operation used to map loss priority
               mapping in the FR to ATM direction.
               Not supported in case of FR-FR connection."
        ::= { cfrConnectionEntry 14}

-- end Conn subgroup }

ciscoFrMIBConformance OBJECT IDENTIFIER ::= { ciscoFrameRelayMIB 3 }
ciscoFrMIBCompliances OBJECT IDENTIFIER ::= { ciscoFrMIBConformance 1 }
ciscoFrMIBGroups      OBJECT IDENTIFIER ::= { ciscoFrMIBConformance 2 }

ciscoFrMIBCompliance MODULE-COMPLIANCE
        STATUS  obsolete  -- obsoleted by ciscoFrMIBCompliancesRev2
        DESCRIPTION
                "The compliance statement for entities which implement
                this Cisco Frame Relay MIB."
        MODULE  -- this module
                MANDATORY-GROUPS { ciscoFrMIBGroup }
        ::= { ciscoFrMIBCompliances 1 }

ciscoFrMIBCompliancesRev1 MODULE-COMPLIANCE
        STATUS  obsolete  -- obsoleted by ciscoFrMIBCompliancesRev2
        DESCRIPTION
                "The compliance statement for entities which implement
                this Cisco Frame Relay MIB."
        MODULE  -- this module
                MANDATORY-GROUPS { ciscoFrMIBGroupRev1 }
        ::= { ciscoFrMIBCompliances 2 }

ciscoFrMIBCompliancesRev2 MODULE-COMPLIANCE
        STATUS  obsolete  -- obsoleted by ciscoFrMIBCompliancesRev3 
        DESCRIPTION
                "The compliance statement for entities which implement
                this Cisco Frame Relay MIB."
        MODULE  -- this module
                MANDATORY-GROUPS { ciscoFrLmiMIBGroup, 
                                   ciscoFrCircuitMIBGroup,
                                   ciscoExtCircuitMIBGroup,
                                   ciscoFrTsMIBGroup,
                                   ciscoFrMapMIBGroup,
                                   ciscoFrSvcMIBGroup }
        ::= { ciscoFrMIBCompliances 3 }

ciscoFrMIBCompliancesRev3 MODULE-COMPLIANCE
        STATUS  deprecated  -- deprecated by ciscoFrMIBCompliancesRev4
        DESCRIPTION
                "The compliance statement for entities which implement
                this Cisco Frame Relay MIB."
        MODULE  -- this module
                MANDATORY-GROUPS { ciscoFrLmiMIBGroup,
                                   ciscoFrCircuitMIBGroup,
                                   ciscoExtCircuitMIBGroup,
                                   ciscoFrTsMIBGroup,
                                   ciscoFrMapMIBGroup,
                                   ciscoFrSvcMIBGroup,
                                   ciscoFrElmiMIBGroup}
        ::= { ciscoFrMIBCompliances 4 }

ciscoFrMIBCompliancesRev4 MODULE-COMPLIANCE
        STATUS  current
        DESCRIPTION
                "The compliance statement for entities which implement
                this Cisco Frame Relay MIB."
        MODULE  -- this module
                MANDATORY-GROUPS { ciscoFrLmiMIBGroup,
                                   ciscoFrCircuitMIBGroup,
                                   ciscoExtCircuitMIBGroup1,
                                   ciscoFrTsMIBGroup,
                                   ciscoFrMapMIBGroup,
                                   ciscoFrSvcMIBGroup,
                                   ciscoFrElmiMIBGroup1,
                                   ciscoFrFragMIBGroup,
                                   ciscoFrConnMIBGroup}
        ::= { ciscoFrMIBCompliances 5 }

-- units of conformance:

ciscoFrMIBGroup OBJECT-GROUP
        OBJECTS {
            cfrLmiLinkstatus,
            cfrLmiLinkType,
            cfrLmiEnquiryIns,
            cfrLmiEnquiryOuts,
            cfrLmiStatusIns,
            cfrLmiStatusOuts,
            cfrLmiUpdateStatusIns,
            cfrLmiUpdateStatusOuts,
            cfrLmiStatusTimeouts,
            cfrLmiStatusEnqTimeouts,
            cfrLmiN392Dce,
            cfrLmiN393Dce,
            cfrLmiT392Dce,
            cfrCircuitDEins,
            cfrCircuitDEouts,
            cfrCircuitDropPktsOuts,
            cfrCircuitType,
            cfrExtCircuitIfName,
            cfrExtCircuitIfType,
            cfrExtCircuitSubifIndex,
            cfrExtCircuitMapStatus,
            cfrExtCircuitCreateType,
            cfrExtCircuitMulticast,
            cfrExtCircuitRoutedDlci,
            cfrExtCircuitRoutedIf,
            cfrMapIndex,
            cfrMapProtocol,
            cfrMapAddress,
            cfrMapType,
            cfrMapEncaps,
            cfrMapBroadcast,
            cfrMapPayloadCompress,
            cfrMapTcpHdrCompress,
            cfrSvcAddrLocal,
            cfrSvcAddrRemote,
            cfrSvcThroughputIn,
            cfrSvcMinThruputOut,
            cfrSvcMinThruputIn,
            cfrSvcCommitBurstIn,
            cfrSvcExcessBurstIn,
            cfrSvcIdleTime
        }
        STATUS  deprecated       -- obsoleted by ciscoFrMIBGroupRev1
        DESCRIPTION
                "The compliance statement for entities which implement
                this Cisco Frame Relay MIB."
        ::= { ciscoFrMIBGroups 1 }

ciscoFrMIBGroupRev1 OBJECT-GROUP
        OBJECTS {
            cfrLmiLinkstatus,
            cfrLmiLinkType,
            cfrLmiEnquiryIns,
            cfrLmiEnquiryOuts,
            cfrLmiStatusIns,
            cfrLmiStatusOuts,
            cfrLmiUpdateStatusIns,
            cfrLmiUpdateStatusOuts,
            cfrLmiStatusTimeouts,
            cfrLmiStatusEnqTimeouts,
            cfrLmiN392Dce,
            cfrLmiN393Dce,
            cfrLmiT392Dce,
            cfrCircuitDEins,
            cfrCircuitDEouts,
            cfrCircuitDropPktsOuts,
            cfrCircuitType,
            cfrExtCircuitIfName,
            cfrExtCircuitIfType,
            cfrExtCircuitSubifIndex,
            cfrExtCircuitMapStatus,
            cfrExtCircuitCreateType,
            cfrExtCircuitMulticast,
            cfrExtCircuitRoutedDlci,
            cfrExtCircuitRoutedIf,
            cfrExtCircuitUncompressIns,  
            cfrExtCircuitUncompressOuts,
            cfrMapIndex,
            cfrMapProtocol,
            cfrMapAddress,
            cfrMapType,
            cfrMapEncaps,
            cfrMapBroadcast,
-- removed  cfrMapPayloadCompress, obsoleted by cfrMapPayloadCompressType
            cfrMapTcpHdrCompress,
            cfrMapRtpHdrCompress,          
            cfrMapPayloadCompressType,    
            cfrSvcAddrLocal,
            cfrSvcAddrRemote,
            cfrSvcThroughputIn,
            cfrSvcMinThruputOut,
            cfrSvcMinThruputIn,
            cfrSvcCommitBurstIn,
            cfrSvcExcessBurstIn,
            cfrSvcIdleTime
        }
        STATUS  deprecated       
        DESCRIPTION
                "A collection of objects providing router's
                Frame Relay configuration and statistics
                information that are additional to the IETF
                standard Frame Relay DTE MIB."
        ::= { ciscoFrMIBGroups 2 }

ciscoFrLmiMIBGroup    OBJECT-GROUP
        OBJECTS { 
            cfrLmiLinkstatus, cfrLmiLinkType, cfrLmiEnquiryIns,
            cfrLmiEnquiryOuts, cfrLmiStatusIns, cfrLmiStatusOuts,
            cfrLmiUpdateStatusIns, cfrLmiUpdateStatusOuts,
            cfrLmiStatusTimeouts, cfrLmiStatusEnqTimeouts,
            cfrLmiN392Dce, cfrLmiN393Dce, cfrLmiT392Dce
        }   
        STATUS current
        DESCRIPTION
                "A collection of objects providing router's
                 Frame Relay LMI configuration and statistics
                 information either supplemental to the 
                 frDlcmiTable of RFC 1315 or specific to Cisco's 
                 implementation."
        ::= { ciscoFrMIBGroups 3 }

ciscoFrCircuitMIBGroup    OBJECT-GROUP
        OBJECTS { 
            cfrCircuitDEins, cfrCircuitDEouts,
            cfrCircuitDropPktsOuts, cfrCircuitType
        }   
        STATUS current
        DESCRIPTION
                "A collection of objects providing information of a
                circuit that are not included in frCircuitTable of
                RFC1315 but are generic to Frame Relay."
        ::= { ciscoFrMIBGroups 4 }

ciscoExtCircuitMIBGroup    OBJECT-GROUP
        OBJECTS { 
            cfrExtCircuitIfName, cfrExtCircuitIfType,
            cfrExtCircuitSubifIndex, cfrExtCircuitMapStatus,
            cfrExtCircuitCreateType, cfrExtCircuitMulticast,
            cfrExtCircuitRoutedDlci, cfrExtCircuitRoutedIf,
            cfrExtCircuitUncompressIns, cfrExtCircuitUncompressOuts,
            cfrExtCircuitFECNOuts, cfrExtCircuitBECNOuts,
            cfrExtCircuitMinThruputOut, cfrExtCircuitMinThruputIn,
            cfrExtCircuitBcastPktOuts, cfrExtCircuitBcastByteOuts,
            cfrExtCircuitBandwidth
        }   
        STATUS  deprecated       
        DESCRIPTION
                "A collection of objects that provide Cisco 
                implementation specific FR circuit information. 
                This is a Cisco extension for the frCircuitTable 
                of RFC 1315."
        ::= { ciscoFrMIBGroups 5 }

ciscoExtCircuitMIBGroup1    OBJECT-GROUP
        OBJECTS {
            cfrExtCircuitIfName, cfrExtCircuitIfType,
            cfrExtCircuitSubifIndex, cfrExtCircuitMapStatus,
            cfrExtCircuitCreateType, cfrExtCircuitMulticast,
            cfrExtCircuitRoutedDlci, cfrExtCircuitRoutedIf,
            cfrExtCircuitUncompressIns, cfrExtCircuitUncompressOuts,
            cfrExtCircuitFECNOuts, cfrExtCircuitBECNOuts,
            cfrExtCircuitMinThruputOut, cfrExtCircuitMinThruputIn,
            cfrExtCircuitBcastPktOuts, cfrExtCircuitBcastByteOuts,
            cfrExtCircuitBandwidth, cfrExtCircuitTxDataRate,
            cfrExtCircuitTxPktRate, cfrExtCircuitRcvDataRate,
            cfrExtCircuitRcvPktRate
        }
        STATUS current
        DESCRIPTION
                "A collection of objects that provide Cisco
                implementation specific FR circuit information.
                This is a Cisco extension for the frCircuitTable
                of RFC 1315."
        ::= { ciscoFrMIBGroups 13 }

ciscoFrTsMIBGroup    OBJECT-GROUP
        OBJECTS { 
            cfrExtCircuitShapeByteLimit, cfrExtCircuitShapeInterval,
            cfrExtCircuitShapeByteIncrement, cfrExtCircuitShapePkts,
            cfrExtCircuitShapeBytes, cfrExtCircuitShapePktsDelay,
            cfrExtCircuitShapeBytesDelay, cfrExtCircuitShapeActive,
            cfrExtCircuitShapeAdapting
        }   
        STATUS current
        DESCRIPTION
                "A collection of objects that provide information
                about Frame Relay Traffic Shaping. These are 
                additional to the IETF standard Frame Relay DTE MIB." 
        ::= { ciscoFrMIBGroups 6 }

ciscoFrMapMIBGroup    OBJECT-GROUP
        OBJECTS { 
            cfrMapIndex, cfrMapProtocol, cfrMapAddress,
            cfrMapType, cfrMapEncaps, cfrMapBroadcast,
            cfrMapTcpHdrCompress, cfrMapRtpHdrCompress,         
            cfrMapPayloadCompressType  
        }   
        STATUS current
        DESCRIPTION
                "A collection of objects to provide mapping 
                information of a Frame Relay virtual circuit.
                These are additional to the IETF standard 
                Frame Relay DTE MIB."
        ::= { ciscoFrMIBGroups 7 }

ciscoFrSvcMIBGroup    OBJECT-GROUP
        OBJECTS { 
            cfrSvcAddrLocal,
            cfrSvcAddrRemote,
            cfrSvcThroughputIn,
            cfrSvcCommitBurstIn,
            cfrSvcExcessBurstIn,
            cfrSvcIdleTime
        }   
        STATUS current
        DESCRIPTION
                "A collection of objects to provide circuit
                information specific to a Frame Relay Switched
                Virtual Circuit.This is in addition to the IETF 
                standard Frame Relay DTE MIB."        
        ::= { ciscoFrMIBGroups 8 }

ciscoFrElmiMIBGroup    OBJECT-GROUP
        OBJECTS {
            cfrElmiIpAddr, cfrElmiArStatus, cfrElmiRemoteStatus,
            cfrElmiNeighborArStatus, cfrElmiNeighborIpAddress,
            cfrElmiNeighborIfIndex, cfrElmiNeighborVendorName,
            cfrElmiNeighborPlatformName, cfrElmiNeighborDeviceName
        }
        STATUS deprecated
        DESCRIPTION
                "A collection of objects providing router's
                ELMI information."
        ::= { ciscoFrMIBGroups 9 }

ciscoFrElmiMIBGroup1    OBJECT-GROUP
        OBJECTS {
            cfrElmiIpAddr, cfrElmiArStatus, cfrElmiRemoteStatus,
            cfrElmiNeighborArStatus, cfrElmiNeighborIpAddress,
            cfrElmiNeighborIfIndex, cfrElmiNeighborVendorName,
            cfrElmiNeighborPlatformName, cfrElmiNeighborDeviceName,
            cfrElmiLinkStatus
        }
        STATUS current
        DESCRIPTION
                "A collection of objects providing router's
                ELMI information."
        ::= { ciscoFrMIBGroups 10 }

ciscoFrFragMIBGroup    OBJECT-GROUP
        OBJECTS {
            cfrFragSize, cfrFragType, cfrFragInPkts, cfrFragOutPkts,
            cfrFragInOctets, cfrFragOutOctets, cfrFragNotInPkts,
            cfrFragNotOutPkts, cfrFragNotInOctets, cfrFragNotOutOctets,
            cfrFragAssembledInPkts, cfrFragAssembledInOctets, 
            cfrFragPreOutPkts, cfrFragPreOutOctets,
            cfrFragDroppedReAssembledInPkts, 
            cfrFragDroppedFragmentedOutPkts,
            cfrFragTimeoutsIn, cfrFragOutOfSeqFragPkts,
            cfrFragUnexpectedBBitSetPkts, cfrFragSeqMissedPkts, 
            cfrFragInterleavedOutPkts  
        }
        STATUS current
        DESCRIPTION
                "A collection of objects providing router's
                fragmentation information."
        ::= { ciscoFrMIBGroups 11 }

ciscoFrConnMIBGroup    OBJECT-GROUP
        OBJECTS {
            cfrConnName, cfrConnID, cfrConnState, cfrConnSegment1Name,
            cfrConnSegment1VCGroup, cfrConnSegment1Dlci,  
            cfrConnSegment2Name, cfrConnSegment2Vpi,
            cfrConnSegment2Vci, cfrConnServiceTranslation, 
            cfrConnFrSscsDlci, cfrConnEfciBit,
            cfrConnDeBit, cfrConnClpBit        
        }
        STATUS current
        DESCRIPTION
                "A collection of objects providing router's
                fragmentation information."
        ::= { ciscoFrMIBGroups 12 }

END
