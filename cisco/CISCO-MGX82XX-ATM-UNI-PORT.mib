CISCO-MGX82XX-ATM-UNI-PORT-MIB DEFINITIONS ::= BEGIN
IMPORTS
    MODULE-IDENTITY,
    OBJECT-TYPE,
    Integer32
                               FROM SNMPv2-SMI
    MODULE-COMPLIANCE,
    OBJECT-GROUP               FROM SNMPv2-CONF
    AtmAddress, NetPrefix      FROM ATM-FORUM-TC-MIB
    atmAddressRegistration     FROM BASIS-MIB
    ciscoWan                   FROM CISCOWAN-SMI;

ciscoMgx82xxAtmUniPortMIB MODULE-IDENTITY
    LAST-UPDATED    "200304180000Z"
    ORGANIZATION    "Cisco Systems, Inc."
    CONTACT-INFO
            "       Cisco Systems
                        Customer Service

                Postal: 170 W Tasman Drive
                        San Jose, CA  95134
                        USA

                        Tel: +1 800 553-NETS

                E-mail: cs-wanatm@cisco.com"
    DESCRIPTION
        "The MIB module containing objects related to
        user-side of the ATM UNI Port.

        The mib is applicable for MGX8250 and MGX8220 products.
        Terminologies used:

       UNI     :  User Network Interface.
       "

    REVISION    "200304180000Z"
    DESCRIPTION
        "Initial version of the MIB.

        The content of this MIB was originally available
        in CISCO-WAN-AXIPOP-MIB defined using SMIv1.
        The applicable objects from CISCO-WAN-AXIPOP-MIB
        are defined using SMIv2 in this MIB. Also the
        descriptions of some of the objects have been 
        modified."
    ::= { ciscoWan 71 }

atmNetPrefixGroup    	OBJECT IDENTIFIER ::= { atmAddressRegistration 1 }
atmAddressGroup   	OBJECT IDENTIFIER ::= { atmAddressRegistration 2 }

--
-- The Address Table
--
atmAddressTable OBJECT-TYPE
    SYNTAX      SEQUENCE OF AtmAddressEntry
    MAX-ACCESS      not-accessible
    STATUS      current
    DESCRIPTION
        "A table implemented by the network-side of an ATM 
        UNI port, containing the ATM-layer addresses in effect
        on the user-side of the UNI."
    ::= { atmAddressGroup 1 }

atmAddressEntry OBJECT-TYPE
    SYNTAX      AtmAddressEntry
    MAX-ACCESS      not-accessible
    STATUS      current
    DESCRIPTION
        "Information about a single ATM-layer address in effect 
        on the user-side of a UNI port."
    INDEX    { axisAtmAddressPort, axisAtmAddressAtmAddress}
    ::= { atmAddressTable 1 }

AtmAddressEntry ::= SEQUENCE {
    axisAtmAddressPort             Integer32,
    axisAtmAddressAtmAddress       AtmAddress,
    axisAtmAddressStatus           INTEGER
}

axisAtmAddressPort  OBJECT-TYPE
    SYNTAX      Integer32 (0..2147483647)
    MAX-ACCESS  read-only
    STATUS      current
    DESCRIPTION
        "A unique value which identifies this port. The value of
        0 has the special meaning of identifying the local UNI."
    ::= { atmAddressEntry 1 }

axisAtmAddressAtmAddress OBJECT-TYPE
    SYNTAX      AtmAddress
    MAX-ACCESS  read-only
    STATUS      current
    DESCRIPTION
        "The ATM address which is in effect on the user-side 
        of the ATM UNI port."
    ::= { atmAddressEntry 2 }

axisAtmAddressStatus OBJECT-TYPE
    SYNTAX      INTEGER {
                    valid(1),
                    invalid(2)
                }
    MAX-ACCESS      read-only
    STATUS      current
    DESCRIPTION
        "An indication of the validity of the ATM address at
        the user-side of the UNI port."
    ::= { atmAddressEntry 3 }

--  The Network Prefix Table

atmNetPrefixTable OBJECT-TYPE
    SYNTAX      SEQUENCE OF AtmNetPrefixEntry
    MAX-ACCESS  not-accessible
    STATUS      current
    DESCRIPTION
        "A table implemented by the UNI Management Entity on
        the user-side of an ATM UNI port, containing the     
        network-prefix(es) for ATM-layer addresses
        in effect on the user-side of the UNI."
    ::= { atmNetPrefixGroup 1 }

atmNetPrefixEntry OBJECT-TYPE
    SYNTAX      AtmNetPrefixEntry
    MAX-ACCESS      not-accessible
    STATUS      current
    DESCRIPTION
        "An entry in the table, containing information about
        the ATM Prefix status."
    INDEX    { axisAtmNetPrefixPort, axisAtmNetPrefixPrefix }
    ::= { atmNetPrefixTable 1 }

AtmNetPrefixEntry ::= SEQUENCE {
    axisAtmNetPrefixPort             Integer32,
    axisAtmNetPrefixPrefix           NetPrefix,
    axisAtmNetPrefixAdminStatus      INTEGER,
    axisAtmNetPrefixOperStatus       INTEGER
}

axisAtmNetPrefixPort OBJECT-TYPE
    SYNTAX      Integer32 (0..2147483647)
    MAX-ACCESS  read-only
    STATUS      current
    DESCRIPTION
        "The unique value which identifies the ILMI port."
    ::= { atmNetPrefixEntry 1 }

axisAtmNetPrefixPrefix OBJECT-TYPE
    SYNTAX      NetPrefix
    MAX-ACCESS  read-only
    STATUS      current
    DESCRIPTION
        "The network prefix for ATM addresses which is in effect
	on the user-side of the ATM UNI port."
    ::= { atmNetPrefixEntry 2 }

axisAtmNetPrefixAdminStatus OBJECT-TYPE
    SYNTAX      INTEGER {
                    valid(1),
                    invalid(2)
                }
    MAX-ACCESS  read-write
    STATUS      current
    DESCRIPTION
        "An indication of the validity of the network prefix 
        for ATM addresses, on the user-side of the UNI port."
    ::= { atmNetPrefixEntry 3 }

axisAtmNetPrefixOperStatus OBJECT-TYPE
    SYNTAX      INTEGER {
                    registering(1),
                    de-registering(2),
		    registered(3),
		    de-registered(4),
		    failRegistering(5),
		    failDe-registering(6)
                }
    MAX-ACCESS read-only
    STATUS     current
    DESCRIPTION
        "An indication of the current registration state for
        the prefix."
    ::= { atmNetPrefixEntry 4 }

-- conformance information

cmauPortMIBConformance  OBJECT IDENTIFIER ::= 
				{ ciscoMgx82xxAtmUniPortMIB 2 }

cmauPortMIBGroups       OBJECT IDENTIFIER ::= 
                              { cmauPortMIBConformance 1 }

cmauPortMIBCompliances  OBJECT IDENTIFIER ::= 
                              { cmauPortMIBConformance 2 }

-- compliance statements

cmauPortCompliance MODULE-COMPLIANCE
    STATUS  current
    DESCRIPTION
        "The compliance statement for objects related
        to ATM UNI ports."
    MODULE  -- this module
        MANDATORY-GROUPS {
            cmauAtmAddressGroup,
            cmauNetPrefixGroup
        }
    ::= { cmauPortMIBCompliances 1 }

cmauAtmAddressGroup OBJECT-GROUP
    OBJECTS {
        axisAtmAddressPort,
        axisAtmAddressAtmAddress,
        axisAtmAddressStatus
      }
      STATUS current
      DESCRIPTION
          "The collection of objects which are used to represent
          ATM Port information."
      ::= { cmauPortMIBGroups 1 }

cmauNetPrefixGroup OBJECT-GROUP
    OBJECTS {
        axisAtmNetPrefixPort,
        axisAtmNetPrefixPrefix,
        axisAtmNetPrefixAdminStatus,
        axisAtmNetPrefixOperStatus
      }
    STATUS current
      DESCRIPTION 
         "The collection of objects related to
         ATM address prefix."
      ::= { cmauPortMIBGroups 2 }

END
