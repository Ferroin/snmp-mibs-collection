CISCO-WAN-NCDP-MIB DEFINITIONS ::= BEGIN

IMPORTS
        MODULE-IDENTITY,    
        OBJECT-TYPE,
        Integer32               FROM SNMPv2-SMI

        TEXTUAL-CONVENTION, 
        TruthValue,
        TimeStamp,          
        DisplayString,
        RowStatus               FROM SNMPv2-TC

        ciscoMgmt               FROM CISCO-SMI

        ifIndex,  
        InterfaceIndexOrZero    FROM IF-MIB

        MODULE-COMPLIANCE,  
        OBJECT-GROUP            FROM SNMPv2-CONF;

ciscoWanNcdpMIB   MODULE-IDENTITY
        LAST-UPDATED    "200111070000Z"
        ORGANIZATION    "Cisco System Inc."
        CONTACT-INFO
                "       Cisco Systems
                        Customer Service

                Postal: 170 West Tasman Drive,
                        San Jose CA 95134-1706.
                        USA

                   Tel: +1 800 553-NETS

                E-mail: cs-atm@ciscoWAN.com"
        DESCRIPTION
                "This MIB module is intended for the management of network clock 
                distribution and the Network Clock Distribution Protocol (NCDP) 
                in Cisco MGX ATM switches. This MIB allows enabling automatic network 
                clock configuration and distribution as well as configuration of 
                manual clock sources.  

                NCDP allows automatic distribution of network clocking sources
                in the network. A spanning network clock distribution tree is
                constructed by each node in the network and each node is 
                synchonized to one single 'master' clock reference. 

                A source of network clock for the device may be an oscillator
                local to the device or a Building Integrated Timing Supply (BITS)
                port or an interface that supports synchronous clock recovery.

                An 'index'('cwnClockSourceIndex') is assigned by the NCDP
                protocol entity in the managed system to identify each available 
                source of network clock on the managed system."   

        REVISION        "200111070000Z"
        DESCRIPTION     "Initial version of the MIB."
        ::= { ciscoMgmt 223 }

-- CISCO-WAN-NCDP-MIB MIB groups
cwnMIBObjects OBJECT IDENTIFIER 
                                        ::= { ciscoWanNcdpMIB 1 }

cwnGlobal       
                        OBJECT IDENTIFIER ::= { cwnMIBObjects 1 }
cwnClockSource   
                        OBJECT IDENTIFIER ::= { cwnMIBObjects 2 } 
cwnManualSource
                        OBJECT IDENTIFIER ::= { cwnMIBObjects 3 }
cwnAtmSource            OBJECT IDENTIFIER ::= { cwnMIBObjects 4 }
cwnAtmInterface         OBJECT IDENTIFIER ::= { cwnMIBObjects 5 }

-- textual conventions

ClockStratum ::= TEXTUAL-CONVENTION
        STATUS          current
        DESCRIPTION
                "The stratum level associated with a source of network clock
                or a device."
        REFERENCE
                "American National Standards Institute, ANSI T1.101,
                'Synchronization Interface for Digital Networks'.

                Bell Communications Research, GR-436-CORE, 'Digital Network
                Synchronization Plan'."  
        SYNTAX  INTEGER { other(1),
                          s1(2),
                          s2e(3),
                          s2(4),
                          s3e(5),
                          s3(6),
                          s4e(7),
                          s4(8)
                }

ClockHealthStatus ::= TEXTUAL-CONVENTION
        STATUS          current
        DESCRIPTION
                "The health of a source of network clock.

                A value of 'good' indicates that a given source of network
                clock is known by the managed system to be good. This 
                indicates the managed system was able to 'lock' onto the
                clock source.

                A value of 'bad' indicates that a given source of network clock
                is known by the managed system to be bad. This indicates the
                managed system was not able to 'lock' onto the clock source.

                A value of 'unknown' indicates that the health of the source of
                network clock is unknown to the managed system. This indicates
                the managed system has not tried to 'lock' onto the clock source."
        SYNTAX  INTEGER { good(1),
                          bad(2),
                          unknown(3)
                }

ClockSourceIndex ::= TEXTUAL-CONVENTION
        STATUS          current 
        DESCRIPTION
                "An 'index' assigned by the device that uniquely identifies an
                available clock source on the device." 
        SYNTAX   Integer32 (1..2147483647)

-- scalars

cwnDistributionMethod OBJECT-TYPE
        SYNTAX  INTEGER { ncdp(1), 
                          manual(2)
                }
        MAX-ACCESS      read-write
        STATUS          current
        DESCRIPTION   
                "The method used to distribute network clock for the device.

                When the mode of operation is 'ncdp', this device participates 
                in NCDP protocol. A single 'master' clock source will be 
                identified as the clock source for this network as a result.
                The tables 'cwnAtmSourceTable' and 'cwnAtmInterfaceTable'
                are used in this mode.

                When the mode of operation is 'manual', the network clock source
                is statically configured in this device. 
                The table 'cwnManualSourceTable' is used in this mode."
        DEFVAL { ncdp }
        ::= { cwnGlobal 1 }

cwnNodeStratum OBJECT-TYPE
        SYNTAX          ClockStratum
        MAX-ACCESS      read-only
        STATUS          current
        DESCRIPTION
                "This variable contains the stratum level of the node. 

                This object is only used if the distribution method is 'ncdp'."
        DEFVAL { s2 }
        ::= { cwnGlobal 2 }

cwnMaxDiameter OBJECT-TYPE
        SYNTAX          Integer32 (3..255)
        MAX-ACCESS      read-write
        STATUS          current
        DESCRIPTION
                "The maximum possible height of a network clock distribution 
                tree in the network.  

                This variable must be configured with the same value for 
                all devices participating in NCDP within the network.

                This object is only used if the distribution method is 'ncdp'."
        DEFVAL { 20 }
        ::= { cwnGlobal 3 }

cwnMessageInterval OBJECT-TYPE
        SYNTAX          Integer32 (75..60000)
        UNITS           "milliseconds"
        MAX-ACCESS      read-write
        STATUS          current
        DESCRIPTION   
                "The interval at which NCDP configuration PDUs ('Hellos') are to be 
                generated.

                The message interval directly affects the convergence time of 
                the NCDP algorithm.  Convergence time is equal to 
                        the max network diameter * message interval + 
                        transmission delays + 
                        the time a configuration PDU is spent being processed 
                        in each device. 
                Thus if transmission delays and processing delays are
                both close to 0, the convergence time is approximately 
                ( max network diameter * message interval ) milliseconds.

                This object is only used if the distribution method is 'ncdp'."
        DEFVAL     { 500 }
        ::= { cwnGlobal 4 }

cwnHoldTime OBJECT-TYPE
        SYNTAX          Integer32 (75..60000)
        UNITS           "milliseconds"
        MAX-ACCESS      read-write
        STATUS          current
        DESCRIPTION   
                "The minimum delay between the transmission of two consecutive
                NCDP configuration PDUs on an interface.

                The value of this object should normally be set to match the 
                value of cwnMessageInterval.  If the value of this object 
                is higher than the value of cwnMessageInterval, NCDP 
                configuration PDUs will end up being propagated at the
                rate specified by the value of this object instead.

                This object is only used if the distribution method is 'ncdp'."
        DEFVAL     { 500 }
        ::= { cwnGlobal 5 }

cwnChangeReason OBJECT-TYPE
        SYNTAX  INTEGER { other(1),
                          none(2),
                          lossOfLock(3),
                          lossOfActivity(4),
                          ncdpRestructure(5)
                }
        MAX-ACCESS    read-only
        STATUS        current
        DESCRIPTION
                "The reason for the most recent change of a source of 
                network clock, as indicated by the change in the value 
                of 'ciscoWanChangeTimeStamp'.

                'none' indicates that the source of network clock 
                has not changed.

                'lossOfLock' indicates that the clock source was 
                changed because the network clocking hardware lost 
                lock on the previous network clock source.

                'lossOfActivity' indicates that the clock source was changed
                because the network clocking hardware detected a loss of 
                activity on the previous network clock source.

                'ncdpRestructure' indicates that the NCDP entity has changed 
                the clock source as a result of a network-wide network clock 
                distribution tree restructuring process.

                When the reason for a clock switchover is none of the 
                above, the value of this object is 'other'."
        ::= { cwnGlobal 6 }

cwnChangeTimeStamp OBJECT-TYPE
        SYNTAX        TimeStamp
        MAX-ACCESS    read-only
        STATUS        current
        DESCRIPTION
                "The value of sysUpTime when the most recent change of a source
                of network clock occurred.

                A value of 0 indicates that no such event has occurred since 
                the instantiation of this object."
        DEFVAL { 0 }    
        ::= { cwnGlobal 7 }

cwnRootClockSource OBJECT-TYPE
        SYNTAX        ClockSourceIndex 
        MAX-ACCESS    read-only
        STATUS        current
        DESCRIPTION
                "The 'index' of the network clock source that is 
                actively supplying network clock within the device.

                When the value of this variable is used as an index into the  
                'cwnAtmSourceTable' and the indicated clock source 
                has 'cwnAtmSourceBestClockSource' with value 'true', then the 
                indicated clock source is the root of some clock distribution tree." 
        ::= { cwnGlobal 8 }

-- table of objects representing available clock sources on the device

cwnClockSourceTable OBJECT-TYPE
        SYNTAX     SEQUENCE OF CwnClockSourceEntry
        MAX-ACCESS not-accessible
        STATUS     current
        DESCRIPTION
                "A table of network clock sources available to the managed
                system."
        ::= { cwnClockSource 1 }

cwnClockSourceEntry OBJECT-TYPE
        SYNTAX     CwnClockSourceEntry
        MAX-ACCESS not-accessible
        STATUS     current
        DESCRIPTION
                "An entry in this table contains an available clock source 
                on the device.

                A source of network clock for the device may be an oscillator
                local to the device or a Building Integrated Timing Supply (BITS)
                port or an interface that supports synchronous clock recovery.

                An index is assigned by the device to uniquely identify each of 
                the source of networking clock on the managed system.

                A description is associated with each clock source.
                This description gives detail information of this clock source.

                The management station should poll this table to obtain 
                these 'cwnClockSourceIndex' and use these indexes 
                to configure clock source in 
                'cwnManualSourceTable' or 'cwnAtmSourceTable'."
    INDEX { cwnClockSourceIndex }
    ::= { cwnClockSourceTable 1 }

CwnClockSourceEntry ::=
        SEQUENCE {
            cwnClockSourceIndex         ClockSourceIndex,
            cwnClockSourceDesc          DisplayString, 
            cwnInterfaceIndex           InterfaceIndexOrZero,
            cwnOtherClockSource         INTEGER
        }

cwnClockSourceIndex OBJECT-TYPE
        SYNTAX        ClockSourceIndex
        MAX-ACCESS    not-accessible
        STATUS        current
        DESCRIPTION
                "An 'index' assigned by the device which uniquely
                identifies an available clock source on the device.
                "
        ::= { cwnClockSourceEntry 1 }

cwnClockSourceDesc OBJECT-TYPE
        SYNTAX        DisplayString 
        MAX-ACCESS    read-only 
        STATUS        current
        DESCRIPTION
                "A description of the clock source associated with this entry.
                The description contains port/type information of this 
                clock source.

                The format of this entry is implementation specific." 
        ::= { cwnClockSourceEntry 2 }

cwnInterfaceIndex OBJECT-TYPE
        SYNTAX        InterfaceIndexOrZero 
        MAX-ACCESS    read-only
        STATUS        current 
        DESCRIPTION
                "If this variable has a non-zero value, this is
                the 'ifIndex' associated with this entry.

                The 'ifIndex' identifies an ATM Virtual Interface
                (ifType 'atmVirtual(149)').

                If this variable has a value of 'zero', this entry
                is not associated with an 'ifIndex' and its type
                is identified by 'cwnOtherClockSource'." 
       ::= { cwnClockSourceEntry 3 }

cwnOtherClockSource OBJECT-TYPE
        SYNTAX        INTEGER {
                         none(1),
                         internalOscillator(2),
                         bitsClockE1(3),
                         bitsClockT1(4) 
                      }
        MAX-ACCESS    read-only 
        STATUS        current
        DESCRIPTION
                "This variable identifies the type of a clock source that
                does not have an 'ifIndex' associated. 

                This value is 'none(1) if 'cwnInterfaceIndex' 
                contains a non-zero value.

                The value 'internalOscillator(1) indicates a clock source
                is an oscillator local to the device.

                The value 'bitsClockE1(2) indicates a Building Integrated 
                Timing Supply (BITS) clock source on an E1 port. 

                The value 'bitsClockT1(3) indicates a BITS clock source 
                on a T1 port."
        ::= { cwnClockSourceEntry 4 }

-- table of objects to configure manual network clock sources

cwnManualSourceTable OBJECT-TYPE
        SYNTAX     SEQUENCE OF CwnManualSourceEntry
        MAX-ACCESS not-accessible
        STATUS     current
        DESCRIPTION
                "A table of network clock sources to be manually 
                configured for the managed system." 
        ::= { cwnManualSource 1 }

cwnManualSourceEntry OBJECT-TYPE
        SYNTAX     CwnManualSourceEntry
        MAX-ACCESS not-accessible
        STATUS     current
        DESCRIPTION
                "When the value of cwnDistributionMethod is 'manual',
                the managed system uses this table to select a source of
                network clock for the managed system from the entries in
                'cwnClockSourceTable'.  

                The management system uses 'cwnClockSourceIndex' 
                to configure the associated clock source to be a primary, 
                secondary or default clock source.

                A source of network clock for the device may be an oscillator
                local to the device or a Building Integrated Timing Supply (BITS)
                port or an interface that supports synchronous clock recovery.

                When the managed system initializes it creates a row for the
                device's default source of network clock, (the entry having
                'cwnManualSourcePriority' with value 'default').
                Only read operations is allowed on the columnar objects in this row. 

                Other rows are created or destroyed by a management station or
                through the device's local management interface when a source
                of network clock is configured or removed.  

                A row is not made active until a valid value for 
                'cwnManualSourceIndex' is supplied.  

                A management station may perform a write operation on any 
                columnar object while the row is active or not in service.
                "
    INDEX { cwnManualSourcePriority }
    ::= { cwnManualSourceTable 1 }

CwnManualSourceEntry ::=
        SEQUENCE {
            cwnManualSourcePriority  INTEGER,
            cwnManualSourceIndex     ClockSourceIndex,
            cwnManualClockHealth     ClockHealthStatus,  
            cwnManualRowStatus       RowStatus
        }

cwnManualSourcePriority OBJECT-TYPE
        SYNTAX  INTEGER { primary(1),
                          secondary(2),
                          default(3)
                }
        MAX-ACCESS    not-accessible
        STATUS        current
        DESCRIPTION
                "A value used to configure an available network clock source to be
                 primary, secondary or default manual clock source." 
        ::= { cwnManualSourceEntry 1 }

cwnManualSourceIndex OBJECT-TYPE
        SYNTAX        ClockSourceIndex 
        MAX-ACCESS    read-create 
        STATUS        current
        DESCRIPTION
                "An 'index' value used to identify the primary, 
                 secondary ,or default manual clock source."
        ::= { cwnManualSourceEntry 2 }

cwnManualClockHealth OBJECT-TYPE
        SYNTAX        ClockHealthStatus 
        MAX-ACCESS    read-only
        STATUS        current
        DESCRIPTION
                "The health of the clock source."
        ::= { cwnManualSourceEntry 3 }

cwnManualRowStatus OBJECT-TYPE
        SYNTAX      RowStatus
        MAX-ACCESS  read-create
        STATUS      current
        DESCRIPTION
                "The status of this conceptual row."
        ::= { cwnManualSourceEntry 4 }

-- table of objects representing network clock sources 
-- advertised by ncdp

cwnAtmSourceTable OBJECT-TYPE
        SYNTAX     SEQUENCE OF CwnAtmSourceEntry
        MAX-ACCESS not-accessible
        STATUS     current
        DESCRIPTION
                "A table of configured network clock sources 
                advertised by this managed system when using
                NCDP."
        ::= { cwnAtmSource 1 }

cwnAtmSourceEntry OBJECT-TYPE
        SYNTAX     CwnAtmSourceEntry
        MAX-ACCESS not-accessible
        STATUS     current
        DESCRIPTION
                "Network clock status for sources of network
                clock identified by 'cwnClockSourceIndex' and used by 
                the managed system when the value of 
                'cwnDistributionMethod' is 'ncdp'. 

                The managed device selects one entry in this table to
                advertise as the best available clock source for the device.

                Cooperating NCDP protocol entities select the best available
                clock source among those advertised within the cooperating
                group and build a clock distribution tree rooted at that clock
                source.  When the value of 'cwnRootClockSource' is used 
                as an index into this table and the indicated clock source has
                'cwnAtmSourceBestClockSource' with value 'true' then the indicated
                clock source is the root of some clock distribution tree.  If
                only one such root exists on all participating devices in the
                network, then it is the root of a network wide clock
                distribution tree.

                When the managed system initializes it creates a row for the
                device's default source of network clock.  This row cannot be
                destroyed by a management station.  Within this row a write
                operation is only allowed on the 'cwnAtmSourcePriority' object.
                The status of this row is always active. The default source
                can always be found by issuing a  read operation on the row within
                'cwnManualSourceTable' that has 'default' as the value 
                of 'cwnManualSourcePriority'. 

                The other rows are created or destroyed by a management station or
                through the device's local management interface when a source
                of network clock is configured or removed.  

                The values of 'cwnAtmSourcePriority', 'cwnAtmSourceStratum' and
                'cwnAtmSourcePRSReference' collectively describe a source of network
                clock. They are the three components of a vector used as an
                input to the NCDP algorithm to make clock source selection
                decisions." 
        INDEX { cwnClockSourceIndex }
        ::= { cwnAtmSourceTable 1 }

CwnAtmSourceEntry ::=
        SEQUENCE {
                cwnAtmSourceBestClockSource             TruthValue,
                cwnAtmSourcePriority                    Integer32,
                cwnAtmSourceStratum                     ClockStratum,
                cwnAtmSourcePRSReference                INTEGER,
                cwnAtmSourceClockHealth                 ClockHealthStatus,
                cwnAtmSourceRowStatus                   RowStatus
        }

cwnAtmSourceBestClockSource OBJECT-TYPE
        SYNTAX        TruthValue
        MAX-ACCESS    read-only
        STATUS        current
        DESCRIPTION   
                "An indication of whether this is the best clock source being
                advertised." 
        ::= { cwnAtmSourceEntry 1 }

cwnAtmSourcePriority OBJECT-TYPE
        SYNTAX        Integer32 (1..255)
        MAX-ACCESS    read-create
        STATUS        current
        DESCRIPTION
                "The network-wide priority of this clock source if configured
                as a source of network clock for NCDP.  The highest priority
                clock source is that clock source having the lowest positive
                numeric value.  The clock source with the highest priority is
                selected as the root of the clock distribution tree by the NCDP
                algorithm.  If more that one clock source is configured with
                with the same priority the NCDP algorithm uses the value
                'cwnAtmSourceStratum' as a tiebreaker."
        DEFVAL { 128 }
        ::= { cwnAtmSourceEntry 2 }

cwnAtmSourceStratum OBJECT-TYPE
        SYNTAX        ClockStratum
        MAX-ACCESS    read-create
        STATUS        current
        DESCRIPTION   
                "The stratum level associated with this clock source if 
                configured as a source of network clock for NCDP. 
                If the value of this object is used as a tiebreaker
                , the lower of the given values is the winner.
                If the values are the same, the value of
                'cwnAtmSourcePRSReference' is used as a tiebreaker by the 
                NCDP algorithm."
        DEFVAL { s2 }
        ::= { cwnAtmSourceEntry 3 }

cwnAtmSourcePRSReference OBJECT-TYPE
        SYNTAX        INTEGER { internal(1),
                                external(2)
                                }
        MAX-ACCESS    read-create
        STATUS        current
        DESCRIPTION   
                "An value that identifies the Primary Reference Source that 
                the network clock available from this source is traceable to  
                if configured as a source of network clock for NCDP. 

                The object takes the value 'internal' when the PRS for this
                source is an onboard oscillator local to the device. For any  
                other cases the value 'external' is used.  

                If the value of this object is used as a tiebreaker by the 
                algorithm,'external' wins over 'internal'. 

                All 'external' sources of network clock are assumed to be
                traceable to the same PRS by the NCDP protocol entity."
        ::= { cwnAtmSourceEntry 4 }

cwnAtmSourceClockHealth OBJECT-TYPE
        SYNTAX        ClockHealthStatus
        MAX-ACCESS    read-only
        STATUS        current
        DESCRIPTION
                "The health of the clock source."
        ::= { cwnAtmSourceEntry 5 }

cwnAtmSourceRowStatus OBJECT-TYPE
        SYNTAX      RowStatus
        MAX-ACCESS  read-create
        STATUS      current
        DESCRIPTION
                "The status of this conceptual row."
        ::= { cwnAtmSourceEntry 6 }

-- table of objects used to support ncdp protocol 
-- entity at atm interfaces

cwnAtmInterfaceTable OBJECT-TYPE
        SYNTAX     SEQUENCE OF CwnAtmInterfaceEntry
        MAX-ACCESS not-accessible
        STATUS     current
        DESCRIPTION
                "A table containing the status of NCDP on the device's ATM
                Network-to-Network(NNI) interfaces."
        ::= { cwnAtmInterface 1 }

cwnAtmInterfaceEntry OBJECT-TYPE
    SYNTAX     CwnAtmInterfaceEntry
    MAX-ACCESS not-accessible
    STATUS     current
    DESCRIPTION
                "An entry in this table contains the status of NCDP 
                on an ATM Netowrk-to-Network (NNI) interface.

                A row in this table is created by the managed system and
                disappears when the associated entity disappears.

                When a row is created all of the row objects are instantiated.

                Each entry identified by 'ifIndex' is of ifType 'atmvirtual(149)'.
                "
    INDEX { ifIndex }
    ::= { cwnAtmInterfaceTable 1 }

CwnAtmInterfaceEntry ::=
        SEQUENCE {
                cwnAtmInterfaceEnable           TruthValue,
                cwnAtmInterfaceAdminWeight      Integer32,
                cwnAtmInterfaceVpi              Integer32,
                cwnAtmInterfaceVci              Integer32
        }

cwnAtmInterfaceEnable OBJECT-TYPE
        SYNTAX        TruthValue
        MAX-ACCESS    read-write
        STATUS        current
        DESCRIPTION   
                "An indication of whether NCDP is presently running on an
                ATM Network-to-Network interface.  When NCDP is enabled for 
                an interface, the interface is an active member of the clock
                distribution topology.

                After this object is instantiated by the agent the
                managed system initializes the value of this object to 'true'.

                By default, all Network-to-Network interfaces participate in
                NCDP until it's disabled by setting the value of this object
                to 'false'."
        DEFVAL {true}
        ::= { cwnAtmInterfaceEntry 1 }

cwnAtmInterfaceAdminWeight OBJECT-TYPE
        SYNTAX        Integer32 (1..16777215)
        MAX-ACCESS    read-write
        STATUS        current
        DESCRIPTION   
                "A weight metric used by the NCDP protocol entity and 
                associated with a physical interface that supports synchronous
                clock recovery.  When NCDP is enabled for the physical
                interface the value of this object is used by NCDP algorithms
                during tree computations.

                The lower the administrative weight, the more attractive the
                given link is to the NCDP algorithm.  If the weight of a link
                is changed, it can cause the NCDP protocol entity to
                reconstruct the clock distribution tree."
        DEFVAL { 10 }
        ::= { cwnAtmInterfaceEntry 2 }

cwnAtmInterfaceVpi OBJECT-TYPE
        SYNTAX            Integer32 (0..4095)
        MAX-ACCESS        read-write
        STATUS            current
        DESCRIPTION
                "The Virtual Path Identifier(VPI) value of the Virtual Channel
                Connection(VCC) supporting the NCDP entity at this  
                ATM interface. 

                If the values of 'cwnAtmInterfaceVpi' and 'cwnAtmInterfaceVci'
                are both equal to zero then the NCDP entity 
                is not supported at this ATM interface."
        DEFVAL { 0 }
        ::= { cwnAtmInterfaceEntry 3 }

cwnAtmInterfaceVci OBJECT-TYPE
        SYNTAX           Integer32 (0..65535)
        MAX-ACCESS       read-write
        STATUS           current
        DESCRIPTION
                "The Virtual Channel Identifier(VCI) value of the VCC supporting 
                the NCDP entity at this ATM interface. 

                If the values of 'cwnAtmInterfaceVpi' and 'cwnAtmInterfaceVci'
                are both equal to zero then the NCDP entity 
                is not supported at this ATM interface."
        DEFVAL { 34 }
        ::= { cwnAtmInterfaceEntry 4 }

-- Notification

ciscoWanNcdpMIBNotificationPrefix OBJECT IDENTIFIER ::=
        { ciscoWanNcdpMIB 2 }

ciscoWanNcdpMIBNotifications OBJECT IDENTIFIER ::=
        { ciscoWanNcdpMIBNotificationPrefix 0 }

-- There is no notifications defined for this module.

-- conformance information
ciscoWanNcdpMIBConformance    OBJECT IDENTIFIER 
                                ::= { ciscoWanNcdpMIB 3}
ciscoWanNcdpMIBCompliances OBJECT IDENTIFIER 
                                ::= { ciscoWanNcdpMIBConformance 1 }
ciscoWanNcdpMIBGroups      OBJECT IDENTIFIER 
                                ::= { ciscoWanNcdpMIBConformance 2 }

-- compliance statements

ciscoWanMIBCompliance MODULE-COMPLIANCE
    STATUS  current
    DESCRIPTION
                "The compliance statement for SNMPv2 entities which
                implement network clock distribution methods and NCDP."
    MODULE  -- this module
        MANDATORY-GROUPS { 
                           ciscoWanNcdpGlobalGroup,
                           ciscoWanNcdpClockSourceGroup,
                           ciscoWanNcdpManualGroup,
                           ciscoWanNcdpAtmGroup
                      }
    ::= { ciscoWanNcdpMIBCompliances 1 }

-- units of conformance

ciscoWanNcdpGlobalGroup OBJECT-GROUP
    OBJECTS   {
                cwnDistributionMethod,
                cwnNodeStratum,       
                cwnMaxDiameter,
                cwnMessageInterval,
                cwnHoldTime,
                cwnChangeReason,
                cwnChangeTimeStamp,
                cwnRootClockSource   
              }
    STATUS    current
    DESCRIPTION
                "This group contains global objects providing for 
                management of network clock distribution and NCDP entities."
    ::= { ciscoWanNcdpMIBGroups 1 }

ciscoWanNcdpClockSourceGroup OBJECT-GROUP
    OBJECTS   {
                cwnClockSourceDesc,
                cwnInterfaceIndex,
                cwnOtherClockSource
              }
    STATUS    current
    DESCRIPTION
                "This group contains the available clock source on the
                managed system."
    ::= { ciscoWanNcdpMIBGroups 2 }

ciscoWanNcdpManualGroup OBJECT-GROUP
    OBJECTS   {
                cwnManualSourceIndex,
                cwnManualClockHealth,
                cwnManualRowStatus
              }
    STATUS    current
    DESCRIPTION
                "This group contains objects for manual configuration
                of clock sources on the managed system."
    ::= { ciscoWanNcdpMIBGroups 3 }

ciscoWanNcdpAtmGroup OBJECT-GROUP
    OBJECTS   { 
                cwnAtmSourceBestClockSource,
                cwnAtmSourcePriority,
                cwnAtmSourceStratum,
                cwnAtmSourcePRSReference,
                cwnAtmSourceClockHealth,
                cwnAtmSourceRowStatus,
                cwnAtmInterfaceEnable,                  
                cwnAtmInterfaceAdminWeight,
                cwnAtmInterfaceVpi,                     
                cwnAtmInterfaceVci
              }
    STATUS    current
    DESCRIPTION
                "This group contains objects for configuration of
                NCDP entity on an ATM platform." 
    ::= { ciscoWanNcdpMIBGroups 4 }

END
