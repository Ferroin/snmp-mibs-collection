CISCO-OPTICAL-MONITOR-CAPABILITY DEFINITIONS ::= BEGIN

IMPORTS
    MODULE-IDENTITY,
    Integer32,
    Unsigned32
        FROM SNMPv2-SMI
    AGENT-CAPABILITIES
        FROM SNMPv2-CONF
    ciscoAgentCapability
        FROM CISCO-SMI
    OpticalAlarmSeverityOrZero
        FROM CISCO-OPTICAL-MONITOR-MIB;

ciscoOpticalMonitorCapability MODULE-IDENTITY
    LAST-UPDATED    "200701080000Z"
    ORGANIZATION    "Cisco Systems, Inc."
    CONTACT-INFO
            "Cisco Systems
            Customer Service

            Postal: 170 West Tasman Drive
            San Jose, CA  95134
            USA

            Tel: +1 800 553-NETS

            E-mail: cs-dwdm@cisco.com,
            cs-lan-switch-snmp@cisco.com"
    DESCRIPTION
        "The capabilities description of
        CISCO-OPTICAL-MONITOR-MIB."
    REVISION        "200701080000Z"
    DESCRIPTION
        "Initial version of this MIB module."
          ::= { ciscoAgentCapability 528 }

ciscoOpticalMonCapCatOSV08R0601 AGENT-CAPABILITIES
    PRODUCT-RELEASE "Cisco CatOS 8.6(1)."
    STATUS          current
    DESCRIPTION     "CISCO-OPTICAL-MONITOR-MIB capabilities."

    SUPPORTS        CISCO-OPTICAL-MONITOR-MIB
    INCLUDES        {
                        cOpticalMIBMonGroup,
                        cOpticalMIBThresholdGroup,
                        cOpticalMIBSeverityGroup,
                        cOpticalMIBNotifyEnableGroup,
                        cOpticalMIBNotifGroup,
                        cOpticalMIBEnableConfigGroup,
                        cOpticalMIBIntervalConfigGroup,
                        cOpticalMonThreshSourceGroup,
                        cOpticalMonIfTimeGroup
                    }
    VARIATION       cOpticalMonEnable
    SYNTAX          BITS {
                        all(0)
                    }
    DESCRIPTION
        "The enumerated values supported are all those
        defined at the time this clause was written."

    VARIATION       cOpticalParamHighAlarmSev
    SYNTAX          INTEGER  {
                        critical(1),
                        major(2),
                        minor(3)
                    }
    DESCRIPTION
        "Only limited set of enumerated values
        are supported."

    VARIATION       cOpticalParamHighWarningSev
    SYNTAX          INTEGER  {
                        minor(3),
                        notAlarmed(4)
                    }
    DESCRIPTION
        "Only limited set of enumerated values
        are supported."

    VARIATION       cOpticalParamLowAlarmSev
    SYNTAX          INTEGER  {
                        critical(1),
                        major(2),
                        minor(3)
                    }
    DESCRIPTION
        "Only limited set of enumerated values
        are supported."

    VARIATION       cOpticalParamLowWarningSev
    SYNTAX          INTEGER  {
                        minor(3),
                        notAlarmed(4)
                    }
    DESCRIPTION
        "Only limited set of enumerated values
        are supported."

    VARIATION       cOpticalParamHighAlarmThresh
    SYNTAX          Integer32 (-500..10000 )
    DESCRIPTION
        "
        Only the value range of (0..6550) is supported
        if the index value of cOpticalMonParameterType
        for an instance of cOpticalParamHighAlarmThresh
        is 'xcvrVoltage'."

    VARIATION       cOpticalParamHighWarningThresh
    SYNTAX          Integer32 (-500..10000 )
    DESCRIPTION
        "
        Only the value range of (0..6550) is supported
        if the index value of cOpticalMonParameterType
        for an instance of cOpticalParamHighWarningThresh
        is 'xcvrVoltage'."

    VARIATION       cOpticalParamLowAlarmThresh
    SYNTAX          Integer32 (-500..10000 )
    DESCRIPTION
        "
        Only the value range of (0..6550) is supported
        if the index value of cOpticalMonParameterType
        for an instance of cOpticalParamLowAlarmThresh
        is 'xcvrVoltage'."

    VARIATION       cOpticalParamLowWarningThresh
    SYNTAX          Integer32 (-500..10000 )
    DESCRIPTION
        "
        Only the value range of (0..6550) is supported
        if the index value of cOpticalMonParameterType
        for an instance of cOpticalParamLowWarningThresh
        is 'xcvrVoltage'.
        "

    VARIATION       cOpticalMonPollInterval
    SYNTAX          Unsigned32 (1..15 )
    DESCRIPTION     "Only limited set of values are supported."

    VARIATION       cOpticalNotifyEnable
    SYNTAX          OpticalAlarmSeverityOrZero (0..4 )
    DESCRIPTION     "Only limited set of values are supported."
    ::= { ciscoOpticalMonitorCapability 1 }

END
