CISCO-ITP-MONITOR-CAPABILITY DEFINITIONS ::= BEGIN

IMPORTS
        MODULE-IDENTITY
                FROM SNMPv2-SMI

        AGENT-CAPABILITIES
                FROM SNMPv2-CONF

        ciscoAgentCapability
                FROM CISCO-SMI; 

ciscoItpMonCapability  MODULE-IDENTITY
       LAST-UPDATED    "200411230000Z"
       ORGANIZATION    "Cisco Systems, Inc."
       CONTACT-INFO
               "       Cisco Systems
                       Customer Service

               Postal: 170 West Tasman Drive
                       San Jose, CA  95134
                       USA

                  Tel: +1 800 553-NETS

               E-mail: cs-ss7@cisco.com"
       DESCRIPTION
          "Agent capabilities for the CISCO-ITP-MONITOR-MIB."

       REVISION        "200411230000Z"
       DESCRIPTION
               "Add the new ciscoItpmNotificationsGroupRev1 group
                to support ciscoItpMonitorState notification."

       REVISION        "200404220000Z"
       DESCRIPTION
               "Initial version of this MIB module."
        ::= { ciscoAgentCapability 422 }

ciscoItpMonCapabilityV12R0221SW AGENT-CAPABILITIES

    PRODUCT-RELEASE "Cisco IOS 12.2(21)SW"
    STATUS           current
    DESCRIPTION     "IOS 12.2(21)SW Cisco CISCO-ITP-MONITOR-MIB.my 
                     User Agent MIB capabilities."

    SUPPORTS        CISCO-ITP-MONITOR-MIB
        INCLUDES    { ciscoItpmConnGroup,  
                      ciscoItpmLinkGroup,
                      ciscoItpmNotificationsGroup  
                    }  

    VARIATION   cItpmLinkSentMsus
    ACCESS      not-implemented      
    DESCRIPTION "Not supported."

    VARIATION   cItpmLinkSentMsuDrops
    ACCESS      not-implemented      
    DESCRIPTION "Not supported."

    VARIATION   cItpmLinkSentMsuRate
    ACCESS      not-implemented      
    DESCRIPTION "Not supported."

    VARIATION   cItpmLinkSentBitsRate
    ACCESS      not-implemented      
    DESCRIPTION "Not supported."
    ::= { ciscoItpMonCapability 1 }

ciscoItpMonCapabilityV12R0251SW AGENT-CAPABILITIES

    PRODUCT-RELEASE "Cisco IOS 12.2(25)SW"
    STATUS           current
    DESCRIPTION     "IOS 12.2(25)SW Cisco CISCO-ITP-MONITOR-MIB.my 
                     User Agent MIB capabilities."

    SUPPORTS        CISCO-ITP-MONITOR-MIB
        INCLUDES    { ciscoItpmConnGroupRev1,  
                      ciscoItpmLinkGroup,
                      ciscoItpmNotificationsGroupRev1
                    }  

    VARIATION   cItpmLinkSentMsus
    ACCESS      not-implemented      
    DESCRIPTION "Not supported."

    VARIATION   cItpmLinkSentMsuDrops
    ACCESS      not-implemented      
    DESCRIPTION "Not supported."

    VARIATION   cItpmLinkSentMsuRate
    ACCESS      not-implemented      
    DESCRIPTION "Not supported."

    VARIATION   cItpmLinkSentBitsRate
    ACCESS      not-implemented      
    DESCRIPTION "Not supported."
    ::= { ciscoItpMonCapability 2 }
END
