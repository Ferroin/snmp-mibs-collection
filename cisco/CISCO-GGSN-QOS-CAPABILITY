CISCO-GGSN-QOS-CAPABILITY DEFINITIONS ::= BEGIN

IMPORTS
        MODULE-IDENTITY
                FROM SNMPv2-SMI
        AGENT-CAPABILITIES
                FROM SNMPv2-CONF
        ciscoAgentCapability
                FROM CISCO-SMI;

ciscoGgsnQosCapability MODULE-IDENTITY
        LAST-UPDATED    "200304081600Z"
        ORGANIZATION    "Cisco Systems, Inc."
        CONTACT-INFO
                "       Cisco Systems
                        Customer Service

                        Postal: 170 West Tasman Drive
                                San Jose, CA  95134
                                USA
                                Tel: +1 800 553-NETS

                        E-mail: cs-gprs@cisco.com"
        DESCRIPTION
                "Agent capabilities for CISCO-GGSN-QOS-MIB."
        REVISION        "200304081600Z"
        DESCRIPTION
                "Initial version of this MIB module."
        ::= { ciscoAgentCapability 295 }

ciscoGgsnQosCapabilityV12R2M4 AGENT-CAPABILITIES

        PRODUCT-RELEASE  "Cisco IOS 12.2(4)MX, 12.2(8)YY"
        STATUS           current
        DESCRIPTION      "Cisco GGSN QOS MIB capabilities."

        SUPPORTS         CISCO-GGSN-QOS-MIB
        INCLUDES         { cggsnQosGeneralConfigGroup,
                           cggsnQosCanonicalQosGroup
                         }
        ::= { ciscoGgsnQosCapability 1 }

ciscoGgsnQosCapabilityV12R2M8 AGENT-CAPABILITIES

        PRODUCT-RELEASE  "Cisco IOS 12.2(8)YW"
        STATUS           current
        DESCRIPTION      "Cisco GGSN QOS MIB capabilities."

        SUPPORTS         CISCO-GGSN-QOS-MIB
        INCLUDES         { cggsnQosGeneralConfigGroup,
                           cggsnQosCanonicalQosGroup,
                           cggsnQosUmtsQosGroup
                         }
        ::= { ciscoGgsnQosCapability 2 }

END
