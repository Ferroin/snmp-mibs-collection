CISCO-VOICE-AALX-PROFILE-CAPABILITY DEFINITIONS ::= BEGIN
IMPORTS
        MODULE-IDENTITY,
        Unsigned32
                FROM SNMPv2-SMI
        AGENT-CAPABILITIES
                FROM SNMPv2-CONF
        ciscoAgentCapability
                FROM CISCO-SMI;

ciscoVoiceAalxProfileCapability MODULE-IDENTITY
    LAST-UPDATED "200402070000Z"
    ORGANIZATION "Cisco Systems, Inc."
    CONTACT-INFO
        "        Cisco Systems
                 Customer Service
        Postal: 170 W Tasman Drive
                San Jose, CA 95134
                USA
           Tel: +1 800 553-NETS
        E-mail: cs-voice-gateway@cisco.com"
    DESCRIPTION
            "The agent capabilities for CISCO-VOICE-AALX-PROFILE-MIB." 

    REVISION "200402070000Z"
    DESCRIPTION
            "Initial version of this MIB module."
        ::= { ciscoAgentCapability 352 }

cVoiceAalxProfileCapV5R00 AGENT-CAPABILITIES

        PRODUCT-RELEASE "MGX8850 Release 5.0.0"
        STATUS           current
        DESCRIPTION     "AALX Profile MIB capabilities for Voice 
                         Switch Service Module(VXSM) in 
                         release 5.0.0." 

        SUPPORTS    CISCO-VOICE-AALX-PROFILE-MIB
        INCLUDES    { 
                        cvapCodecConfigGroup
                    }

        VARIATION   cvapCodecNegotiationOption
        ACCESS      not-implemented
        DESCRIPTION "Not supported."

        VARIATION   cvapCodecConfigAdaptType
        SYNTAX      INTEGER {
                        aal5 (2),
                        aal2 (4)
                    }
        DESCRIPTION "Supports aal5(2), aal2(4).
                     other(1) and aal1(3) are not supported."

	VARIATION    cvapCodecConfigType
        SYNTAX       INTEGER {
                         g729Ar8000        (2),
                         g726r32000        (5),
                         g711ulawr64000    (6),
                         g711Alawr64000    (7),
                         g729ABr8000       (13),
                         clearChannel      (18)
                     }
        DESCRIPTION  "Support limited values."

        VARIATION       cvapCodecConfigPreference
        DESCRIPTION     
            "If this object is set to 0, the CODEC will not
             be used in CODEC negotiation or in CODEC choose
             command. If the command from MGC has this CODEC
             as the only CODEC in a= line, then the command
             will be rejected.

             The default value of this object is listed as below:

             cvapCodecConfigType  Preference 
             ---------------------------------
             g729Ar8000      (2)     2
             g726r32000      (5)     3
             g711ualawr64000 (6)     5
             g711Alawr640000 (7)     6
             g729ABr8000     (13)    1
             clearChannel    (18)    7
             ---------------------------------
            "

        VARIATION       cvapCodecConfigVoicePacketPeriod
        DEFVAL          { pktPeriod10000us }
        DESCRIPTION     
            "The valid range of values for this object depends
             on CODEC types specified by cvapCodecConfigType.

             When the value of cvapCodecConfigType is the
             following values:
                 g726r32000     (5)
                 g711ulawr64000 (6)
                 g711Alawr64000 (7)
                 clearChannel  (18)
             The valid values for this object are:
                 pktPeriod10000us(4) 
                 pktPeriod15000us(5) 
                 pktPeriod20000us(6) 
                 pktPeriod25000us(7) 
                 pktPeriod30000us(8) 

             When the value of cvapCodecConfigType is the
             following values:
                 g729Ar8000     (2)
                 g729ABr8000   (13)
             The valid values for this object are:
                 pktPeriod10000us(4) 
                 pktPeriod20000us(6) 
                 pktPeriod30000us(8) 
                 pktPeriod40000us(10)
                 pktPeriod50000us(12)
                 pktPeriod60000us(14)
                 pktPeriod70000us(16)
                 pktPeriod80000us(18) 
            "

        VARIATION       cvapCodecConfigVbdPacketPeriod
        DEFVAL          { pktPeriod10000us }
        DESCRIPTION     
            "The value of this object is limited to
                 pktPeriod10000us(4) 
                 pktPeriod15000us(5) 
                 pktPeriod20000us(6) 
                 pktPeriod25000us(7) 
                 pktPeriod30000us(8) 
            "

        VARIATION       cvapCodecConfigJitterDelayMode
        DESCRIPTION 
            "The value of this object depends on the CODEC type
             (cvapCodecConfigType).
             When the value of cvapCodecConfigType is the
             following values:
                 g711ulawr64000   (6)       
                 g711Alawr64000   (7)      
                 g726r32000       (5)     
                 g729Ar8000       (2)
                 g729ABr8000      (13)
             The value of this object is 'adaptive'.

             When the value of cvapCodecConfigType is clearChannel (18),
             the value of this object is 'fixed'.
            "

        VARIATION       cvapCodecConfigJitterMaxDelay
        SYNTAX          Unsigned32 (20..135)
        DESCRIPTION 
            "Support limited values.

             The default value for this object depends on
             the combination of CODEC type (cvapCodecConfigType)
             and the adaptation type (cvapCodecConfigAdaptType).
             When the value of cvapCodecConfigType is the
             following values and cvapCodecAdaptType is 'aal5(2)':
                 g711ulawr64000   (6)
                 g711Alawr64000   (7) 
                 g726r32000       (5)     
                 g729Ar8000       (2)
                 g729ABr8000      (13)
             The default value of this object is 100.

             When the value of cvapCodecConfigType is the
             following values and cvapCodecAdaptType is 
             'aal2(4)':
                 g711ulawr64000   (6)
                 g711Alawr64000   (7) 
                 g726r32000       (5)     
                 g729Ar8000       (2)
                 g729ABr8000      (13)
             The default value of this object is 60.

             When the value of cvapCodecConfigType is clearChannel(18)
             the default value of this object is 135.
            "

        VARIATION    cvapCodecConfigJitterNomDelay
        SYNTAX       Unsigned32 (5..135)
        DESCRIPTION
            "Support limited values.

             The default value for this object depends on
             the combination of CODEC type (cvapCodecConfigType) and
             the adaptation type (cvapCodecConfigAdaptType).
             When the value of cvapCodecConfigType is the
             following values and cvapCodecAdaptType is 'aal5(2)':
                 g711ulawr64000   (6)
                 g711Alawr64000   (7) 
                 g726r32000       (5)     
                 g729Ar8000       (2)
                 g729ABr8000      (13)
             The default value of this object is 30.

             When the value of cvapCodecConfigType is the
             following values and cvapCodecAdaptType is 
             'aal2(4)':
                 g711ulawr64000   (6)
                 g711Alawr64000   (7) 
                 g726r32000       (5)     
                 g729Ar8000       (2)
                 g729ABr8000      (13)
             The default value of this object is 20.

             When the value of cvapCodecConfigType is clearChannel(18)
             the default value of this object is 70.
            "

	VARIATION    cvapCodecConfigJitterMinDelay
        SYNTAX       Unsigned32 (0..135)
        DESCRIPTION
            "Support limited values.

             The default value for this object depends on
             the combination of CODEC type (cvapCodecConfigType).

             When the value of cvapCodecConfigType is the
             following values:
                 g711ulawr64000   (6)
                 g711Alawr64000   (7) 
                 g726r32000       (5)     
                 g729Ar8000       (2)
                 g729ABr8000      (13)
             The default value of this object is 5.

             When the value of cvapCodecConfigType is 
             clearChannel (18), the default value of this object
             is 0.
            "

	VARIATION	cvapCodecConfigDtmfRelay
        DESCRIPTION
            "The default value of this object depends on the
             CODEC type (cvapCodecConfigType).
             When the value of cvapCodecConfigType is the
             following values:
                 g726r32000       (5)     
                 g711ulawr64000   (6)
                 g711Alawr64000   (7)
                 clearChannel     (18)    
             The default value of this object is 'false'.

                 g729Ar8000       (2)
                 g729ABr8000      (13)
             The default value of this object is 'true'.
            "

	VARIATION	cvapCodecConfigPayloadType
        DESCRIPTION     
            "This object is applicable only when the 
             cvapCodecConfigAdaptType is set to aal5(2) in VoIP 
             application.

             System allows user to configure this object with the 
             value (0..127) to associate with any supported CODEC.

             If more than one CODECs have the same payload type,
             system chooses the CODEC based on the preference specified
             in cvapCodecConfigPreference.

             When the user configures the payload type of the CODEC,
             care must be taken to ensure the consistency throughout
             the whole network.

             The default value of the payload type for each CODEC
             is listed below:

             cvapCodecConfigType  Payload Type
             ---------------------------------
             g729Ar8000      (2)     97
             g726r32000      (5)     2
             g711ualawr64000 (6)     0
             g711Alawr640000 (7)     8
             g729ABr8000     (13)    99
             clearChannel    (18)    104
             ---------------------------------
             "
    ::= { ciscoVoiceAalxProfileCapability 1 }
END
