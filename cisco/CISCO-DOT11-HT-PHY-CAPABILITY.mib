CISCO-DOT11-HT-PHY-CAPABILITY DEFINITIONS ::= BEGIN

IMPORTS
    MODULE-IDENTITY
        FROM SNMPv2-SMI
    AGENT-CAPABILITIES
        FROM SNMPv2-CONF
    TruthValue
        FROM SNMPv2-TC
    ciscoAgentCapability
        FROM CISCO-SMI;

cDot11HtPhyCapability MODULE-IDENTITY
    LAST-UPDATED    "200708220000Z"
    ORGANIZATION    "Cisco Systems, Inc."
    CONTACT-INFO
            "Cisco Systems
            Customer Service

            Postal: 170 W Tasman Drive
            San Jose, CA  95134
            USA

            Tel: +1 800 553-NETS

            E-mail: cs-wnbu-snmp@cisco.com"
    DESCRIPTION
        "Agent capabilities for CISCO-DOT11-HT-PHY-MIB"
    REVISION        "200708220000Z"
    DESCRIPTION
        "Initial version of this MIB module."
    ::= { ciscoAgentCapability 551 }

cDot11HtPhyCapabilityV12R0410BJA AGENT-CAPABILITIES
    PRODUCT-RELEASE "Cisco IOS 12.4(10b)JA for the AP1250 802.11 
                         Access Points"
    STATUS          current
    DESCRIPTION
        "CISCO-DOT11-HT-PHY-MIB capabilities"

    SUPPORTS        CISCO-DOT11-HT-PHY-MIB
    INCLUDES        {
                        ciscoDot11HtPhyAntennaGroup,
                        ciscoDot11HtPhyConfigGroup,
                        ciscoDot11HtPhyMcsGroup,
                        ciscoDot11HtPhyTxBfGroup
                    }
    VARIATION       cD11HtPhyOperatingMode
    SYNTAX          INTEGER  {
                        legacy(1),
                        mixed(2)
                    }
    DESCRIPTION
        "Only a limited set of enumerated values is
        supported."

    VARIATION       cD11HtPhyOperModeFrequency
    ACCESS          not-implemented
    DESCRIPTION
        "This object is not supported."

    VARIATION       cD11HtPhyFortyMHzOperationImplemented
    SYNTAX          TruthValue {
                        true(1)
                    }
    DESCRIPTION
        "Only a limited set of enumerated values is
        supported."

    VARIATION       cD11HtPhyExtChannelCCAImplemented
    SYNTAX          TruthValue {
                        false(2)
                    }
    DESCRIPTION
        "Only a limited set of enumerated values is
        supported."

    VARIATION       cD11HtPhyNumberOfSpatialStreamsImplemented
    SYNTAX          INTEGER (2)
    DESCRIPTION
        "The implementation supports 2 spatial streams."

    VARIATION       cD11HtPhyNumberOfSpatialStreamsEnabled
    SYNTAX          INTEGER (1..2)
    DESCRIPTION
        "Either one or two spatial streams are enabled
        at any point in time."

    VARIATION       cD11HtPhyGreenFieldImplemented
    SYNTAX          TruthValue {
                        false(2)
                    }
    DESCRIPTION
        "Only a limited set of enumerated values is
        supported."

    VARIATION       cD11HtPhyGreenFieldEnabled
    SYNTAX          TruthValue {
                        false(2)
                    }
    ACCESS          read-only
    DESCRIPTION
        "Only a limited set of enumerated values is
        supported. The implementation also doesn't
        support write operations on this object."

    VARIATION       cD11HtPhyShortGIInTwentyImplemented
    SYNTAX          TruthValue {
                        true(1)
                    }
    DESCRIPTION
        "Only a limited set of enumerated values is
        supported."

    VARIATION       cD11HtPhyShortGIInFortyImplemented
    SYNTAX          TruthValue {
                        true(1)
                    }
    DESCRIPTION
        "Only a limited set of enumerated values is
        supported."

    VARIATION       cD11HtPhyAdvancedCodingImplemented
    SYNTAX          TruthValue {
                        false(2)
                    }
    DESCRIPTION
        "Only a limited set of enumerated values is
        supported."

    VARIATION       cD11HtPhyAdvancedCodingEnabled
    SYNTAX          TruthValue {
                        false(2)
                    }
    ACCESS          read-only
    DESCRIPTION
        "Only a limited set of enumerated values is
        supported. The implementation also doesn't
        support write operations on this object."

    VARIATION       cD11HtPhyTxSTBCImplemented
    SYNTAX          TruthValue {
                        false(2)
                    }
    DESCRIPTION
        "Only a limited set of enumerated values is
        supported."

    VARIATION       cD11HtPhyTxSTBCEnabled
    SYNTAX          TruthValue {
                        false(2)
                    }
    ACCESS          read-only
    DESCRIPTION
        "Only a limited set of enumerated values is
        supported. The implementation also doesn't
        support write operations on this object."

    VARIATION       cD11HtPhyRxSTBCImplemented
    SYNTAX          TruthValue {
                        false(2)
                    }
    DESCRIPTION
        "Only a limited set of enumerated values is
        supported."

    VARIATION       cD11HtPhyRxSTBCEnabled
    SYNTAX          TruthValue {
                        false(2)
                    }
    ACCESS          read-only
    DESCRIPTION
        "Only a limited set of enumerated values is
        supported. The implementation also doesn't
        support write operations on this object."

    VARIATION       cD11HtPhyBeamFormingImplemented
    SYNTAX          TruthValue {
                        false(2)
                    }
    DESCRIPTION
        "Only a limited set of enumerated values is
        supported."

    VARIATION       cD11HtPhyBeamFormingEnabled
    SYNTAX          TruthValue {
                        false(2)
                    }
    ACCESS          read-only
    DESCRIPTION
        "Only a limited set of enumerated values is
        supported. The implementation also doesn't
        support write operations on this object."

    VARIATION       cD11HtPhyAntennaSelectionImplemented
    SYNTAX          TruthValue {
                        true(1)
                    }
    DESCRIPTION
        "Only a limited set of enumerated values is
        supported."

    VARIATION       cD11HtPhyRcvAntennaSelImplemented
    SYNTAX          TruthValue {
                        true(1)
                    }
    DESCRIPTION
        "Only a limited set of enumerated values is
        supported."

    VARIATION       cD11HtPhySupportedMCSTxValue
    SYNTAX          OCTET STRING (SIZE (2))
    DESCRIPTION
        "The implementation returns 0xFFFF to indicate
        the support for 15 MCS rates."

    VARIATION       cD11HtPhySupportedMCSRxValue
    SYNTAX          OCTET STRING (SIZE (2))
    DESCRIPTION
        "The implementation returns 0xFFFF to indicate
        the support for 15 MCS rates, each bit indicating
        the support for the respective nth MCS rate."

    VARIATION       cD11HtPhyRxStaggerSoundImplemented
    SYNTAX          TruthValue {
                        false(2)
                    }
    DESCRIPTION
        "Only a limited set of enumerated values is
        supported."

    VARIATION       cD11HtPhyTxStaggerSoundImplemented
    SYNTAX          TruthValue {
                        false(2)
                    }
    DESCRIPTION
        "Only a limited set of enumerated values is
        supported."

    VARIATION       cD11HtPhyRxZLFImplemented
    SYNTAX          TruthValue {
                        false(2)
                    }
    DESCRIPTION
        "Only a limited set of enumerated values is
        supported."

    VARIATION       cD11HtPhyTxZLFImplemented
    SYNTAX          TruthValue {
                        false(2)
                    }
    DESCRIPTION
        "Only a limited set of enumerated values is
        supported."

    VARIATION       cD11HtPhyImplicitTxBFImplemented
    SYNTAX          TruthValue {
                        false(2)
                    }
    DESCRIPTION
        "Only a limited set of enumerated values is
        supported."

    VARIATION       cD11HtPhyCalibrationImplemented
    SYNTAX          INTEGER  {
                        inCapable(1)
                    }
    DESCRIPTION
        "Only a limited set of enumerated values is
        supported."

    VARIATION       cD11HtPhyExplCSITxBFImplemented
    SYNTAX          TruthValue {
                        false(2)
                    }
    DESCRIPTION
        "Only a limited set of enumerated values is
        supported."

    VARIATION       cD11HtPhyExplUncompSteerMatrixImplemented
    SYNTAX          TruthValue {
                        false(2)
                    }
    DESCRIPTION
        "Only a limited set of enumerated values is
        supported."

    VARIATION       cD11HtPhyExplBFCSIFdbkImplemented
    ACCESS          not-implemented
    DESCRIPTION
        "This object is not supported."

    VARIATION       cD11HtPhyExplUncompSteerMatrixFdbkImplemented
    ACCESS          not-implemented
    DESCRIPTION
        "This object is not supported."

    VARIATION       cD11HtPhyExplCompSteerMatrixFdbkImplemented
    ACCESS          not-implemented
    DESCRIPTION
        "This object is not supported."

    VARIATION       cD11HtPhyNumberBeamFormingCSISupportAntenna
    ACCESS          not-implemented
    DESCRIPTION
        "This object is not supported."

    VARIATION       cD11HtPhyNumberUncompSteerMatrixSupportAntenna
    ACCESS          not-implemented
    DESCRIPTION
        "This object is not supported."

    VARIATION       cD11HtPhyNumberCompSteerMatrixSupportAntenna
    ACCESS          not-implemented
    DESCRIPTION
        "This object is not supported."

    VARIATION       cD11HtPhyEnhPowerLevel20MHz
    ACCESS          not-implemented
    DESCRIPTION
        "This object is not supported."

    VARIATION       cD11HtPhyEnhPowerLevel40MHz
    ACCESS          not-implemented
    DESCRIPTION
        "This object is not supported."
    ::= { cDot11HtPhyCapability 1 }

END
