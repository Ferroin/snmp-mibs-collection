CISCO-MODEM-MGMT-CAPABILITY DEFINITIONS ::= BEGIN

IMPORTS
    MODULE-IDENTITY
        FROM SNMPv2-SMI
    AGENT-CAPABILITIES
        FROM SNMPv2-CONF
    ciscoAgentCapability
        FROM CISCO-SMI;

ciscoModemMgmtCapability MODULE-IDENTITY
    LAST-UPDATED    "200607310000Z"
    ORGANIZATION    "Cisco Systems, Inc."
    CONTACT-INFO
            "Cisco Systems
            Customer Service

            Postal: 170 West Tasman Drive
            San Jose, CA  95134
            USA

            Tel: +1 800 553-NETS

            E-mail: cs-snmp@cisco.com"
    DESCRIPTION     "Agent capabilities for CISCO-MODEM-MGMT-MIB."
    REVISION        "200607310000Z"
    DESCRIPTION
            "Initial version of this MIB module"
          ::= { ciscoAgentCapability 9999 }

ciscoModemMgmtCapV12R4TISR AGENT-CAPABILITIES
    PRODUCT-RELEASE "Cisco IOS 12.4 for ATG Platform Devices"
    STATUS          current
    DESCRIPTION     "CISCO-MODEM-MGMT-MIB capabilities."

    SUPPORTS        CISCO-MODEM-MGMT-MIB
    INCLUDES        {
                        cmSystemInfoGroup,
                        cmGroupInfoGroup,
                        cmLineInfoGroup,
                        cmManagedLineInfoGroup,
                        cmLineSpeedInfoGroup,
                        cmSystemInfoGroupRev1,
                        cmLineSpeedInfoGroupRev1,
                        cmManagedLineInfoGroupRev1,
                        cmNotificationConfigGroup,
                        cmLineSpeedInfoGroupRev2,
                        cmManagedLineInfoGroupRev2
                    }

    VARIATION       cmStateNotifyEnable
    ACCESS          read-only
    DESCRIPTION
            "Write operation is not supported in ATG Platform Devices "
    ::= { ciscoModemMgmtCapability 1 }

END
