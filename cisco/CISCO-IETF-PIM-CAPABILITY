CISCO-IETF-PIM-CAPABILITY DEFINITIONS ::= BEGIN

IMPORTS
        MODULE-IDENTITY
                FROM SNMPv2-SMI
        AGENT-CAPABILITIES
                FROM SNMPv2-CONF
        ciscoAgentCapability
                FROM CISCO-SMI;   

ciscoIetfPimCapability MODULE-IDENTITY
    LAST-UPDATED    "200507270000Z"
    ORGANIZATION    "Cisco Systems, Inc."
    CONTACT-INFO  
        "       Cisco Systems
                Customer Service

               Postal: 170 West Tasman Drive
               San Jose, CA  95134
               USA

               Tel: +1 800 553-NETS

               E-mail: cs-ipmulticast@cisco.com"
    DESCRIPTION
       "The capabilities description of  CISCO-IETF-PIM-MIB"

    REVISION        "200507270000Z"
    DESCRIPTION
       "Initial version of this MIB module."
    ::= {  ciscoAgentCapability 441 }

cIetfPimCapV320CRS1 AGENT-CAPABILITIES
    PRODUCT-RELEASE "Cisco IOS XR 3.2.0 for CRS-1"
    STATUS          current
    DESCRIPTION     "CISCO-IETF-PIM-MIB capabilities." 

    SUPPORTS        CISCO-IETF-PIM-MIB 
     INCLUDES       {             
                     cPimNotificationGroup,
                     cPimV2MIBGroup,
                     cPimDenseV2MIBGroup,
                     cPimAssertGroup  
                    } 

    VARIATION          cPimJoinPruneInterval
     ACCESS            not-implemented
     DESCRIPTION       "Not Supported."

    VARIATION          cPimIfCBSRPreference
     ACCESS            not-implemented
     DESCRIPTION       "Not Supported."

    VARIATION          cPimRPMapTable 
     ACCESS            not-implemented
     DESCRIPTION       "Not Supported."

    VARIATION          cPimComponentTable 
     ACCESS            not-implemented
     DESCRIPTION       "Not Supported."
    ::= { ciscoIetfPimCapability 1 }
END
