CISCO-ITP-MSU-RATES-CAPABILITY DEFINITIONS ::= BEGIN

IMPORTS
    MODULE-IDENTITY
        FROM SNMPv2-SMI
    AGENT-CAPABILITIES
        FROM SNMPv2-CONF
    ciscoAgentCapability
        FROM CISCO-SMI;

ciscoItpMsuRatesCapability MODULE-IDENTITY
    LAST-UPDATED    "200703200000Z"
    ORGANIZATION    "Cisco Systems, Inc."
    CONTACT-INFO
            "Cisco Systems
            Customer Service

            Postal: 170 W Tasman Drive

            San Jose, CA  95134

            USA

            Tel: +1 800 553-NETS

            E-mail: cs-itp@cisco.com"
    DESCRIPTION
        "Agent capabilities for the CISCO-ITP-MSU-RATES-MIB."
    REVISION        "200703200000Z"
    DESCRIPTION
        "Initial version of this MIB module."
    ::= { ciscoAgentCapability 537 }

ciscoItpMsuCapabilityV12R0225SW7 AGENT-CAPABILITIES
    PRODUCT-RELEASE "Cisco IOS 12.2(25)SW7"
    STATUS          current
    DESCRIPTION
        "Cisco IOS 12.2(25)SW7 CISCO-ITP-MSU-RATES-MIB.my User
        Agent MIB capabilities."

    SUPPORTS        CISCO-ITP-MSU-RATES-MIB
    INCLUDES        {
                        ciscoItpMsuRatesScalarsGroup,
                        ciscoItpMsuRatesObjects,
                        ciscoItpMsuDistObjects,
                        ciscoItpMsuRatesNotifyGroup
                    }
    VARIATION       cimrMsuProcPhysicalIndex
    ACCESS          not-implemented
    DESCRIPTION
        "Not implemented."
    ::= { ciscoItpMsuRatesCapability 1 }

ciscoItpMsuCapabilityV12R0218IXB AGENT-CAPABILITIES
    PRODUCT-RELEASE "Cisco IOS 12.2(18)IXB"
    STATUS          current
    DESCRIPTION
        "Cisco IOS 12.2(18)IXB CISCO-ITP-MSU-RATES-MIB.my User
        Agent MIB capabilities."

    SUPPORTS        CISCO-ITP-MSU-RATES-MIB
    INCLUDES        {
                        ciscoItpMsuRatesScalarsGroup,
                        ciscoItpMsuRatesObjects,
                        ciscoItpMsuDistObjects,
                        ciscoItpMsuRatesNotifyGroup
                    }
    VARIATION       cimrMsuProcPhysicalIndex
    ACCESS          not-implemented
    DESCRIPTION
        "Not Implemented"
    ::= { ciscoItpMsuRatesCapability 2 }

ciscoItpMsuCapabilityV12R0411SW AGENT-CAPABILITIES
    PRODUCT-RELEASE "Cisco IOS 12.4(11)SW"
    STATUS          current
    DESCRIPTION
        "Cisco IOS 12.4(11)SW CISCO-ITP-MSU-RATES-MIB.my User
        Agent MIB capabilities."

    SUPPORTS        CISCO-ITP-MSU-RATES-MIB
    INCLUDES        {
                        ciscoItpMsuRatesScalarsGroup,
                        ciscoItpMsuRatesObjects,
                        ciscoItpMsuDistObjects,
                        ciscoItpMsuRatesNotifyGroup
                    }
    VARIATION       cimrMsuProcPhysicalIndex
    ACCESS          not-implemented
    DESCRIPTION
        "Not implemented."
    ::= { ciscoItpMsuRatesCapability 3 }

END
