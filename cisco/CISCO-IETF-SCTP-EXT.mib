CISCO-IETF-SCTP-EXT-MIB DEFINITIONS ::= BEGIN

    IMPORTS
      InetAddressType, 
      InetAddress
           FROM INET-ADDRESS-MIB         -- RFC2851

      Gauge32,
      MODULE-IDENTITY, 
      NOTIFICATION-TYPE,
      OBJECT-TYPE, 
      Counter32,
      Unsigned32
           FROM SNMPv2-SMI               -- RFC2578

      TimeStamp,
      TruthValue 
           FROM SNMPv2-TC                -- RFC2579

      MODULE-COMPLIANCE, 
      NOTIFICATION-GROUP,
      OBJECT-GROUP
           FROM SNMPv2-CONF              -- RFC2580

      ciscoExperiment
                FROM CISCO-SMI

      cSctpAssocEntry,
      cSctpAssocRemAddressEntry,
      cSctpAssocRemAddressStatus
                FROM CISCO-IETF-SCTP-MIB;                

cSctpExtMIB MODULE-IDENTITY
      LAST-UPDATED "200111090000Z"       -- November 09, 2001
      ORGANIZATION " "
      CONTACT-INFO
           "       Cisco Systems, Inc
                   Customer Service

           Postal: 170 W. Tasman Drive
                   San Jose, CA  95134
                   USA

              Tel: +1 800 553-NETS

           E-mail: cs-sctp@cisco.com"
      DESCRIPTION
           "An extension to the CISCO-IETF-SCTP-MIB.my used to 
            provide additional information to manage the Stream 
            Control Transmission  Protocol (RFC 2960)."

      REVISION  "200111090000Z"          -- November 09, 2001
      DESCRIPTION
           "Added support for effective destination address,
            count of fast retransmission per association and 
            notification when destination address changes states.

            cSctpAssocExtEffectiveAddrType
            cSctpAssocExtEffectiveAddress 
            cSctpAssocExtRtxChunksFast    
            cSctpAddressStateNotifEnabled
            cSctpExtDestAddressStateChange
            cSctpAssocExtBundleFlag
            cSctpAssocExtBundleTimeout"

      REVISION  "200108270000Z"          -- August 27, 2001
      DESCRIPTION
           "MIB module developed for the SIGTRAN IETF group. Based on
           SCTP, RFC2960"
      ::= { ciscoExperiment 76 } --  

-- Top-level structure of the MIB
cSctpExtNotifications      OBJECT IDENTIFIER ::= { cSctpExtMIB 0 }
cSctpExtObjects            OBJECT IDENTIFIER ::= { cSctpExtMIB 1 }

cSctpScalarsExt            OBJECT IDENTIFIER ::= { cSctpExtObjects 1 }
cSctpExtTables             OBJECT IDENTIFIER ::= { cSctpExtObjects 2 }

-- ********************************************************************
-- SCTP Scalars Extensions
-- ********************************************************************

cSctpStatRtxChucks           OBJECT-TYPE
  SYNTAX                     Counter32
  UNITS                      "chunks" 
  MAX-ACCESS                 read-only
  STATUS                     current
  DESCRIPTION
       "Number of SCTP chunks retransmitted due to the T3 timers
        expiring before the packet is acknowledged. "
  REFERENCE
       "[sctp] section 6.3.3. Handle T3-rtx Expiration"
  ::= { cSctpScalarsExt 1 }

cSctpStatRtxChucksFast       OBJECT-TYPE
  SYNTAX                     Counter32
  UNITS                      "chunks" 
  MAX-ACCESS                 read-only
  STATUS                     current
  DESCRIPTION
       "Number of SCTP chunks retransmitted using the 
        fast-recovery retransmission mechanism specified 
        in [sctp]."
  REFERENCE
       "[sctp] section 7.2.4.- Fast Retransmit on Gap Reports."
  ::= { cSctpScalarsExt 2 }

cSctpStatDestAddressFailures OBJECT-TYPE
  SYNTAX                     Counter32
  MAX-ACCESS                 read-only
  STATUS                     current
  DESCRIPTION
       "The accumulated number of times a destination IP address
        was marked unavailable since the start of this association.
        The IP destination address will be marked unavailable when
        the specified number of retransmissions have failed."
  ::= { cSctpScalarsExt 3 }

cSctpCtrlPurgeTimeout        OBJECT-TYPE
  SYNTAX                     Unsigned32(3600..3000000) 
  UNITS                      "seconds"
  MAX-ACCESS                 read-write
  STATUS                     current
  DESCRIPTION
       "The amount of time the SCTP protocol software will wait
        before purging an associations TCB. An association TCB 
        will exist until a management station sets the cSctpAssocState
        to deleteTCB or is purge by the protocol implementation. The
        protocol implementation will purge an association TCB
        using a combination of cSctpCtrlPurgeTimeout and 
        cSctpCtrlMaxHeld. The cSctpCtrlPurgeTimeout ranges from
        the minimum of one hour to roughly one month. The default
        value is roughly one day."
  DEFVAL { 86400 } 
  ::= { cSctpScalarsExt 4 }

cSctpCtrlMaxHeld             OBJECT-TYPE
  SYNTAX                     Unsigned32(30..10000)
  UNITS                      "association TCBs"
  MAX-ACCESS                 read-write
  STATUS                     current
  DESCRIPTION
       "The maximum number of association TCBS that will be held
        after they have been marked closed and are no longer
        providing service. This limit is used to prevent 
        excessive waste of resources." 
  DEFVAL { 100 } 
  ::= { cSctpScalarsExt 5 }

cSctpAddressStateNotifEnabled OBJECT-TYPE
  SYNTAX                      TruthValue
  MAX-ACCESS                  read-write
  STATUS                      current
  DESCRIPTION          
          "This object controls the generation of 
            cSctpExtDestAddressStateChange as follows:

           'true'  Indicates that an address state change
                   notification is to be generated whenever a IP
                   address used by one or more associations
                   becomes available or unavailable. That is,
                   the notification generation is enabled.

           'false' Indicates that an address state change
                   notification generation is disabled."
  DEFVAL { false }
  ::= { cSctpScalarsExt 6 }

-- ********************************************************************
-- SCTP Association Extensions TABLE  
-- ********************************************************************
cSctpAssocExtTable           OBJECT-TYPE
  SYNTAX                     SEQUENCE OF CSctpAssocExtEntry
  MAX-ACCESS                 not-accessible
  STATUS                     current
  DESCRIPTION
       "A table containing SCTP association-specific information."
  ::= { cSctpExtTables 1 }

cSctpAssocExtEntry           OBJECT-TYPE
  SYNTAX                     CSctpAssocExtEntry
  MAX-ACCESS                 not-accessible
  STATUS                     current
  DESCRIPTION
       "General common variables and statistics for the whole
        association."
  AUGMENTS {cSctpAssocEntry}
  ::= { cSctpAssocExtTable 1 }

CSctpAssocExtEntry ::= SEQUENCE {
    cSctpAssocExtRtoMin                Unsigned32,
    cSctpAssocExtRtoMax                Unsigned32,
    cSctpAssocExtRtoInitial            Unsigned32,
    cSctpAssocExtValCookieLife         Unsigned32,
    cSctpAssocExtMaxInitRetr           Unsigned32,
    cSctpAssocExtMTU                   Unsigned32,
    cSctpAssocExtLocRecWnd             Unsigned32,
    cSctpAssocExtLocRecWndLowMark      Gauge32,
    cSctpAssocExtLocRecWndZeroCnt      Counter32,
    cSctpAssocExtRemRecWnd             Unsigned32,
    cSctpAssocExtRemRecWndLowMark      Gauge32,
    cSctpAssocExtRemRecWndZeroCnt      Counter32,
    cSctpAssocExtUlpQueued             Gauge32,
    cSctpAssocExtUlpQueuedHW           Gauge32,
    cSctpAssocExtUlpQueuedRT           TimeStamp, 
    cSctpAssocExtChunksRecControl      Counter32,
    cSctpAssocExtChunksRecOrdered      Counter32,
    cSctpAssocExtChunksRecUnOrdered    Counter32,
    cSctpAssocExtChunksSentControl     Counter32,                    
    cSctpAssocExtChunksSentOrdered     Counter32,
    cSctpAssocExtChunksSentUnOrdered   Counter32,          
    cSctpAssocExtDatagramsRec          Counter32,
    cSctpAssocExtDatagramsSent         Counter32,
    cSctpAssocExtEffectiveAddrType     InetAddressType,
    cSctpAssocExtEffectiveAddress      InetAddress,
    cSctpAssocExtRtxChunksFast         Counter32,
    cSctpAssocExtBundleFlag            TruthValue,
    cSctpAssocExtBundleTimeout         Unsigned32
  }

cSctpAssocExtRtoMin          OBJECT-TYPE
  SYNTAX                     Unsigned32
  UNITS                      "milliseconds"
  MAX-ACCESS                 read-only
  STATUS                     current
  DESCRIPTION
      "The minimum value permitted by a SCTP implementation for the
       retransmission timeout, measured in milliseconds.  More
       refined semantics for objects of this type depend upon the
       algorithm used to determine the retransmission timeout.
       Minimum recommended value is 1000 milliseconds. Some telephony
       applications could require less than 1 second, see [SIGAS] for
       further information."
  REFERENCE
      "[SIGAS] Telephony Signaling Transport over SCTP Applicability
       Statement"
  ::= { cSctpAssocExtEntry 1 }

cSctpAssocExtRtoMax          OBJECT-TYPE
  SYNTAX                     Unsigned32
  UNITS                      "milliseconds"
  MAX-ACCESS                 read-only
  STATUS                     current
  DESCRIPTION
       "The maximum value permitted by a SCTP implementation for the
       retransmission timeout, measured in milliseconds.  More
       refined semantics for objects of this type depend upon the
       algorithm used to determine the retransmission timeout.
       Recommended value is 60000 milliseconds."
  ::= { cSctpAssocExtEntry 2 }

cSctpAssocExtRtoInitial      OBJECT-TYPE
  SYNTAX                     Unsigned32
  UNITS                      "milliseconds"
  MAX-ACCESS                 read-only
  STATUS                     current
  DESCRIPTION
       "Initial value for the Retransmission timer. Recommended value
       is 3000 milliseconds."
  ::= { cSctpAssocExtEntry 3 }

cSctpAssocExtValCookieLife   OBJECT-TYPE
  SYNTAX                     Unsigned32
  UNITS                      "milliseconds"
  MAX-ACCESS                 read-only
  STATUS                     current
  DESCRIPTION
       "Valid cookie life in the 4-way start-up handshake procedure.
       Recommended value: 60000 milliseconds."
  ::= { cSctpAssocExtEntry 4 }

cSctpAssocExtMaxInitRetr     OBJECT-TYPE
  SYNTAX                     Unsigned32
  MAX-ACCESS                 read-only
  STATUS                     current
  DESCRIPTION
       "The maximum number of retransmissions at the start-up phase
       (INIT and COOKIE ECHO chunks). Recommended value: 8 attempts."
  ::= { cSctpAssocExtEntry 5 }

cSctpAssocExtMTU             OBJECT-TYPE
  SYNTAX                     Unsigned32(37..65535)
  UNITS                      "bytes"
  MAX-ACCESS                 read-only
  STATUS                     current
  DESCRIPTION
       "The Maximum Transmission Size to be used by this 
        association. The size will the smallest MTU size supported
        by any of the IP Addresses used by the association."
  ::= { cSctpAssocExtEntry 6 }

cSctpAssocExtLocRecWnd       OBJECT-TYPE
  SYNTAX                     Unsigned32(1..65535)
  UNITS                      "bytes"
  MAX-ACCESS                 read-only
  STATUS                     current
  DESCRIPTION
       "The current local receive window size for this 
        association."
  ::= { cSctpAssocExtEntry 7 }

cSctpAssocExtLocRecWndLowMark  OBJECT-TYPE
  SYNTAX                     Gauge32 (0..65535)
  UNITS                      "bytes"
  MAX-ACCESS                 read-only
  STATUS                     current
  DESCRIPTION
       "Low water mark for Local Receive Window Size."
  ::= { cSctpAssocExtEntry 8 }

cSctpAssocExtLocRecWndZeroCnt  OBJECT-TYPE
  SYNTAX                     Counter32
  MAX-ACCESS                 read-only
  STATUS                     current
  DESCRIPTION                
       "Number of times the Local Receive window reached 
        zero bytes."
  ::= { cSctpAssocExtEntry 9 }

cSctpAssocExtRemRecWnd       OBJECT-TYPE
  SYNTAX                     Unsigned32(0..65535)
  UNITS                      "bytes"
  MAX-ACCESS                 read-only
  STATUS                     current
  DESCRIPTION
       "The Remote Receive Window Size for this association."
  ::= { cSctpAssocExtEntry 10 }

cSctpAssocExtRemRecWndLowMark  OBJECT-TYPE
  SYNTAX                     Gauge32 (0..65535)
  UNITS                      "bytes"
  MAX-ACCESS                 read-only
  STATUS                     current
  DESCRIPTION
       "Low water mark for Remote Receive Window Size."
  ::= { cSctpAssocExtEntry 11 }

cSctpAssocExtRemRecWndZeroCnt   OBJECT-TYPE
  SYNTAX                     Counter32
  MAX-ACCESS                 read-only
  STATUS                     current
  DESCRIPTION                
       "Number of times the Remote Receive window reached 
        zero bytes."
  ::= { cSctpAssocExtEntry 12 }

cSctpAssocExtUlpQueued       OBJECT-TYPE
  SYNTAX                     Gauge32(0..65535) 
  UNITS                      "datagrams"
  MAX-ACCESS                 read-only
  STATUS                     current
  DESCRIPTION
       "Current number of IP datagrams waiting to be sent."
  ::= { cSctpAssocExtEntry 13 }

cSctpAssocExtUlpQueuedHW     OBJECT-TYPE
  SYNTAX                     Gauge32 (0..65535) 
  UNITS                      "datagrams"
  MAX-ACCESS                 read-write
  STATUS                     current
  DESCRIPTION
       "High water mark for data grams waiting to be sent.
        Resetting this object is achieved by setting this
        object to 0. Attempting to set this object to any
        other value will result in a wrongValue error."
  ::= { cSctpAssocExtEntry 14 }

cSctpAssocExtUlpQueuedRT     OBJECT-TYPE
    SYNTAX                   TimeStamp
    MAX-ACCESS               read-only
    STATUS                   current
    DESCRIPTION
       "The time when cSctpAssocUlpQueuedHW was set to 0."
  ::= { cSctpAssocExtEntry 15 }

cSctpAssocExtChunksRecControl OBJECT-TYPE
    SYNTAX                   Counter32
    UNITS                    "chunks"
    MAX-ACCESS               read-only
    STATUS                   current
    DESCRIPTION
      "Number of control Chucks received by this association."
  ::= { cSctpAssocExtEntry 16 }

cSctpAssocExtChunksRecOrdered   OBJECT-TYPE
    SYNTAX                   Counter32
    UNITS                    "chunks"
    MAX-ACCESS               read-only
    STATUS                   current
    DESCRIPTION
      "Number of Chucks received by this association where order
       is required."
  ::= { cSctpAssocExtEntry 17 }

cSctpAssocExtChunksRecUnOrdered OBJECT-TYPE
    SYNTAX                   Counter32
    UNITS                    "chunks"
    MAX-ACCESS               read-only
    STATUS                   current
    DESCRIPTION
      "Number of Chucks received by this association where order
       is not required."
  ::= { cSctpAssocExtEntry 18 }

cSctpAssocExtChunksSentControl  OBJECT-TYPE
    SYNTAX                   Counter32
    UNITS                    "chunks"
    MAX-ACCESS               read-only
    STATUS                   current
    DESCRIPTION
      "Number of control Chucks sent by this association."
  ::= { cSctpAssocExtEntry 19 }

cSctpAssocExtChunksSentOrdered  OBJECT-TYPE
    SYNTAX                   Counter32
    UNITS                    "chunks"
    MAX-ACCESS               read-only
    STATUS                   current
    DESCRIPTION
      "Number of Chucks sent by this association where order 
       is required."
  ::= { cSctpAssocExtEntry 20 }

cSctpAssocExtChunksSentUnOrdered  OBJECT-TYPE
    SYNTAX                   Counter32
    UNITS                    "chunks"
    MAX-ACCESS               read-only
    STATUS                   current
    DESCRIPTION
      "Number of Chucks sent by this association where order 
       is not required."
  ::= { cSctpAssocExtEntry 21 }

cSctpAssocExtDatagramsRec       OBJECT-TYPE
    SYNTAX                   Counter32
    UNITS                    "datagrams"
    MAX-ACCESS               read-only
    STATUS                   current
    DESCRIPTION
      "Number of IP datagrams received by this association."
  ::= { cSctpAssocExtEntry 22 }

cSctpAssocExtDatagramsSent      OBJECT-TYPE
    SYNTAX                   Counter32
    UNITS                    "datagrams"
    MAX-ACCESS               read-only
    STATUS                   current
    DESCRIPTION
      "Number of IP datagrams sent by this association."
 ::= { cSctpAssocExtEntry 23 }

cSctpAssocExtEffectiveAddrType OBJECT-TYPE
    SYNTAX         InetAddressType
    MAX-ACCESS     read-only
    STATUS         current
    DESCRIPTION
         "Internet type of effective destination IP address. This 
          is the type of IP address to which traffic is currently
          sent for this association."
 ::= { cSctpAssocExtEntry 24 }

cSctpAssocExtEffectiveAddress OBJECT-TYPE
    SYNTAX         InetAddress
    MAX-ACCESS     read-only
    STATUS         current
    DESCRIPTION
        "Effective destination IP address. This is the IP address
         to which traffic is currently sent for this association.
         This value can be any of the IP addresses defined in 
         the cSctpAssocRemAddressExtTable Table."  
    REFERENCE 
       "[sctp] RFC2960 section 8.1 Endpoint Failure Detection"
 ::= { cSctpAssocExtEntry 25 }

cSctpAssocExtRtxChunksFast   OBJECT-TYPE
  SYNTAX                     Counter32
  UNITS                      "chunks" 
  MAX-ACCESS                 read-only
  STATUS                     current
  DESCRIPTION
       "The accumulated number of SCTP chunks retransmitted using the 
        fast-recovery retransmission mechanism specified in [sctp]
        since the start of this association."
  REFERENCE
       "RFC 2960 section 7.2.4. - Fast Retransmit on Gap Reports."
 ::= { cSctpAssocExtEntry 26 }

cSctpAssocExtBundleFlag       OBJECT-TYPE
  SYNTAX                      TruthValue
  MAX-ACCESS                  read-only
  STATUS                      current
  DESCRIPTION          
          "This objects indicates if the SCTP protocol allows chunks to 
           be bundled into a single datagram as follows:

           'true(1)'  Indicates that chunks will be bundled.

           'false(2)' Indicates that chunks will not be bundled."
 ::= { cSctpAssocExtEntry 27 }

cSctpAssocExtBundleTimeout   OBJECT-TYPE
  SYNTAX                     Unsigned32 (1..60000) 
  UNITS                      "milliseconds"
  MAX-ACCESS                 read-only
  STATUS                     current
  DESCRIPTION
       "The amount time to wait to allow data chunks to
        accumulate so that they can be transmitted in the 
        same datagram. The arrival of the first data chunk
        will start a timer that will expire in the specified
        milliseconds. All later chunks will be delayed until 
        the timer expires. When the timer expires the data
        chunks will be sent out in one or more datagrams." 
 ::= { cSctpAssocExtEntry 28 }

-- *************************************************************
-- * Association Remote Addresses Extensions TABLE 
-- *************************************************************
cSctpAssocRemAddressExtTable OBJECT-TYPE
 SYNTAX                      SEQUENCE OF CSctpAssocRemAddressExtEntry
 MAX-ACCESS                  not-accessible
 STATUS                      current
 DESCRIPTION
      "Expanded table of cSctpAssocRemAddressExtTable based on 
       the AssocId index."  
 ::= { cSctpExtTables 2 }

cSctpAssocRemAddressExtEntry OBJECT-TYPE
 SYNTAX                      CSctpAssocRemAddressExtEntry
 MAX-ACCESS                  not-accessible
 STATUS                      current
 DESCRIPTION
      "Additional information about destination IP 
       addresses."
 AUGMENTS {cSctpAssocRemAddressEntry}
 ::= { cSctpAssocRemAddressExtTable 1 }

CSctpAssocRemAddressExtEntry ::= SEQUENCE {
 cSctpAssocRemAddressFailedCnt       Counter32,     -- Statistic
 cSctpAssocRemAddressSRTT            Unsigned32
 }

cSctpAssocRemAddressFailedCnt OBJECT-TYPE
 SYNTAX                      Counter32
 MAX-ACCESS                  read-only
 STATUS                      current
 DESCRIPTION
      "Number of times the destination address was marked 
       as failed."
 ::= { cSctpAssocRemAddressExtEntry 1 }

cSctpAssocRemAddressSRTT     OBJECT-TYPE
 SYNTAX                      Unsigned32(0..65535)
 UNITS                       "milliseconds"
 MAX-ACCESS                  read-only
 STATUS                      current
 DESCRIPTION
      "The Smoothed Round Trip Time(SRTT) is obtained by 
       averaging the measured Rount trip times(RTT) between
       the local and remote systems on an IP Network.
       A value of '0' is reported for SRTT prior to the 
       first successful RTT calculation."
 REFERENCE
       "[sctp] section 6.3.1 RTO Calculation"
 ::= { cSctpAssocRemAddressExtEntry 2 }

-- *************************************************************
-- *                                                           *
-- * Notifications                                             *
-- *                                                           *
-- *************************************************************
cSctpExtDestAddressStateChange NOTIFICATION-TYPE
     OBJECTS {
              cSctpAssocRemAddressStatus
     }
     STATUS  current
     DESCRIPTION
          "The notification is generated when the state 
           transition of cSctpAssocRemAddressStatus has occurred."
     ::= { cSctpExtNotifications 1 }

-- ********************************************************************
-- Conformance  
-- ********************************************************************
cSctpExtConformance  OBJECT IDENTIFIER ::= { cSctpExtMIB 3 }
cSctpExtCompliances  OBJECT IDENTIFIER ::= { cSctpExtConformance 1 }
cSctpExtGroups       OBJECT IDENTIFIER ::= { cSctpExtConformance 2 }

-- ********************************************************************
-- Compliance Statements
-- ********************************************************************
cSctpExtCompliance MODULE-COMPLIANCE
  STATUS deprecated -- superceded by cSctpExtComplianceRev1
  DESCRIPTION
       "The compliance statement for CISCO-IETF-SCTP-EXT-MIB.my."

  MODULE  -- this module

       MANDATORY-GROUPS    {  cSctpExtStatGroup,
                              cSctpExtCtrlGroup,
                              cSctpExtAssocCtrlGroup,
                              cSctpExtAssocStatGroup,
                              cSctpExtAssocRemAddrGroup
                           }
  ::= { cSctpExtCompliances 1 }

cSctpExtComplianceRev1 MODULE-COMPLIANCE
  STATUS    current
  DESCRIPTION
       "The compliance statement for CISCO-IETF-SCTP-EXT-MIB.my."

  MODULE  -- this module

       MANDATORY-GROUPS    {  cSctpExtStatGroup,
                              cSctpExtAssocCtrlGroup,
                              cSctpExtAssocRemAddrGroup,
                              cSctpExtAssocNotificationsGroup,
                              cSctpExtCtrlGroupRev1,
                              cSctpExtAssocStatGroupRev1
                           }
         OBJECT  cSctpAssocExtEffectiveAddrType
         SYNTAX  InetAddressType -- { ipv4(1), ipv6(2) }
         DESCRIPTION
             "It is only required to have IPv4 and IPv6 addresses.
              Host names will be converted into IP addresses by the
              application requesting the assocation. Therefore,
              the only valid InetAddressTypes are IPv4 and IPv6."
  ::= { cSctpExtCompliances 2 }

-- ********************************************************************
-- Units of Conformance
-- ********************************************************************

cSctpExtStatGroup OBJECT-GROUP
  OBJECTS   { 
              cSctpStatRtxChucks,
              cSctpStatRtxChucksFast,
              cSctpStatDestAddressFailures
            }
  STATUS    current
  DESCRIPTION
      "A collection of objects providing SCTP per system basis 
       statistics for all associations."
  ::= { cSctpExtGroups 1 }

cSctpExtCtrlGroup OBJECT-GROUP
  OBJECTS   { 
              cSctpCtrlPurgeTimeout,
              cSctpCtrlMaxHeld
            }
  STATUS deprecated -- superceded by cSctpExtStatGroupRev1
  DESCRIPTION
       "A collection of objects providing SCTP per system basis 
        control behavior for all associations."
  ::= { cSctpExtGroups 2 }

cSctpExtAssocCtrlGroup  OBJECT-GROUP
  OBJECTS   { 
              cSctpAssocExtRtoMin,
              cSctpAssocExtRtoMax,
              cSctpAssocExtRtoInitial,
              cSctpAssocExtValCookieLife,
              cSctpAssocExtMaxInitRetr
            }
  STATUS    current
  DESCRIPTION
       "Objects used to control the behavior each association."
  ::= { cSctpExtGroups 3 }

cSctpExtAssocStatGroup  OBJECT-GROUP
  OBJECTS   { 
              cSctpAssocExtMTU,      
              cSctpAssocExtLocRecWnd,
              cSctpAssocExtLocRecWndLowMark,
              cSctpAssocExtLocRecWndZeroCnt,
              cSctpAssocExtRemRecWnd,
              cSctpAssocExtRemRecWndLowMark,
              cSctpAssocExtRemRecWndZeroCnt,
              cSctpAssocExtUlpQueued,
              cSctpAssocExtUlpQueuedHW,
              cSctpAssocExtUlpQueuedRT,
              cSctpAssocExtChunksRecControl,
              cSctpAssocExtChunksRecOrdered,  
              cSctpAssocExtChunksRecUnOrdered,
              cSctpAssocExtChunksSentControl,  
              cSctpAssocExtChunksSentOrdered,   
              cSctpAssocExtChunksSentUnOrdered, 
              cSctpAssocExtDatagramsRec,        
              cSctpAssocExtDatagramsSent
            }
  STATUS deprecated -- superceded by cSctpExtAssocStatGroupRev1
  DESCRIPTION
       "Objects used to collect information and statistics on 
        each association."
  ::= { cSctpExtGroups 4 }

cSctpExtAssocRemAddrGroup  OBJECT-GROUP
  OBJECTS   { 
              cSctpAssocRemAddressFailedCnt,
              cSctpAssocRemAddressSRTT 
            }
  STATUS    current
  DESCRIPTION
       "Objects used to collect information and statistics on 
        each destination IP address."
  ::= { cSctpExtGroups 5 }

cSctpExtAssocNotificationsGroup NOTIFICATION-GROUP
  NOTIFICATIONS {
          cSctpExtDestAddressStateChange
  }                      
  STATUS current
  DESCRIPTION
          "Object used to provide notifications of state changes 
           on destination IP addresses."
  ::= { cSctpExtGroups 6 }

cSctpExtCtrlGroupRev1 OBJECT-GROUP
  OBJECTS   { 
              cSctpCtrlPurgeTimeout,
              cSctpCtrlMaxHeld,
              cSctpAddressStateNotifEnabled
            }
  STATUS    current
  DESCRIPTION
       "A collection of objects providing SCTP per system basis 
        control behavior for all associations."
  ::= { cSctpExtGroups 7 }

cSctpExtAssocStatGroupRev1  OBJECT-GROUP
  OBJECTS   { 
              cSctpAssocExtMTU,      
              cSctpAssocExtLocRecWnd,
              cSctpAssocExtLocRecWndLowMark,
              cSctpAssocExtLocRecWndZeroCnt,
              cSctpAssocExtRemRecWnd,
              cSctpAssocExtRemRecWndLowMark,
              cSctpAssocExtRemRecWndZeroCnt,
              cSctpAssocExtUlpQueued,
              cSctpAssocExtUlpQueuedHW,
              cSctpAssocExtUlpQueuedRT,
              cSctpAssocExtChunksRecControl,
              cSctpAssocExtChunksRecOrdered,  
              cSctpAssocExtChunksRecUnOrdered,
              cSctpAssocExtChunksSentControl,  
              cSctpAssocExtChunksSentOrdered,   
              cSctpAssocExtChunksSentUnOrdered, 
              cSctpAssocExtDatagramsRec,        
              cSctpAssocExtDatagramsSent,
              cSctpAssocExtEffectiveAddrType,
              cSctpAssocExtEffectiveAddress, 
              cSctpAssocExtRtxChunksFast,    
              cSctpAssocExtBundleTimeout,   
              cSctpAssocExtBundleFlag      
            }
  STATUS    current
  DESCRIPTION
       "Objects used to collect information and statistics on 
        each association."
  ::= { cSctpExtGroups 8 }

END
