CISCO-COMMON-MGMT-CAPABILITY DEFINITIONS ::= BEGIN

IMPORTS
        MODULE-IDENTITY
                FROM SNMPv2-SMI
        AGENT-CAPABILITIES
                FROM SNMPv2-CONF
        ciscoAgentCapability
                FROM CISCO-SMI;

ciscoCommonMgmtCapability MODULE-IDENTITY
        LAST-UPDATED    "200508270000Z"
        ORGANIZATION    "Cisco Systems, Inc."
        CONTACT-INFO
                "       Cisco Systems
                        Customer Service

                Postal: 170 W Tasman Drive
                        San Jose, CA  95134
                        USA

                   Tel: +1 800 553-NETS

                E-mail: cs-san@cisco.com"
        DESCRIPTION
                "Agent capabilities for CISCO-COMMON-MGMT-MIB"

        REVISION  "200508270000Z"
        DESCRIPTION
                "Initial version of this MIB module."        
        ::= { ciscoAgentCapability 448 }

--
-- Agent capability for SANOS 3.0 (MDS Platform)
--
ciscoCommonMgmtCapMDS30R1 AGENT-CAPABILITIES

PRODUCT-RELEASE "Cisco MDS 3.0(1)"
        STATUS          current
        DESCRIPTION     "Cisco Common Management MIB capabilities"

        SUPPORTS        CISCO-COMMON-MGMT-MIB
        INCLUDES        { ccmConfigurationGroup }

        VARIATION       ccmCommonUserLastChange
        ACCESS          not-implemented
        DESCRIPTION     "Not supported."

        VARIATION       ccmCommonUserExpiryDate
        DESCRIPTION     "Only the Date (Year, Month and Day) fields of 
                         of the object are used. All other fields are 
                         initialized to zero."

        VARIATION       ccmCommonUserStorageType
        ACCESS          read-only
        DESCRIPTION     "This object is implemented as read-only."

        VARIATION       ccmCommonUserRowStatus
        SYNTAX          INTEGER {             
                            active (1),
                            createAndGo (4),
                            destroy (6)
                        }
        DESCRIPTION     "Only allowed values are :
                         - createAndGo(4) 
                         - destroy(6)
                         - active(1)
                         ."

        VARIATION       ccmCommonUserRoleName
        SYNTAX          SnmpAdminString (SIZE(1..16))
        DESCRIPTION     "Size of 1-16 is supported in line with
                         commonRoleName of CISCO-COMMON-ROLES-MIB."

        VARIATION       ccmCommonUserRoleStorageType
        ACCESS          read-only
        DESCRIPTION     "This object is implemented as read-only."

        VARIATION       ccmCommonUserRoleRowStatus
        SYNTAX          INTEGER {             
                            active (1),
                            createAndGo (4),
                            destroy (6)
                        }
        DESCRIPTION     "Only allowed values are :
                         - createAndGo(4) 
                         - destroy(6)
                         - active(1)
                         ."
::= { ciscoCommonMgmtCapability 1 }

END
