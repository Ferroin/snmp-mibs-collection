CISCO-PRINTER-CAPABILITY DEFINITIONS ::= BEGIN

IMPORTS
    MODULE-IDENTITY
        FROM SNMPv2-SMI
    AGENT-CAPABILITIES
        FROM SNMPv2-CONF
    ciscoAgentCapability
        FROM CISCO-SMI;

ciscoPrinterCapability MODULE-IDENTITY
    LAST-UPDATED    "200706070000Z"
    ORGANIZATION    "Cisco Systems, Inc."
    CONTACT-INFO
            "Cisco Systems
            Customer Service

            Postal: 170 W Tasman Drive
            San Jose, CA  95134
            USA

            Tel: +1 800 553-NETS

            E-mail: cs-snmp@cisco.com"
    DESCRIPTION
        "Agent capabilities for Printer-MIB"
    REVISION        "200706070000Z"
    DESCRIPTION
        "Initial version of this MIB module."
    ::= { ciscoAgentCapability 548 }

ciscoPrinterCapabilityV12R04 AGENT-CAPABILITIES
    PRODUCT-RELEASE "Cisco IOS 12.4"
    STATUS          current
    DESCRIPTION
        "Printer MIB capabilities"

    SUPPORTS        Printer-MIB
    INCLUDES        { prtGeneralV2Group }
    VARIATION       prtGeneralPrinterName
    ACCESS          read-only
    DESCRIPTION
        "write access is not implemented"

    VARIATION       prtGeneralSerialNumber
    ACCESS          read-only
    DESCRIPTION
        "write access is not implemented"
    ::= { ciscoPrinterCapability 1 }

END
