CISCO-TN3270SERVER-MIB DEFINITIONS ::= BEGIN

IMPORTS
        MODULE-IDENTITY, 
        OBJECT-TYPE,
        Counter32,
        -- Unsigned32,
        Gauge32,
        IpAddress
            FROM SNMPv2-SMI

        TEXTUAL-CONVENTION, 
        DisplayString, 
        MacAddress, 
        TimeStamp, 
        TruthValue
            FROM SNMPv2-TC

        MODULE-COMPLIANCE, OBJECT-GROUP
            FROM SNMPv2-CONF

        ciscoMgmt
	    FROM CISCO-SMI
;

ciscoTn3270ServerMIB MODULE-IDENTITY
        LAST-UPDATED "9701220000Z"
        ORGANIZATION "Cisco Systems, Inc."
        CONTACT-INFO
            "        Cisco Systems
                     Customer Service

             Postal: 170 W. Tasman Drive
                     San Jose, CA 95134
                     USA

                Tel: +1 800 553-NETS
             e-mail: cs-tn3270@cisco.com"
        DESCRIPTION
                "The MIB module for TN3270 Server.

                MIB description

                The PU and LU MIB are defined in RFC 1666. This MIB provides
                additional information on IP and LU mapping. The following 
                entities are managed:

                1) TN3270S Global
                2) TN3270S Stats on Listen IP/Port basis
                3) TN3270S PU
                4) TN3270S IP to LU Mapping
                5) TN3270S LU to IP Mapping
                "
        REVISION     "9701220000Z"
        DESCRIPTION
                "Added tn3270sPuIpPrecedenceScreen,
                 tn3270sPuIpPrecedencePrinter,
                 tn3270sPuIpTosScreen and
                 tn3270sPuIpTosPrinter to tn3270sPuTable.

                 Added tn3270sPuNailTable and tn3270sIpNailTable.
                "

        REVISION     "9609120000Z"
        DESCRIPTION
                "Obsoleted tn3270sLuLastEvent.
                 Added ciscoTn3270ServerMIBGroupObsolete.
                 Modified SYNTAX clause for tn3270sLuAppnLinkIndex.
                 Introduced tn3270sRunningTime.
                 Replaced tn3270sStatsInboundTransactions,
                          tn3270sStatsOutboundTransactions,
                          tn3270sStatsSampledInboundTransactions,
                          tn3270sStatsNetSampledInboundTransactionRespTime,
                          tn3270sStatsSampledOutboundTransactions,
                          tn3270sStatsNetSampledOutboundTransactionRespTime,
                 with     
                          tn3270sStatsInboundChains,
                          tn3270sStatsOutboundChains,
                          tn3270sStatsSampledHostResponses,
                          tn3270sStatsNetSampledHostResponseTime,
                          tn3270sStatsSampledClientResponses,
                          tn3270sStatsNetSampledClientResponseTime
                 respectively.
                "
::= { ciscoMgmt 54 }

tn3270sObjects     OBJECT IDENTIFIER ::= { ciscoTn3270ServerMIB 1 }
tn3270sGlobal      OBJECT IDENTIFIER ::= { tn3270sObjects 1 }
tn3270sStats       OBJECT IDENTIFIER ::= { tn3270sObjects 2 }
tn3270sPu          OBJECT IDENTIFIER ::= { tn3270sObjects 3 }
tn3270sIp          OBJECT IDENTIFIER ::= { tn3270sObjects 4 }
tn3270sLu          OBJECT IDENTIFIER ::= { tn3270sObjects 5 }
tn3270sPuNail      OBJECT IDENTIFIER ::= { tn3270sObjects 6 }
tn3270sIpNail      OBJECT IDENTIFIER ::= { tn3270sObjects 7 }

Tn3270sUnsigned32 ::= TEXTUAL-CONVENTION
        STATUS     current
        DESCRIPTION
                "Unsigned32 definition. To be replaced by Unsigned32
                from SNMPv2-SMI when its implememted."
        SYNTAX INTEGER ( 0..4294967295 )

Tn3270sTCPPort ::= TEXTUAL-CONVENTION
        STATUS     current
        DESCRIPTION
                "A range for tn3270 port addresses."
        SYNTAX INTEGER ( 0..65535 )

Tn3270sPUIndex ::= TEXTUAL-CONVENTION
        STATUS     current
        DESCRIPTION
                "Address range for a PU."
        SYNTAX Tn3270sUnsigned32

Tn3270sLUIndex ::= TEXTUAL-CONVENTION
        STATUS     current
        DESCRIPTION
                "Address range for a LU."
        SYNTAX Tn3270sUnsigned32

Tn3270sCpuCard ::= TEXTUAL-CONVENTION
        STATUS current
        DESCRIPTION
                "The identity of the board running the server.
                 The values are as follows:
                  'CIP slot <number>'
                  'ECPA bay <number>'
                  'PCPA bay <number>'
                     where number is a positive integer indicating
                     the location on the platform the card is 
                     installed in."
        SYNTAX DisplayString ( SIZE ( 10..16 ) )

--  *************************************************************
--  *                                                           *
--  *           TN3270 Server -  Global information             *
--  *                                                           *
--  *************************************************************
tn3270sGlobalTable  OBJECT-TYPE
        SYNTAX      SEQUENCE OF Tn3270sGlobalEntry
        MAX-ACCESS  not-accessible
        STATUS      current
        DESCRIPTION
                "A list of TN3270 server and DLUR global information."
        ::= { tn3270sGlobal 1 }

tn3270sGlobalEntry OBJECT-TYPE
        SYNTAX    Tn3270sGlobalEntry  
        MAX-ACCESS  not-accessible
        STATUS      current
        DESCRIPTION
                "Parameters values for a group."
        INDEX { tn3270sIndex }
        ::= { tn3270sGlobalTable 1 }

Tn3270sGlobalEntry  ::=    SEQUENCE {
        tn3270sIndex                  Tn3270sUnsigned32,
        tn3270sCpuCard                Tn3270sCpuCard,
        tn3270sMaxLus                 Tn3270sUnsigned32,
        tn3270sLusInUse               Gauge32,
        tn3270sStartupTime            TimeStamp,
        tn3270sGlobalTcpPort          Tn3270sTCPPort,
        tn3270sGlobalIdleTimeout      INTEGER,
        tn3270sGlobalKeepAlive        INTEGER,
        tn3270sGlobalUnbindAction     INTEGER,
        tn3270sGlobalGenericPool      INTEGER,
        tn3270sTimingMarkSupported    TruthValue,
        tn3270sRunningTime            Tn3270sUnsigned32
}

tn3270sIndex OBJECT-TYPE
        SYNTAX Tn3270sUnsigned32
        MAX-ACCESS  not-accessible
        STATUS current
        DESCRIPTION
                "Index used to uniquely identify each tn3270 server
                instance. This index value shall not be reused when
                the server is shut down and a new instance invoked."
        ::= { tn3270sGlobalEntry 1 }

tn3270sCpuCard OBJECT-TYPE
        SYNTAX Tn3270sCpuCard
        MAX-ACCESS  read-only
        STATUS current
        DESCRIPTION
                "The identity of the board running the server."
        ::= { tn3270sGlobalEntry 2 }

tn3270sMaxLus OBJECT-TYPE
        SYNTAX Tn3270sUnsigned32 (1..65535)
        MAX-ACCESS read-only
        STATUS current
        DESCRIPTION
                "The maximum number of LUs supported by the server."
        ::= { tn3270sGlobalEntry 3 }

tn3270sLusInUse OBJECT-TYPE
        SYNTAX Gauge32 (0..65535)
        MAX-ACCESS read-only
        STATUS current
        DESCRIPTION
                "The number of LUs currently in use on the server."
        ::= { tn3270sGlobalEntry 4 }

tn3270sStartupTime OBJECT-TYPE
        SYNTAX TimeStamp
        MAX-ACCESS read-only
        STATUS current
        DESCRIPTION
                "The timestamp when the tn3270 server started."
        ::= { tn3270sGlobalEntry 5 }

tn3270sGlobalTcpPort OBJECT-TYPE
        SYNTAX Tn3270sTCPPort
        MAX-ACCESS read-only
        STATUS current
        DESCRIPTION
                "The default TCP port of this TN3270 Server, which is 
                inherited by the PU if it doesn't have the TCP port
                explicitly defined in the router configuration for this PU."
        ::= { tn3270sGlobalEntry 6 }

tn3270sGlobalIdleTimeout OBJECT-TYPE
        SYNTAX INTEGER (0..65534)
        UNITS "seconds"
        MAX-ACCESS read-only
        STATUS current
        DESCRIPTION
                "The number of seconds of LU inactivity (from either
                host or client) before the TN3270 session is disconnected.
                Zero seconds means that LU sessions, by default, will 
                not be disconnected when inactive, regardless of the 
                amount of idle time spent."
        ::= { tn3270sGlobalEntry 7 }

tn3270sGlobalKeepAlive OBJECT-TYPE
        SYNTAX INTEGER (0..65534)
        UNITS   "seconds"
        MAX-ACCESS read-only
        STATUS current
        DESCRIPTION
                "The number of seconds of inactivity from client side 
                which the TN3270 Server allows to elapse before sending
                DO-TIMING-MARK to the TN3270 client. If the client does
                not reply within thirty minutes of such a TIMING-MARK 
                sending, the server disconnects the tn3270 session. 
                Zero seconds indicates that no keepalives will be sent."
        ::= { tn3270sGlobalEntry 8 }

tn3270sGlobalUnbindAction OBJECT-TYPE
        SYNTAX INTEGER { keep(1), disconnect(2) }
        MAX-ACCESS read-only
        STATUS current
        DESCRIPTION
                "This variable indicates whether or not a tn3270 session
                will be disconnected upon UNBIND.

                keep indicates that no automatic disconnect will be made
                by the server upon receipt of an UNBIND. 

                disconnect indicates that the session will be 
                disconnected upon receipt of an UNBIND."
        ::= { tn3270sGlobalEntry 9 }

tn3270sGlobalGenericPool OBJECT-TYPE
        SYNTAX INTEGER { permit(1), deny(2) }
        MAX-ACCESS read-only
        STATUS current
        DESCRIPTION
                "This variable indicates whether or not leftover LUs 
                will be made available to tn3270 sessions which
                do not request a specific LU or LU pool. 

                A 'leftover' LU is defined as one for which all of the
                following conditions hold true:
                  .the SSCP did not send an ACTLU during PU startup; and
                  .the PU controlling the LU is capable of carrying PSID
                     vectors on NMVT messages(thus allowing DDDLU operation
                     for that LU).

                deny indicates that the leftover LUs should not
                be given to a generic pool (ie, the PU is not
                automatically fully populated with 255 LOCADDR definitions);

                permit indicates leftover LUs should be made available to 
                tn3270 users wanting 'generic' sessions. All LUs in the 
                generic pool are (by definition) Dynamic Definition of 
                Dependant (DDDLU) capable."
        REFERENCE " 'SNA Formats', 
                    publication number GA27-3136, IBM Corporation,
                    'APPN Dependent LU Requester Architecture Reference'
                    Document Number: SV40-1010-01, IBM Corporation.
                  "
        ::= { tn3270sGlobalEntry 10 }

tn3270sTimingMarkSupported OBJECT-TYPE
        SYNTAX TruthValue
        MAX-ACCESS read-only
        STATUS current
        DESCRIPTION
                "This variable indicates whether to send a timing mark to 
                solicit a response before sending a response to the host.
                true indicates that a timing mark is sent, false
                indicates that it is not sent.

                By using timing mark, an application can determine the
                response time from the client. Some existing clients do
                not implement the timing mark correctly and will not work
                with this server if this parameter is set to true "
        ::= { tn3270sGlobalEntry 11 }

tn3270sRunningTime OBJECT-TYPE
        SYNTAX Tn3270sUnsigned32
        UNITS "seconds"
        MAX-ACCESS read-only
        STATUS current
        DESCRIPTION
                "Total time elapsed since start of tn3270 server." 
        ::= { tn3270sGlobalEntry 12 }

--  *************************************************************
--  *                                                           *
--  * TN3270 Server -  Statistics and Load balancing parameters *
--  *                                                           *
--  *************************************************************

tn3270sStatsTable OBJECT-TYPE
        SYNTAX      SEQUENCE OF Tn3270sStatsEntry
        MAX-ACCESS  not-accessible
        STATUS      current
        DESCRIPTION
                "A list of statistics for each TN3270 Server Listening 
                IP/Port pair."
        ::= { tn3270sStats 1 }

tn3270sStatsEntry OBJECT-TYPE
        SYNTAX    Tn3270sStatsEntry  
        MAX-ACCESS  not-accessible
        STATUS      current
        DESCRIPTION
                "The entry contains parameters which describe the
                statistics of the ip stacks."
        INDEX { tn3270sIndex, 
                tn3270sStatsServerAddr,
                tn3270sStatsServerTcpPort }
        ::= { tn3270sStatsTable 1 }

Tn3270sStatsEntry ::= SEQUENCE {
        tn3270sStatsServerAddr                            IpAddress,
        tn3270sStatsServerTcpPort                         Tn3270sTCPPort,
        tn3270sStatsMaxSess                               Gauge32,
        tn3270sStatsSpareSess                             Gauge32,
        tn3270sStatsConnectsIn                            Counter32,
        tn3270sStatsDisconnects                           Counter32,
        tn3270sStatsTN3270ConnectsFailed                  Counter32,
        tn3270sStatsInboundChains                         Counter32,
        tn3270sStatsOutboundChains                        Counter32,
        tn3270sStatsSampledHostResponses                  Counter32,
        tn3270sStatsNetSampledHostResponseTime            Tn3270sUnsigned32,
        tn3270sStatsSampledClientResponses                Counter32,
        tn3270sStatsNetSampledClientResponseTime          Tn3270sUnsigned32
}

tn3270sStatsServerAddr OBJECT-TYPE
        SYNTAX IpAddress
        MAX-ACCESS not-accessible
        STATUS current
        DESCRIPTION
                "The ip address of this TN3270 Server Listen endpoint."
        ::= { tn3270sStatsEntry 1 }

tn3270sStatsServerTcpPort OBJECT-TYPE
        SYNTAX Tn3270sTCPPort
        MAX-ACCESS not-accessible
        STATUS current
        DESCRIPTION
                "The TCP port in this TN3270 Server Listen endpoint."
        ::= { tn3270sStatsEntry 2 }

tn3270sStatsMaxSess OBJECT-TYPE
        SYNTAX Gauge32
        MAX-ACCESS read-only
        STATUS current
        DESCRIPTION
                "Number of Tn3270 sessions configured which are
                available to be used by tn3270 clients."
        ::= { tn3270sStatsEntry 3 }

tn3270sStatsSpareSess OBJECT-TYPE
        SYNTAX Gauge32
        MAX-ACCESS read-only
        STATUS current
        DESCRIPTION
                "Spare number of TN3270 sessions available for connect
                at query time."
        ::= { tn3270sStatsEntry 4 }

tn3270sStatsConnectsIn OBJECT-TYPE
        SYNTAX Counter32
        MAX-ACCESS read-only
        STATUS current
        DESCRIPTION
                "Total number of TN3270 session connects-in received."
        ::= { tn3270sStatsEntry 5 }

tn3270sStatsDisconnects OBJECT-TYPE
        SYNTAX Counter32
        MAX-ACCESS read-only
        STATUS current
        DESCRIPTION
                "Total number of TN3270 sessions disconnected."
        ::= { tn3270sStatsEntry 6 }

tn3270sStatsTN3270ConnectsFailed OBJECT-TYPE
        SYNTAX Counter32
        MAX-ACCESS read-only
        STATUS current
        DESCRIPTION
                "Total number of attempted sessions which failed to
                negotiate TN3270/E or were rejected by control point."
        ::= { tn3270sStatsEntry 7 }

tn3270sStatsInboundChains OBJECT-TYPE
        SYNTAX Counter32
        MAX-ACCESS read-only
        STATUS current
        DESCRIPTION
                "Total number of inbound(from client to host) RU chains 
                (identified by end of record (EOR)) processed. Since 
                every inbound RU chain is accompanied by client giving 
                host the direction(CD), it is also a count of number of 
                client transactions."
        ::= { tn3270sStatsEntry 8 }

tn3270sStatsOutboundChains OBJECT-TYPE
        SYNTAX Counter32
        MAX-ACCESS read-only
        STATUS current
        DESCRIPTION
                "Total number of Outbound(from host to client) RU Chains 
                 (identified by EOR) processed."
        ::= { tn3270sStatsEntry 9 }

tn3270sStatsSampledHostResponses OBJECT-TYPE
        SYNTAX Counter32
        MAX-ACCESS read-only
        STATUS current
        DESCRIPTION
                "Total number of Sampled Inbound Transactions 
                (identified by EOR) on which response time is 
                computed since restart of last listen on
                ServerAddress/TcpPort. Counters get reset at 
                that point."
        ::= { tn3270sStatsEntry 10 }

tn3270sStatsNetSampledHostResponseTime OBJECT-TYPE
        SYNTAX Tn3270sUnsigned32
        UNITS "10milliseconds"
        MAX-ACCESS read-only
        STATUS current
        DESCRIPTION
                "Total response time for all sampled inbound 
                transactions for which response time is computed.
                Response time is the time difference between receiving
                EOR from the client, and receiving the response from the
                host. Note that the average response time is given by
                this object divided by tn3270sStatsSampledHostResponses."
        ::= { tn3270sStatsEntry 11 }

tn3270sStatsSampledClientResponses OBJECT-TYPE
        SYNTAX Counter32
        MAX-ACCESS read-only
        STATUS current
        DESCRIPTION
                "Total number of sampled outbound timing marks on 
                 which response time computed."
        ::= { tn3270sStatsEntry 12 }

tn3270sStatsNetSampledClientResponseTime OBJECT-TYPE
        SYNTAX Tn3270sUnsigned32
        UNITS "10milliseconds"
        MAX-ACCESS read-only
        STATUS current
        DESCRIPTION
                "Total response time for all sampled timing marks 
                on which response time is computed. Response time
                is the time diference between sending the timeing mark
                to the client and receiving the response from the client.
                Note that this is only valid if timeing mark is 
                configured. Note that the average outbound response 
                time is given by this object divided by 
                tn3270sStatsSampledClientResponses."
        ::= { tn3270sStatsEntry 13 }

--  *************************************************************
--  *                                                           *
--  *           TN3270 Server -  PU parameters                  *
--  *                                                           *
--  *************************************************************

tn3270sPuTable OBJECT-TYPE
        SYNTAX  SEQUENCE OF Tn3270sPuEntry
        MAX-ACCESS  not-accessible
        STATUS  current
        DESCRIPTION
                "This table contains objects which describe the PU
                configuration parameters not defined in the
                NAU mib, APPN mib or DLUR mib"
        ::= { tn3270sPu  1 }

tn3270sPuEntry OBJECT-TYPE
        SYNTAX  Tn3270sPuEntry
        MAX-ACCESS  not-accessible
        STATUS  current
        DESCRIPTION
                "A list of TN3270 server PU parameters"
        INDEX  { tn3270sIndex, tn3270sPuIndex }
        ::= { tn3270sPuTable 1 }

Tn3270sPuEntry ::= SEQUENCE {
        tn3270sPuIndex               Tn3270sPUIndex,
        tn3270sPuIpAddr              IpAddress,
        tn3270sPuTcpPort             Tn3270sTCPPort,
        tn3270sPuIdleTimeout         INTEGER,
        tn3270sPuKeepAlive           INTEGER,
        tn3270sPuUnbindAction        INTEGER,
        tn3270sPuGenericPool         INTEGER,
        tn3270sPuState               INTEGER,
        tn3270sPuType                INTEGER,
        tn3270sPuLuSeed              DisplayString,
        tn3270sLocalSapAddress       INTEGER,
        tn3270sRemoteSapAddress      INTEGER,
        tn3270sRemoteMacAddress      MacAddress,
        tn3270sPuIpPrecedenceScreen  INTEGER,
        tn3270sPuIpPrecedencePrinter INTEGER,
        tn3270sPuIpTosScreen         INTEGER,
        tn3270sPuIpTosPrinter        INTEGER
}

tn3270sPuIndex OBJECT-TYPE
        SYNTAX  Tn3270sPUIndex
        MAX-ACCESS  not-accessible
        STATUS  current
        DESCRIPTION
                "Index used to uniquely identify each Node instance. This
                is the same as snaNodeAdminIndex in the NAU MIB."
        ::= { tn3270sPuEntry 1 }

tn3270sPuIpAddr OBJECT-TYPE
        SYNTAX IpAddress
        MAX-ACCESS read-only
        STATUS current
        DESCRIPTION
                "The ip address of this TN3270 server."
        ::= { tn3270sPuEntry 2 }

tn3270sPuTcpPort OBJECT-TYPE
        SYNTAX Tn3270sTCPPort
        MAX-ACCESS read-only
        STATUS current
        DESCRIPTION
                "The TCP port of this TN3270 server telnet session."
        ::= { tn3270sPuEntry 3 }

tn3270sPuIdleTimeout OBJECT-TYPE
        SYNTAX INTEGER (0..65535)
        MAX-ACCESS read-only
        STATUS current
        DESCRIPTION
                "The number of seconds of LU inactivity (from either
                host or client) before the TN3270 session is
                disconnected. Zero seconds means that LU sessions,
                by default, will not be disconnected when inactive,
                regardless of the amount of idle time spent.

                65535 (not valid in server context) indicates that
                the idletime value should be taken from the server 
                context."
        ::= { tn3270sPuEntry 4 }

tn3270sPuKeepAlive OBJECT-TYPE
        SYNTAX INTEGER (0..65535)
        MAX-ACCESS read-only
        STATUS current
        DESCRIPTION
                "The number of seconds of inactivity from client side
                which the TN3270 Server allows to elapse before
                sending DO-TIMING-MARK to the TN3270 client. If the
                client does not reply within thirty minutes of such
                a TIMING-MARK sending, the server disconnect the tn3270
                session. Zero seconds indicates that no keepalives
                will be sent. 

                65535 (not valid in server context) indicates that the 
                default keepalive value for an LU is taken from whatever
                value had been defined in the server context for this 
                CIP card."
        ::= { tn3270sPuEntry 5 }

tn3270sPuUnbindAction OBJECT-TYPE
        SYNTAX INTEGER { keep(1), disconnect(2), inherit(3) }
        MAX-ACCESS read-only
        STATUS current
        DESCRIPTION
                "This variable indicates whether or not a tn3270 session
                will be disconnected upon UNBIND.

                keep indicates that no automatic disconnect will be made by
                  the server upon receipt of an UNBIND.

                disconnect indicates that the session will be 
                  disconnected upon receipt of an UNBIND. 

                inherit indicates that the default keepalive value of an
                  LU is taken from whatever value had been defined in
                  the server context for this CIP card."
        ::= { tn3270sPuEntry 6 }

tn3270sPuGenericPool OBJECT-TYPE
        SYNTAX INTEGER { permit(1), deny(2), inherit(3) }
        MAX-ACCESS read-only
        STATUS current
        DESCRIPTION
                "This variable indicates whether or not leftover LUs
                will be made available to tn3270 sessions which
                do not request a specific LU or LU pool.

                A 'leftover' LU is defined as one for which all of
                the following conditions hold true:
                    .the SSCP did not send an ACTLU during PU startup; and
                    .the PU controlling the LU is capable of carrying PSID
                       vectors on NMVT messages (thus allowing DDDLU 
                       operation for that LU).

                inherit indicates that the value of tn3270sPuGenericPool is
                  to be the same as tn3270sGlobalGenericPool.

                deny indicates that the leftover LUs should not be given
                  to a generic pool (ie, the PU is not automatically
                  fully populated with 255 LOCADDR definitions);

                permit indicates leftover LUs should be made available to
                  tn3270 users wanting 'generic' sessions. All LUs in the
                  generic pool are (by definition) DDDLU capable."
        ::= { tn3270sPuEntry 7 }

tn3270sPuState   OBJECT-TYPE
        SYNTAX INTEGER {
            shut     (1),
            reset    (2),
            inactive (3),
            test     (4),
            xid      (5),
            pActpu   (6),
            active   (7),
            actBusy  (8)
        }
        MAX-ACCESS read-only
        STATUS current
        DESCRIPTION
                "The value identifies the current PU state. This has 
                a different meaning for direct or DLUR PU before the
                link station is established.
                For DLUR PU, the PU is in reset state, for direct PU, 
                this will be either sending a TEST or XID

                shut     (1) - The PU is configured but in shut state
                reset    (2) - The link station of this PU is not active.
                inactive (3) - The PU is not activated and the link-station 
                                 or DLUR state is unknown.
                test     (4) - PU is sending a TEST to establish link.
                xid      (5) - TEST is responded, XID is sent.
                pActpu   (6) - The link station is up but no ACTPU is 
                                 received.
                active   (7) - ACTPU is received and acknowledged positively.
                actBusy  (8) - Awaiting host to acknowledge the SSCP-PU data.
          "
        ::= { tn3270sPuEntry 8 }

tn3270sPuType   OBJECT-TYPE
        SYNTAX INTEGER { dlur(1), direct(2) }
        MAX-ACCESS read-only
        STATUS current
        DESCRIPTION
                "This defines whether the connection to the host is
                via DLUR or direct link. If DLUR, LuSeed, lmac/sap,
                and rmac/sap in this table are undefined."
        ::= { tn3270sPuEntry 9 }

tn3270sPuLuSeed OBJECT-TYPE
        SYNTAX DisplayString ( SIZE ( 1..6 ) )
        MAX-ACCESS read-only
        STATUS current
        DESCRIPTION
                "For Direct PU this defines the LU name prefix (LU seed)
                which is concatinated with the locaddr to form a unique 
                name."
        ::= { tn3270sPuEntry 10 }

tn3270sLocalSapAddress OBJECT-TYPE
        SYNTAX INTEGER (1..254)
        MAX-ACCESS read-only
        STATUS current
        DESCRIPTION
                "SAP address of the local direct node."
        ::= { tn3270sPuEntry 11 }

tn3270sRemoteSapAddress OBJECT-TYPE
        SYNTAX INTEGER (1..254)
        MAX-ACCESS read-only
        STATUS current
        DESCRIPTION
                "SAP address of the remote node; valid for direct PU only."
        ::= { tn3270sPuEntry 12 }

tn3270sRemoteMacAddress OBJECT-TYPE
        SYNTAX MacAddress
        MAX-ACCESS read-only
        STATUS current
        DESCRIPTION
                "MAC address of the remote node; valid for direct PU only."
        ::= { tn3270sPuEntry 13 }

tn3270sPuIpPrecedenceScreen OBJECT-TYPE
        SYNTAX INTEGER (0..7)
        MAX-ACCESS read-only
        STATUS current
        DESCRIPTION
                "The value of the PRECEDENCE field in the Type of 
                Service octet in the IP header set by the TN3270
                server for outbound IP packets destined to the TN3270
                client screen. That is from the router to the TN3270
                client screen."
        REFERENCE "RFC791, RFC1349"
        ::= { tn3270sPuEntry 14 }

tn3270sPuIpPrecedencePrinter OBJECT-TYPE
        SYNTAX INTEGER (0..7)
        MAX-ACCESS read-only
        STATUS current
        DESCRIPTION
                "The value of the PRECEDENCE field in the Type of 
                Service octet in the IP header set by the TN3270
                server for outbound IP packets destined to the TN3270
                client printer. That is from the router to the TN3270
                client printer."
        REFERENCE "RFC791, RFC1349"
        ::= { tn3270sPuEntry 15 }

tn3270sPuIpTosScreen OBJECT-TYPE
        SYNTAX INTEGER (0..15)
        MAX-ACCESS read-only
        STATUS current
        DESCRIPTION
                "The value of the TOS field in the Type of Service
                octet in the IP header set by the TN3270 server
                for outbound IP packets destined to the TN3270
                client screen. That is from the router to the TN3270
                client screen."
        REFERENCE "RFC791, RFC1349"
        ::= { tn3270sPuEntry 16 }

tn3270sPuIpTosPrinter OBJECT-TYPE
        SYNTAX INTEGER (0..15)
        MAX-ACCESS read-only
        STATUS current
        DESCRIPTION
                "The value of the TOS field in the Type of Service
                octet in the IP header set by the TN3270 server
                for outbound IP packets destined to the TN3270
                client printer. That is from the router to the TN3270
                client printer."
        REFERENCE "RFC791, RFC1349"
        ::= { tn3270sPuEntry 17 }

--  *************************************************************
--  *                                                           *
--  *           TN3270 Server -  IP mapping                     *
--  *                                                           *
--  *************************************************************

tn3270sIpTable OBJECT-TYPE
        SYNTAX      SEQUENCE OF Tn3270sIpEntry
        MAX-ACCESS  not-accessible
        STATUS      current
        DESCRIPTION
                "A list of IP to LU mapping entries"
        ::= { tn3270sIp 1 }

tn3270sIpEntry OBJECT-TYPE
        SYNTAX    Tn3270sIpEntry  
        MAX-ACCESS  not-accessible
        STATUS      current
        DESCRIPTION
                "A list of entries to relate a client IP address to the
                LU"
        INDEX { tn3270sIndex, tn3270sIpClientAddr,  tn3270sIpClientTcpPort }
        ::= { tn3270sIpTable 1 }

Tn3270sIpEntry ::= SEQUENCE {
        tn3270sIpClientAddr     IpAddress,
        tn3270sIpClientTcpPort  Tn3270sTCPPort,
        tn3270sIpPuIndex        Tn3270sPUIndex,
        tn3270sIpLuIndex        Tn3270sLUIndex
}

tn3270sIpClientAddr OBJECT-TYPE
        SYNTAX IpAddress
        MAX-ACCESS not-accessible
        STATUS current
        DESCRIPTION
                "The ip address of the TN3270 client."
        ::= { tn3270sIpEntry 1 }

tn3270sIpClientTcpPort OBJECT-TYPE
        SYNTAX Tn3270sTCPPort
        MAX-ACCESS not-accessible
        STATUS current
        DESCRIPTION
                "The TCP port of the TN3270 client."
        ::= { tn3270sIpEntry 2 }

tn3270sIpPuIndex OBJECT-TYPE
        SYNTAX Tn3270sPUIndex
        MAX-ACCESS read-only
        STATUS current
        DESCRIPTION
                "The PU index associated with NAU and PU objects"
        ::= { tn3270sIpEntry 3 }

tn3270sIpLuIndex OBJECT-TYPE
        SYNTAX Tn3270sLUIndex
        MAX-ACCESS read-only
        STATUS current
        DESCRIPTION
                "The LU index associated with NAU and LU objects."
        ::= { tn3270sIpEntry 4 }

--  *************************************************************
--  *                                                           *
--  *           TN3270 Server -  LU mapping                     *
--  *                                                           *
--  *************************************************************

tn3270sLuTable OBJECT-TYPE
        SYNTAX      SEQUENCE OF Tn3270sLuEntry
        MAX-ACCESS  not-accessible
        STATUS      current
        DESCRIPTION
                "This helps map LU to client ip/port. Also it provides
                other useful parameters not available elsewhere."
        ::= { tn3270sLu 1 }

tn3270sLuEntry OBJECT-TYPE
        SYNTAX    Tn3270sLuEntry  
        MAX-ACCESS  not-accessible
        STATUS      current
        DESCRIPTION
                "Parameters values for a group."
        INDEX { tn3270sIndex, tn3270sLuPuIndex, tn3270sLuIndex }
        ::= { tn3270sLuTable 1 }

Tn3270sLuEntry ::=  SEQUENCE {
        tn3270sLuPuIndex       Tn3270sPUIndex,
        tn3270sLuIndex         Tn3270sLUIndex,
        tn3270sLuClientAddr    IpAddress,
        tn3270sLuClientTcpPort Tn3270sTCPPort,
        tn3270sLuTelnetType    INTEGER,
        tn3270sLuTermModel     DisplayString,
        tn3270sLuState         INTEGER,
        tn3270sLuCurInbPacing  INTEGER,
        tn3270sLuCurInbQsize   INTEGER,
        tn3270sLuCurOutQsize   INTEGER,
        tn3270sLuIdleTime      INTEGER,
        tn3270sLuType          INTEGER,
        tn3270sLuAppnLinkIndex DisplayString,
        tn3270sLuLfsid         INTEGER,
        tn3270sLuLastEvent     TimeStamp,
        tn3270sLuEvents        OCTET STRING,
        tn3270sLuNail          TruthValue
}

tn3270sLuPuIndex OBJECT-TYPE
        SYNTAX Tn3270sPUIndex
        MAX-ACCESS not-accessible
        STATUS current
        DESCRIPTION
                "Index used to uniquely identify each PU instance. This
                is the same as snaNodeAdminIndex in the NAU MIB."
        ::= { tn3270sLuEntry 1 }

tn3270sLuIndex OBJECT-TYPE
        SYNTAX Tn3270sLUIndex
        MAX-ACCESS not-accessible
        STATUS current
        DESCRIPTION
                "Index used to uniquely identify the LU instance within 
                a PU. It is the locaddr. This is the same as 
                snaLuAdminLuIndex in the NAU MIB."
        ::= { tn3270sLuEntry 2 }

tn3270sLuClientAddr OBJECT-TYPE
        SYNTAX IpAddress
        MAX-ACCESS read-only
        STATUS current
        DESCRIPTION
                "The ip address of the TN3270 client connected to this LU."
        ::= { tn3270sLuEntry 3 }

tn3270sLuClientTcpPort OBJECT-TYPE
        SYNTAX Tn3270sTCPPort
        MAX-ACCESS read-only
        STATUS current
        DESCRIPTION
                "The TCP port of the TN3270 client connected to this LU."
        ::= { tn3270sLuEntry 4 }

tn3270sLuTelnetType OBJECT-TYPE
        SYNTAX INTEGER { tn3270(1), tn3270e(2), neverConnect(3) }
        MAX-ACCESS read-only
        STATUS current
        DESCRIPTION
                "This indicates whether the negotiated TN3270 session.
                TN3270, TN3270E or never connected."
        ::= { tn3270sLuEntry 5 }

tn3270sLuTermModel   OBJECT-TYPE
        SYNTAX DisplayString ( SIZE ( 1..17 ) )
        MAX-ACCESS read-only
        STATUS current
        DESCRIPTION
                "Terminal type or model number of the incoming TN3270 client."
        REFERENCE "rfc1647"
        ::= { tn3270sLuEntry 6 }

tn3270sLuState OBJECT-TYPE
        SYNTAX INTEGER {
             inactive   (1),
             active     (2),
             pSdt       (3),
             actSession (4),
             pActlu     (5),
             pNotifyAv  (6),
             pNotifyUa  (7),
             pReset     (8),
             pPsid      (9),
             pBind      (10),
             pUnbind    (11),
             unbindWt   (12),
             sdtWt      (13)
        }
        MAX-ACCESS read-only
        STATUS current
        DESCRIPTION
                "The value identifies the current LU state.
                inactive    (1)  - LU didn't receive ACTLU.
                active      (2)  - LU received ACTLU and acknowledged 
                                    positively.
                pSdt        (3)  - LU is bound but there is no SDT yet.
                act/session (4)  - LU is bound and in session.
                pActlu      (5)  - telnet connects in and is awating for 
                                    ACTLU.
                pNotifyAv   (6)  - awaiting host notify-available response.
                pNotifyUa   (7)  - awaiting host notify-unavailable response.
                pReset      (8)  - awaiting for a buffer to send DACTLU 
                                    response.
                pPsid       (9)  - awaiting for NMVT Reply psid response.
                pBind       (10) - awaiting for host to send bind.
                pUnbind     (11) - awaiting host unbind response.
                unbindWt    (12) - awaiting for client to acknowledge 
                                     disconnection.
                sdtWt       (13) - awaiting for client to acknowledge SDT
                "
        ::= { tn3270sLuEntry 7 }

tn3270sLuCurInbPacing OBJECT-TYPE
        SYNTAX INTEGER( 0..63 )
        MAX-ACCESS read-only
        STATUS current
        DESCRIPTION
                "The number of inbound frames allowed to be sent to the
                host without receiving a pacing response from the host."
        ::= { tn3270sLuEntry 8 }

tn3270sLuCurInbQsize OBJECT-TYPE
        SYNTAX INTEGER( 0..63 )
        MAX-ACCESS read-only
        STATUS current
        DESCRIPTION
                "After inbound pacing credit is exhausted, the inbound 
                data is queued. This is the number of inbound frames
                queued waiting for host pacing response."
        ::= { tn3270sLuEntry 9 }

tn3270sLuCurOutQsize OBJECT-TYPE
        SYNTAX INTEGER( 0..63 )
        MAX-ACCESS read-only
        STATUS current
        DESCRIPTION
                "The number of TCP packets in the server queued for 
                transmission to the client"
        ::= { tn3270sLuEntry 10 }

tn3270sLuIdleTime OBJECT-TYPE
        SYNTAX INTEGER( 0..65535 )
        UNITS "seconds"
        MAX-ACCESS read-only
        STATUS current
        DESCRIPTION
                "Time since last activity was recorded on this LU."
        ::= { tn3270sLuEntry 11 }

tn3270sLuType OBJECT-TYPE
        SYNTAX INTEGER { dynamic(1), static(2) }
        MAX-ACCESS read-only
        STATUS current
        DESCRIPTION
                "This indicates whether LU is dynamic or static.
                dynamic (1) - LU is configured as DDDLU. 
                static  (2) - LU is configured as specific. Host will send
                                ACTLU as soon as PU is active.
                "
        ::= { tn3270sLuEntry 12 }

tn3270sLuAppnLinkIndex OBJECT-TYPE
        SYNTAX DisplayString (SIZE (1..8) )
        MAX-ACCESS read-only
        STATUS current
        DESCRIPTION
                "This is the link index into APPN mib for link on which 
                bind flowed; only valid for DLUR LU."
        ::= { tn3270sLuEntry 13 }

tn3270sLuLfsid OBJECT-TYPE
        SYNTAX INTEGER( 0..65535 )
        MAX-ACCESS read-only
        STATUS current
        DESCRIPTION
                "This is the session identifier on a PU 2.1 link."
        ::= { tn3270sLuEntry 14 }

tn3270sLuLastEvent OBJECT-TYPE
        SYNTAX TimeStamp
        MAX-ACCESS read-only
        STATUS obsolete
        DESCRIPTION
                "Time at which the last data was logged for this LU."
        ::= { tn3270sLuEntry 15 }

tn3270sLuEvents  OBJECT-TYPE
        SYNTAX  OCTET STRING ( SIZE ( 0..16 ) )
        MAX-ACCESS read-only
        STATUS current
        DESCRIPTION
                "An array of octets indicating the latest events which
                happened in this LU. Octet 1 is the most recent event,
                octet 2 the next most recent and so on. Although
                the maximum number of events kept is 16, the actual
                number of events kept may be lower than that. When more
                events are generated than are kept, the oldest ones are
                discarded.

                Events are encoded as:
                1  inactivity timer expired.
                2  dynamic timer expired,
                3  actlu from host
                4  bind  from host
                5  clear from host
                6  dactlu from host
                7  hierarchical reset from PU (warn actpu)
                8  sdt from host
                9  unbind from host
                10 notify response from host
                11 Reply psid negative response from host
                12 Reply psid pos response from host
                13 unbind response from host
                14 hierarchical reset from pu
                15 connect from client
                16 disconnect from client
                17 timing-mark response from client
                18 flow control timer expired
                19 negative response to host
                20 negative response from host
                21 data contention happened
                22 no buffer to send response
                23 receive a sna response while inbound
                "
        ::= { tn3270sLuEntry 16 }

tn3270sLuNail OBJECT-TYPE
        SYNTAX TruthValue
        MAX-ACCESS read-only
        STATUS current
        DESCRIPTION
                "This variable indicates whether this LU has been
                configured (Nailed) for a specific TN3270 client.
                TRUE  -> LU is nailed to the client IP address
                FALSE -> LU is not nailed to the client IP address
                "
        ::= { tn3270sLuEntry 17 }

--  *************************************************************
--  *                                                           *
--  *           TN3270 Server -  LU Nail Mapping                *
--  *                                                           *
--  *************************************************************
tn3270sPuNailTable OBJECT-TYPE
        SYNTAX  SEQUENCE OF Tn3270sPuNailEntry
        MAX-ACCESS  not-accessible
        STATUS  current
        DESCRIPTION
                "A list of reserved LUs and their associated IP
                addresses is represented here for the containing
                PU. Each LU is configured for a specific client
                IP address. This association between the LU and
                the client IP Address is called nailing. The client
                is said to be nailed to its LU and visa-versa.

                If the client IP address is known but the PU index
                is not known, a more efficient way to access
                this info is via tn3270sIpNailTable.
                "
        ::= { tn3270sPuNail 1 }

tn3270sPuNailEntry OBJECT-TYPE
        SYNTAX  Tn3270sPuNailEntry
        MAX-ACCESS  not-accessible
        STATUS  current
        DESCRIPTION
                "A list of entries to relate a PU to nailed
                clients.This table contains the same info as
                tn3270sIpNailTable. The indices are ordered to
                facilitate access to the information when the
                PU index is known but not the client IP address.
                This is necessitated due to the potentially large
                number of rows in the table.
                "
        INDEX { tn3270sIndex, tn3270sPuIndex, tn3270sPuNailClientIpAddr,
                tn3270sPuNailLuFirst }
        ::= { tn3270sPuNailTable 1 }

Tn3270sPuNailEntry ::= SEQUENCE {
        tn3270sPuNailClientIpAddr   IpAddress,
        tn3270sPuNailClientIpMask   IpAddress,
        tn3270sPuNailType           INTEGER,
        tn3270sPuNailLuFirst        INTEGER,
        tn3270sPuNailLuLast         INTEGER
}

tn3270sPuNailClientIpAddr OBJECT-TYPE
        SYNTAX IpAddress
        MAX-ACCESS read-only
        STATUS current
        DESCRIPTION
                "The IP address of the nailed TN3270 client."
        ::= { tn3270sPuNailEntry 1 }

tn3270sPuNailClientIpMask OBJECT-TYPE
        SYNTAX IpAddress
        MAX-ACCESS read-only
        STATUS current
        DESCRIPTION
                "The subnet mask of the nailed TN3270 client."
        ::= { tn3270sPuNailEntry 2 }

tn3270sPuNailType OBJECT-TYPE
        SYNTAX INTEGER { screen(1), printer(2) }
        MAX-ACCESS read-only
        STATUS current
        DESCRIPTION
                "The nailing type configured for the range of LUs 
                within this PU is either screen or printer.  
                screen -  The range of LUs will only be connected to
                          TN3270 clients with a device type which is 
                          not 328*.  If an LU is statically configured
                          at the host, then it should be configured
                          with a screen DLOGMOD definition.
                printer - The range of LUs will only be connected to 
                          TN3270
                          clients with device type which is 328*.
                          If an LU is statically configured at the
                          host, then it should be configured with
                          a printer DLOGMOD definition. 
                "
        ::= { tn3270sPuNailEntry 3 }

tn3270sPuNailLuFirst OBJECT-TYPE
        SYNTAX INTEGER ( 1..255 )
        MAX-ACCESS read-only
        STATUS current
        DESCRIPTION
                "The first LU in this range nailed to this client ip
                address."
        ::= { tn3270sPuNailEntry 4 }

tn3270sPuNailLuLast OBJECT-TYPE
        SYNTAX INTEGER( 1..255 )
        MAX-ACCESS read-only
        STATUS current
        DESCRIPTION
                "The last LU in this range nailed to this client ip
                address."
        ::= { tn3270sPuNailEntry 5 }

--  *************************************************************
--  *                                                           *
--  *           TN3270 Server -  LU Nail Mapping                *
--  *                                                           *
--  *************************************************************
tn3270sIpNailTable OBJECT-TYPE
        SYNTAX  SEQUENCE OF Tn3270sIpNailEntry
        MAX-ACCESS  not-accessible
        STATUS  current
        DESCRIPTION
                "A list of reserved LUs and their associated IP
                addresses is represented here for the containing
                PU. Each LU is configured for a specific client
                IP address. This association between the LU and
                the client IP Address is called nailing. The client
                is said to be nailed to its LU and visa-versa.

                If the PU index is known but the client IP address
                is not known, a more efficient way to access
                this info is via tn3270sPuNailTable.
                "
        ::= { tn3270sIpNail 1 }

tn3270sIpNailEntry OBJECT-TYPE
        SYNTAX  Tn3270sIpNailEntry
        MAX-ACCESS  not-accessible
        STATUS  current
        DESCRIPTION
                "A list of entries to relate a PU to nailed
                clients. This table contains the same info as
                tn3270sPuNailTable. The indices are ordered to
                facilitate access to the info when the client
                IP address is known but not the PU index.
                This is necessitated due to the potentially large
                number of rows in the table.
                "
        INDEX { tn3270sIndex, tn3270sIpNailClientIpAddr,
                tn3270sPuIndex, tn3270sIpNailLuFirst }
        ::= { tn3270sIpNailTable 1 }

Tn3270sIpNailEntry ::= SEQUENCE {
        tn3270sIpNailClientIpAddr   IpAddress,
        tn3270sIpNailClientIpMask   IpAddress,
        tn3270sIpNailType           INTEGER,
        tn3270sIpNailLuFirst        INTEGER,
        tn3270sIpNailLuLast         INTEGER
}

tn3270sIpNailClientIpAddr OBJECT-TYPE
        SYNTAX IpAddress
        MAX-ACCESS read-only
        STATUS current
        DESCRIPTION
                "The IP address of the nailed TN3270 client."
        ::= { tn3270sIpNailEntry 1 }

tn3270sIpNailClientIpMask OBJECT-TYPE
        SYNTAX IpAddress
        MAX-ACCESS read-only
        STATUS current
        DESCRIPTION
                "The subnet mask of the nailed TN3270 client."
        ::= { tn3270sIpNailEntry 2 }

tn3270sIpNailType OBJECT-TYPE
        SYNTAX INTEGER { screen(1), printer(2) }
        MAX-ACCESS read-only
        STATUS current
        DESCRIPTION
                "The nailing type configured for the range of LUs 
                 within this PU is either screen or printer.  
                 screen -  The range of LUs will only be connected to
                           TN3270 clients with a device type which is
                           not 328*.  If an LU is statically configured
                           at the host, then it should be configured
                           with a screen DLOGMOD definition.
                 printer - The range of LUs will only be connected to
                           TN3270 clients with device type which is 328*.
                           If an LU is statically configured at the
                           host, then it should be configured with
                           a printer DLOGMOD definition. 
                "
        ::= { tn3270sIpNailEntry 3 }

tn3270sIpNailLuFirst OBJECT-TYPE
        SYNTAX INTEGER( 1..255 )
        MAX-ACCESS read-only
        STATUS current
        DESCRIPTION
                "The first LU in this range nailed to this client ip
                address."
        ::= { tn3270sIpNailEntry 4 }

tn3270sIpNailLuLast OBJECT-TYPE
        SYNTAX INTEGER( 1..255 )
        MAX-ACCESS read-only
        STATUS current
        DESCRIPTION
                "The last LU in this range nailed to this client ip
                address."
        ::= { tn3270sIpNailEntry 5 }

-- Notifications
ciscoTn3270ServerMIBNotificationPrefix OBJECT IDENTIFIER ::= { ciscoTn3270ServerMIB 2 }
--   No notifications currently defined.

-- conformance information

ciscoTn3270ServerMIBConformance OBJECT IDENTIFIER ::= { ciscoTn3270ServerMIB 3 }
ciscoTn3270ServerMIBCompliances OBJECT IDENTIFIER ::= { ciscoTn3270ServerMIBConformance 1 }
ciscoTn3270ServerMIBGroups      OBJECT IDENTIFIER ::= { ciscoTn3270ServerMIBConformance 2 }

-- compliance statements

ciscoTn3270ServerMIBCompliance MODULE-COMPLIANCE
        STATUS  current
        DESCRIPTION
                "The compliance statement for entities which implement
                 the Cisco Tn3270s MIB"
        MODULE  -- this module
           MANDATORY-GROUPS { ciscoTn3270ServerMIBGroup }
        ::= { ciscoTn3270ServerMIBCompliances 1 }

-- units of conformance

ciscoTn3270ServerMIBGroup OBJECT-GROUP
        OBJECTS {
                tn3270sCpuCard,
                tn3270sMaxLus,
                tn3270sLusInUse,
                tn3270sStartupTime,
                tn3270sGlobalTcpPort,
                tn3270sGlobalIdleTimeout,
                tn3270sGlobalKeepAlive,
                tn3270sGlobalUnbindAction,
                tn3270sGlobalGenericPool,
                tn3270sTimingMarkSupported,
                tn3270sRunningTime,
                tn3270sStatsMaxSess,
                tn3270sStatsSpareSess,
                tn3270sStatsConnectsIn,
                tn3270sStatsDisconnects,
                tn3270sStatsTN3270ConnectsFailed,
                tn3270sStatsInboundChains,
                tn3270sStatsOutboundChains,
                tn3270sStatsSampledHostResponses,
                tn3270sStatsNetSampledHostResponseTime,
                tn3270sStatsSampledClientResponses,
                tn3270sStatsNetSampledClientResponseTime,
                tn3270sPuIpAddr,
                tn3270sPuTcpPort,
                tn3270sPuIdleTimeout,
                tn3270sPuKeepAlive,
                tn3270sPuUnbindAction,
                tn3270sPuGenericPool,
                tn3270sPuState,
                tn3270sPuType,
                tn3270sPuLuSeed,
                tn3270sLocalSapAddress,
                tn3270sRemoteSapAddress,
                tn3270sRemoteMacAddress,
                tn3270sIpPuIndex,
                tn3270sIpLuIndex,
                tn3270sLuClientAddr,
                tn3270sLuClientTcpPort,
                tn3270sLuTelnetType,
                tn3270sLuTermModel,
                tn3270sLuState,
                tn3270sLuCurInbPacing,
                tn3270sLuCurInbQsize,
                tn3270sLuCurOutQsize,
                tn3270sLuIdleTime,
                tn3270sLuType,
                tn3270sLuAppnLinkIndex,
                tn3270sLuLfsid,
                tn3270sLuEvents
        }
        STATUS  current
        DESCRIPTION
                "A collection of objects providing Tn3270 ability to a
                Cisco agent."
        ::= { ciscoTn3270ServerMIBGroups 1 }

ciscoTn3270ServerMIBComplianceObsolete MODULE-COMPLIANCE
        STATUS  obsolete
        DESCRIPTION
                "The compliance statement for obsolete entities."
        MODULE  -- this module
           GROUP ciscoTn3270ServerMIBGroupObsolete
           DESCRIPTION "list of obsolete objects."
        ::= { ciscoTn3270ServerMIBCompliances 2 }

ciscoTn3270ServerMIBGroupObsolete OBJECT-GROUP
        OBJECTS {
                tn3270sLuLastEvent
        }
        STATUS  obsolete
        DESCRIPTION
                "A collection of objects providing Tn3270 ability to a
                Cisco agent."
        ::= { ciscoTn3270ServerMIBGroups 2 }

ciscoTn3270ServerMIBComplianceRev1 MODULE-COMPLIANCE
        STATUS  current
        DESCRIPTION
                "The compliance statement for the TN3270 Server."
        MODULE  -- this module
           MANDATORY-GROUPS { ciscoTn3270ServerMIBGroup,
                              ciscoTn3270ServerMIBGroupRev1 }
        ::= { ciscoTn3270ServerMIBCompliances 3 }

ciscoTn3270ServerMIBGroupRev1 OBJECT-GROUP
        OBJECTS {
                -- IP precedence objects
                tn3270sPuIpPrecedenceScreen,
                tn3270sPuIpPrecedencePrinter,
                tn3270sPuIpTosScreen,
                tn3270sPuIpTosPrinter,
                -- Nail objects
                tn3270sLuNail,
                -- tn3270sPuNailTable
                tn3270sPuNailClientIpAddr,
                tn3270sPuNailClientIpMask,
                tn3270sPuNailType,
                tn3270sPuNailLuFirst,
                tn3270sPuNailLuLast,
                -- tn3270sIpNailTable
                tn3270sIpNailClientIpAddr,
                tn3270sIpNailClientIpMask,
                tn3270sIpNailType,
                tn3270sIpNailLuFirst,
                tn3270sIpNailLuLast
        }
        STATUS  current
        DESCRIPTION
                "A collection of objects providing LU nailing and IP
                 precedence features."
        ::= { ciscoTn3270ServerMIBGroups 3 }

END
