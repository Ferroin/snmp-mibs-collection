CISCO-SSG-CAPABILITY DEFINITIONS ::= BEGIN

IMPORTS
        MODULE-IDENTITY
                FROM SNMPv2-SMI
        AGENT-CAPABILITIES
                FROM SNMPv2-CONF
        ciscoAgentCapability
                FROM CISCO-SMI;

ciscoSsgCapability MODULE-IDENTITY
        LAST-UPDATED    "200408130000Z"
        ORGANIZATION    "Cisco Systems, Inc."
        CONTACT-INFO
                "       Cisco Systems
                        Customer Service

                Postal: 170 W Tasman Drive
                        San Jose, CA  95134
                        USA

                   Tel: +1 800 553-NETS

                E-mail: cs-ssg@cisco.com"
        DESCRIPTION
                "This is the Agent Capability MIB for
                 CISCO-SSG-MIB."
        REVISION        "200408130000Z"
        DESCRIPTION
                "Initial version of this MIB module."
        ::= { ciscoAgentCapability 1500 }

ciscoSsgCapabilityV12R03RevT AGENT-CAPABILITIES

        PRODUCT-RELEASE  "Cisco IOS 12.3T"
        STATUS           current
        DESCRIPTION      "CISCO-SSG-MIB capabilities"
        SUPPORTS         CISCO-SSG-MIB
        INCLUDES         {
                           ciscoSsgCfgGroupRev1,
                           ciscoSsgExclusionsGroup,
                           ciscoSsgTcpRedirectGroup,
                           ciscoSsgServiceInterfaceGroup,
                           ciscoSsgRadiusClientsGroup,
                           ciscoSsgPortMapGroup
                         }

        VARIATION        cssgCfgSsgEnabled
        ACCESS           read-only
        DESCRIPTION      "Write access is not supported."

        VARIATION        cssgCfgAutoDomainMode
        ACCESS           read-only
        DESCRIPTION      "Write access is not supported."

        VARIATION        cssgCfgLocalForwardingEnabled
        ACCESS           read-only
        DESCRIPTION      "Write access is not supported."

        VARIATION        cssgCfgAutoLogOffMode
        ACCESS           read-only
        DESCRIPTION      "Write access is not supported."

        VARIATION        cssgCfgRadiusProxyEnabled
        ACCESS           read-only
        DESCRIPTION      "Write access is not supported."

        VARIATION        cssgCfgTcpRedirectEnabled
        ACCESS           read-only
        DESCRIPTION      "Write access is not supported."

        VARIATION        cssgCfgAutoDomainNatEnabled
        ACCESS           read-only
        DESCRIPTION      "Write access is not supported."

        VARIATION        cssgCfgPortBundleHostKeyEnabled
        ACCESS           read-only
        DESCRIPTION      "Write access is not supported."

        VARIATION        cssgCfgTransPassThroughEnabled
        ACCESS           read-only
        DESCRIPTION      "Write access is not supported."

        VARIATION        cssgCfgAutoLogOffInterval
        ACCESS           read-only
        DESCRIPTION      "Write access is not supported."

        VARIATION        cssgCfgAutoLogOffIcmpRetries
        ACCESS           read-only
        DESCRIPTION      "Write access is not supported."

        VARIATION        cssgCfgMaxServicesPerUser
        ACCESS           read-only
        DESCRIPTION      "Write access is not supported."

        VARIATION        cssgCfgAccountingEnabled
        ACCESS           read-only
        DESCRIPTION      "Write access is not supported."

        VARIATION        cssgCfgDefaultNetworkType
        ACCESS           read-only
        DESCRIPTION      "Write access is not supported."

        VARIATION        cssgCfgDefaultNetwork
        ACCESS           read-only
        DESCRIPTION      "Write access is not supported."

        VARIATION        cssgCfgRadiusAuthenPort
        ACCESS           read-only
        DESCRIPTION      "Write access is not supported."

        VARIATION        cssgCfgRadiusAccountingPort
        ACCESS           read-only
        DESCRIPTION      "Write access is not supported."

        VARIATION        cssgCfgRadiusFwdAcctPktsEnabled
        ACCESS           read-only
        DESCRIPTION      "Write access is not supported."

        VARIATION        cssgCfgAccountingInterval
        ACCESS           read-only
        DESCRIPTION      "Write access is not supported."

        VARIATION        cssgCfgTCPRedirGrpForUnAuthUsers
        ACCESS           read-only
        DESCRIPTION      "Write access is not supported."

        VARIATION        cssgCfgTCPRedirGrpForUnAuthServ
        ACCESS           read-only
        DESCRIPTION      "Write access is not supported."

        VARIATION        cssgCfgTcpRedirGrpForSMTP
        ACCESS           read-only
        DESCRIPTION      "Write access is not supported."

        VARIATION        cssgCfgTcpRedirGrpForInitialCapt
        ACCESS           read-only
        DESCRIPTION      "Write access is not supported."

        VARIATION        cssgCfgTcpRedirGrpForAdvCapt
        ACCESS           read-only
        DESCRIPTION      "Write access is not supported."

        VARIATION        cssgCfgTalEnabled
        ACCESS           read-only
        DESCRIPTION      "Write access is not supported."

        VARIATION        cssgExcludedAPNRowStatus
        ACCESS           read-only
        DESCRIPTION      "Create row is not supported."

        VARIATION        cssgExcludedDomainRowStatus
        ACCESS           read-only
        DESCRIPTION      "Create row is not supported."

        VARIATION        cssgTcpRedirectGrpRowStatus
        ACCESS           read-only
        DESCRIPTION      "Create row is not supported."

        VARIATION        cssgNetworkGrpNetRowStatus
        ACCESS           read-only
        DESCRIPTION      "Create row is not supported."

        VARIATION        cssgPortGrpPortRowStatus
        ACCESS           read-only
        DESCRIPTION      "Create row is not supported."

        VARIATION        cssgTcpRedirNetworkMapGrpName
        ACCESS           read-only
        DESCRIPTION      "Write/create access is not supported."

        VARIATION        cssgTcpRedirNetworkGrpMapRowStat
        ACCESS           read-only
        DESCRIPTION      "Write/create access is not supported."

        VARIATION        cssgTcpRedirPortMapGrpName
        ACCESS           read-only
        DESCRIPTION      "Write/create access is not supported."

        VARIATION        cssgTcpRedirPortGrpMapRowStat
        ACCESS           read-only
        DESCRIPTION      "Write/create access is not supported."

        VARIATION        cssgTcpRedirPortNo
        ACCESS           read-only
        DESCRIPTION      "Write/create access is not supported."

        VARIATION        cssgTcpRedirPortNoMapRowStat
        ACCESS           read-only
        DESCRIPTION      "Write/create access is not supported."

        VARIATION        cssgServiceIfIndex
        ACCESS           read-only
        DESCRIPTION      "Write/create access is not supported."

        VARIATION        cssgServiceIfRowStatus
        ACCESS           read-only
        DESCRIPTION      "Write/create access is not supported."

        VARIATION        cssgRadiusClientRowStatus
        ACCESS           read-only
        DESCRIPTION      "Write/create access is not supported."

        VARIATION        cssgPortMapLength
        ACCESS           read-only
        DESCRIPTION      "Write access is not supported."

        VARIATION        cssgPortMapPortRangeFrom
        ACCESS           read-only
        DESCRIPTION      "Write/create access is not supported."

        VARIATION        cssgPortMapPortRangeTo
        ACCESS           read-only
        DESCRIPTION      "Write/create access is not supported."

        VARIATION        cssgPortMapRowStatus
        ACCESS           read-only
        DESCRIPTION      "Write/create access is not supported."
        ::= { ciscoSsgCapability 1 }
END
