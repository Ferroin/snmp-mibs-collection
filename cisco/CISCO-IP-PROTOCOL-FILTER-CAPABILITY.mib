CISCO-IP-PROTOCOL-FILTER-CAPABILITY DEFINITIONS ::= BEGIN

IMPORTS
    MODULE-IDENTITY
        FROM SNMPv2-SMI
    AGENT-CAPABILITIES
        FROM SNMPv2-CONF
    ciscoAgentCapability
        FROM CISCO-SMI;

ciscoIpProtFilterCapability MODULE-IDENTITY
    LAST-UPDATED    "200806090000Z"
    ORGANIZATION    "Cisco Systems, Inc."
    CONTACT-INFO
            "Cisco Systems
            Customer Service

            Postal: 170 West Tasman Drive
            San Jose, CA  95134
            USA

            Tel: +1 800 553-NETS

            E-mail: cs-dot11@cisco.com"
    DESCRIPTION
        "The capabilities description for
        CISCO-IP-PROTOCOL-FILTER-MIB."
    REVISION        "200806090000Z"
    DESCRIPTION
        "Added capability statement
        cIpProtFilterCapc4710aceVA1R700 for ACE 4710 
        Application Control Engine Appliance."
    REVISION        "200604190000Z"
    DESCRIPTION
        "Added capability statement
        cIpProtFilterCapACSWV03R000 
        for Application Control Engine (ACE)."
    ::= { ciscoAgentCapability 500 }

cIpProtFilterCapACSWV03R000 AGENT-CAPABILITIES
    PRODUCT-RELEASE "ACSW (Application Control Software) 3.0"
    STATUS          current
    DESCRIPTION
        "CISCO-IP-PROTOCOL-FILTER-MIB capabilities."

    SUPPORTS        CISCO-IP-PROTOCOL-FILTER-MIB
    INCLUDES        {
                        ciscoIpProtocolFilteringGroup,
                        ciscoIpProtocolFilterGroup2,
                        ciscoIpProtocolFilterExtGroup,
                        ciscoIpProtocolFilterStatsGroup
                    }
    VARIATION       cippfIpProfileType
    ACCESS          read-only
    DESCRIPTION
        "Create operation not allowed."

    VARIATION       cippfIpProfileStatus
    ACCESS          read-only
    DESCRIPTION
        "Create operation not allowed."

    VARIATION       cippfIfIpProfileName
    ACCESS          read-only
    DESCRIPTION
        "Create operation not allowed."

    VARIATION       cippfIfIpProfileStatus
    ACCESS          read-only
    DESCRIPTION
        "Create operation not allowed."

    VARIATION       cippfIpFilterOrderPosition
    ACCESS          read-only
    DESCRIPTION
        "Create operation not allowed."

    VARIATION       cippfIpFilterAction
    ACCESS          read-only
    DESCRIPTION
        "Create operation not allowed."

    VARIATION       cippfIpFilterAddressType
    ACCESS          read-only
    DESCRIPTION
        "Create operation not allowed."

    VARIATION       cippfIpFilterSrcAddress
    ACCESS          read-only
    DESCRIPTION
        "Create operation not allowed."

    VARIATION       cippfIpFilterSrcMask
    ACCESS          read-only
    DESCRIPTION
        "Create operation not allowed."

    VARIATION       cippfIpFilterDestAddress
    ACCESS          read-only
    DESCRIPTION
        "Create operation not allowed."

    VARIATION       cippfIpFilterDestMask
    ACCESS          read-only
    DESCRIPTION
        "Create operation not allowed."

    VARIATION       cippfIpFilterProtocol
    ACCESS          read-only
    DESCRIPTION
        "Create operation not allowed."

    VARIATION       cippfIpFilterSrcPortLow
    ACCESS          read-only
    DESCRIPTION
        "Create operation not allowed."

    VARIATION       cippfIpFilterSrcPortHigh
    ACCESS          read-only
    DESCRIPTION
        "Create operation not allowed."

    VARIATION       cippfIpFilterDestPortLow
    ACCESS          read-only
    DESCRIPTION
        "Create operation not allowed."

    VARIATION       cippfIpFilterDestPortHigh
    ACCESS          read-only
    DESCRIPTION
        "Create operation not allowed."

    VARIATION       cippfIpFilterPrecedence
    ACCESS          read-only
    DESCRIPTION
        "Create operation not allowed."

    VARIATION       cippfIpFilterTos
    ACCESS          read-only
    DESCRIPTION
        "Create operation not allowed."

    VARIATION       cippfIpFilterLogEnabled
    ACCESS          read-only
    DESCRIPTION
        "Create operation not allowed."

    VARIATION       cippfIpFilterStatus
    ACCESS          read-only
    DESCRIPTION
        "Create operation not allowed."

    VARIATION       cippfIpFilterICMPType
    ACCESS          read-only
    DESCRIPTION
        "Create operation not allowed."

    VARIATION       cippfIpFilterTCPEstablished
    ACCESS          read-only
    DESCRIPTION
        "Create operation not allowed."

    VARIATION       cippfIpFilterFragments
    ACCESS          read-only
    DESCRIPTION
        "Create operation not allowed."

    VARIATION       cippfIpFilterICMPCode
    ACCESS          read-only
    DESCRIPTION
        "Create operation not allowed."

    VARIATION       cippfIpFilterExtDescription
    ACCESS          read-only
    DESCRIPTION
        "Create operation not allowed."

    VARIATION       cippfIpFilterExtLogLevel
    ACCESS          read-only
    DESCRIPTION
        "Create operation not allowed."

    VARIATION       cippfIpFilterExtLogInterval
    ACCESS          read-only
    DESCRIPTION
        "Create operation not allowed."
    ::= { ciscoIpProtFilterCapability 1 }

cIpProtFilterCapc4710aceVA1R700 AGENT-CAPABILITIES
    PRODUCT-RELEASE "ACSW (Application Control Software) A1(7)
                  for ACE 4710 Application Control Engine 
                  Appliance."
    STATUS          current
    DESCRIPTION
        "CISCO-IP-PROTOCOL-FILTER-MIB capabilities."

    SUPPORTS        CISCO-IP-PROTOCOL-FILTER-MIB
    INCLUDES        {
                        ciscoIpProtocolFilteringGroup,
                        ciscoIpProtocolFilterGroup2,
                        ciscoIpProtocolFilterExtGroup,
                        ciscoIpProtocolFilterStatsGroup
                    }
    VARIATION       cippfIpProfileType
    ACCESS          read-only
    DESCRIPTION
        "Create operation not allowed."

    VARIATION       cippfIpProfileStatus
    ACCESS          read-only
    DESCRIPTION
        "Create operation not allowed."

    VARIATION       cippfIfIpProfileName
    ACCESS          read-only
    DESCRIPTION
        "Create operation not allowed."

    VARIATION       cippfIfIpProfileStatus
    ACCESS          read-only
    DESCRIPTION
        "Create operation not allowed."

    VARIATION       cippfIpFilterOrderPosition
    ACCESS          read-only
    DESCRIPTION
        "Create operation not allowed."

    VARIATION       cippfIpFilterAction
    ACCESS          read-only
    DESCRIPTION
        "Create operation not allowed."

    VARIATION       cippfIpFilterAddressType
    ACCESS          read-only
    DESCRIPTION
        "Create operation not allowed."

    VARIATION       cippfIpFilterSrcAddress
    ACCESS          read-only
    DESCRIPTION
        "Create operation not allowed."

    VARIATION       cippfIpFilterSrcMask
    ACCESS          read-only
    DESCRIPTION
        "Create operation not allowed."

    VARIATION       cippfIpFilterDestAddress
    ACCESS          read-only
    DESCRIPTION
        "Create operation not allowed."

    VARIATION       cippfIpFilterDestMask
    ACCESS          read-only
    DESCRIPTION
        "Create operation not allowed."

    VARIATION       cippfIpFilterProtocol
    ACCESS          read-only
    DESCRIPTION
        "Create operation not allowed."

    VARIATION       cippfIpFilterSrcPortLow
    ACCESS          read-only
    DESCRIPTION
        "Create operation not allowed."

    VARIATION       cippfIpFilterSrcPortHigh
    ACCESS          read-only
    DESCRIPTION
        "Create operation not allowed."

    VARIATION       cippfIpFilterDestPortLow
    ACCESS          read-only
    DESCRIPTION
        "Create operation not allowed."

    VARIATION       cippfIpFilterDestPortHigh
    ACCESS          read-only
    DESCRIPTION
        "Create operation not allowed."

    VARIATION       cippfIpFilterPrecedence
    ACCESS          read-only
    DESCRIPTION
        "Create operation not allowed."

    VARIATION       cippfIpFilterTos
    ACCESS          read-only
    DESCRIPTION
        "Create operation not allowed."

    VARIATION       cippfIpFilterLogEnabled
    ACCESS          read-only
    DESCRIPTION
        "Create operation not allowed."

    VARIATION       cippfIpFilterStatus
    ACCESS          read-only
    DESCRIPTION
        "Create operation not allowed."

    VARIATION       cippfIpFilterICMPType
    ACCESS          read-only
    DESCRIPTION
        "Create operation not allowed."

    VARIATION       cippfIpFilterTCPEstablished
    ACCESS          read-only
    DESCRIPTION
        "Create operation not allowed."

    VARIATION       cippfIpFilterFragments
    ACCESS          read-only
    DESCRIPTION
        "Create operation not allowed."

    VARIATION       cippfIpFilterICMPCode
    ACCESS          read-only
    DESCRIPTION
        "Create operation not allowed."

    VARIATION       cippfIpFilterExtDescription
    ACCESS          read-only
    DESCRIPTION
        "Create operation not allowed."

    VARIATION       cippfIpFilterExtLogLevel
    ACCESS          read-only
    DESCRIPTION
        "Create operation not allowed."

    VARIATION       cippfIpFilterExtLogInterval
    ACCESS          read-only
    DESCRIPTION
        "Create operation not allowed."
    ::= { ciscoIpProtFilterCapability 2 }

END
