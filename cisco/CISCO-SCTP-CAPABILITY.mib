CISCO-SCTP-CAPABILITY DEFINITIONS ::= BEGIN

IMPORTS
        MODULE-IDENTITY
                FROM SNMPv2-SMI
        AGENT-CAPABILITIES
                FROM SNMPv2-CONF
        ciscoAgentCapability
                FROM CISCO-SMI;

ceSctpCapability MODULE-IDENTITY
                LAST-UPDATED    "200106050000Z"
                ORGANIZATION    "Cisco Systems, Inc."
                CONTACT-INFO
                        "       Cisco Systems
                                Customer Service

                        Postal: 170 West Tasman Drive
                                San Jose, CA  95134
                                USA

                           Tel: +1 800 553-NETS

                        E-mail: tac@cisco.com"
                DESCRIPTION
                        "Agent capabilities for the CISCO-SCTP-MIB."
                REVISION        "200106050000Z"
                DESCRIPTION
                        "Initial version of this MIB module."
        ::= { ciscoAgentCapability 190 }

ceSctpCapabilityV12R021MB1 AGENT-CAPABILITIES

PRODUCT-RELEASE "Cisco IOS 12.2(1)MB1"
  STATUS          current
  DESCRIPTION     "IOS 12.2(1)MB1 Cisco CISCO-SCTP-MIB.my User Agent
                   MIB capabilities."

SUPPORTS        CISCO-SCTP-MIB
  INCLUDES      { ceSctpGeneralVariablesGroup,    
                  ceSctpStateStatGroup,           
                  ceSctpOtherStatGroup,           
                  ceSctpAssocTablesVariablesGroup,
                  ceSctpAssocStatGroup }           
::= { ceSctpCapability 1 }

END
