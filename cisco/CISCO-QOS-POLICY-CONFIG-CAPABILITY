CISCO-QOS-POLICY-CONFIG-CAPABILITY DEFINITIONS ::= BEGIN
IMPORTS
        MODULE-IDENTITY
                FROM SNMPv2-SMI
        AGENT-CAPABILITIES
                FROM SNMPv2-CONF
        ciscoAgentCapability
                FROM CISCO-SMI;   

ciscoQosPolicyConfigCapability MODULE-IDENTITY
        LAST-UPDATED    "200706280000Z"
        ORGANIZATION    "Cisco Systems, Inc."
        CONTACT-INFO
                "       Cisco Systems
                        Customer Service

                Postal: 170 W Tasman Drive
                        San Jose, CA  95134
                        USA

                        Tel: +1 800 553-NETS

                E-mail: cs-lan-switch-snmp@cisco.com"
        DESCRIPTION
                "The Agent capabilities for CISCO-QOS-POLICY-CONFIG-MIB"
        REVISION        "200706280000Z"
        DESCRIPTION
                "Add cqpcCapabilityV12R0233SXHPCat6k statement."
        REVISION        "200310200000Z"
        DESCRIPTION
                "Initial version of this MIB module."
        ::= { ciscoAgentCapability 363 }

cqpcCapabilityCatOSV08R0101Cat6k AGENT-CAPABILITIES
    PRODUCT-RELEASE  "Cisco CatOS 8.1(1) on Catalyst 6000/6500
                      and Cisco 7600 series devices."
    STATUS            current
    DESCRIPTION      "CISCO-QOS-POLICY-CONFIG-MIB capabilities."

    SUPPORTS         CISCO-QOS-POLICY-CONFIG-MIB
        INCLUDES     {
                          qosGlobalGroup,
                          qosPrGlobalGroup,
                          qosPrInterfaceGroup,
                          qosInterfaceCapabilityGroup,
                          qosCopsPolicyStatusGroup
                     }
    ::= { ciscoQosPolicyConfigCapability 1 }

cqpcCapabilityV12R0233SXHPCat6k AGENT-CAPABILITIES
    PRODUCT-RELEASE     "Cisco IOS 12.2(33)SXH on Catalyst 6000/6500
                         devices."
    STATUS              current
    DESCRIPTION         "CISCO-QOS-POLICY-CONFIG-MIB capabilities."

    SUPPORTS            CISCO-QOS-POLICY-CONFIG-MIB
        INCLUDES        { 
                          qosGlobalGroup,
                          qosInterfaceCapabilityGroup
                        }
    ::= { ciscoQosPolicyConfigCapability 2 }

END
