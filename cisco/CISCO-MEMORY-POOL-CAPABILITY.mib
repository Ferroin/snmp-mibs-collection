CISCO-MEMORY-POOL-CAPABILITY DEFINITIONS ::= BEGIN

IMPORTS
        MODULE-IDENTITY
                FROM SNMPv2-SMI
        AGENT-CAPABILITIES
                FROM SNMPv2-CONF
        ciscoAgentCapability
                FROM CISCO-SMI;

ciscoMemoryPoolCapability MODULE-IDENTITY
        LAST-UPDATED    "200605020000Z"
    ORGANIZATION    "Cisco Systems, Inc."
        CONTACT-INFO
                "       Cisco Systems
                        Customer Service

                Postal: 170 West Tasman Drive
                        San Jose, CA  95134
                        USA

                   Tel: +1 800 553-NETS

                E-mail: cs-lan-switch-snmp@cisco.com
                        cs-snmp@cisco.com"
        DESCRIPTION
                "The capabilities description of
                 CISCO-MEMORY-POOL-MIB."

        REVISION        "200605020000Z"
        DESCRIPTION
                "Corrected existing Agent Capability
                 for IOS XR release 2.0 CRS1"

    REVISION        "200510260000Z"
        DESCRIPTION
                "Added ciscoMemoryPoolCapabilityIOSXRV2R0CRS1
        agent capabilities for IOS XR release 2.0 CRS1"

    REVISION        "200308070000Z"
        DESCRIPTION
                "Initial version of this MIB module."
        ::= { ciscoAgentCapability 338 }

ciscoMemoryPoolCapCatOSV08R0101 AGENT-CAPABILITIES
    PRODUCT-RELEASE     "Cisco CatOS 8.1(1)."
    STATUS              current
    DESCRIPTION         "CISCO-MEMORY-POOL-MIB capabilities."

    SUPPORTS            CISCO-MEMORY-POOL-MIB
        INCLUDES        { ciscoMemoryPoolGroup,
                          ciscoMemoryPoolUtilizationGroup }
    ::= { ciscoMemoryPoolCapability 1 }

ciscoMemoryPoolCapabilityIOSXRV2R0CRS1 AGENT-CAPABILITIES
    PRODUCT-RELEASE     "Cisco IOS XR 2.0 for CRS-1"
    STATUS              current
    DESCRIPTION         "CISCO-MEMORY-POOL-MIB capabilities for 
            IOS XR release 2.0"

    SUPPORTS            CISCO-MEMORY-POOL-MIB
        INCLUDES        { ciscoMemoryPoolGroup }

    VARIATION           ciscoMemoryPoolAlternate
    ACCESS              not-implemented
    DESCRIPTION         "Not supported."

    VARIATION           ciscoMemoryPoolLargestFree
    ACCESS              not-implemented
    DESCRIPTION         "Not supported."   
    ::= { ciscoMemoryPoolCapability 2 }

END
