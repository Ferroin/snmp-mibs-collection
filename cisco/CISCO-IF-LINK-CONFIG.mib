CISCO-IF-LINK-CONFIG-MIB DEFINITIONS ::= BEGIN
IMPORTS
    MODULE-IDENTITY,
    OBJECT-TYPE
                        FROM SNMPv2-SMI
    RowStatus           FROM SNMPv2-TC
    MODULE-COMPLIANCE,
    OBJECT-GROUP        FROM SNMPv2-CONF
    InterfaceIndex      FROM IF-MIB
    CiscoLocationSpecifier   FROM CISCO-TC
    ciscoMgmt           FROM CISCO-SMI;

ciscoIfLinkConfigMIB MODULE-IDENTITY
    LAST-UPDATED   "200110050000Z"
    ORGANIZATION   "Cisco Systems, Inc."
    CONTACT-INFO
                    "Cisco Systems
                     Customer Service
                Postal: 170 W Tasman Drive
                    San Jose, CA  95134
                    USA
                    Tel: +1 800 553-NETS
                E-mail: cs-wanatm@cisco.com"
    DESCRIPTION
        "The MIB module for configuration of bulk distribution
         (de-multiplexing of traffic from higher-bandwidth to 
         lower-bandwidth interfaces).

         Terminology :

         bulk-distribution        : The bulk distribution is the 
                                    feature by which a line/interface
                                    on one module can replace the line
                                    for the other.

         bulk-distribution module : The module which links its 
                                    interfaces to the target module.

         target module            : A module that gets incoming traffic
                                    from a bulk distribution module 
                                    rather than from a back card.

         The Module which supports bulk distribution, converts 
         traffic from its lines (may be T3, OC-N) to lines on 
         the target module (may be
         T3, T1 etc). The bulk distribution is achieved by having a 
         point-to-point connection (bulk-distribution bus) between the 
         bulk-distribution module and the target module. The benefit 
         of bulk distribution is that the target module need not have
         the back cards. The lines/interfaces from bulk-distribution
         module will be used as lines for the target module.

         An example is given here on linking interfaces.

            |------------------------------------------------|
            |                                                |
            |             |------------------------------|   |
            |             |           |             |    |   |
            |             |           |-------------|    |   |
          Ta|rget Module  |           |             |    |   |
         -------       -------     -------     ---------------
         |     |       |     |     |     |     |              |
         |     |       |     |     |     |     |              |
         |  T1 |       | T1  |     |T1   |     | Bulk         |
         |card |       |card |     |card |     | Distribution |
         |     |       |     |     |     |     |              |
         |     |       |     |     |     |     | Module       |
         |     |       |     |     |     |     |              |
         |     |       |     |     |     |     | (T3 card)    |
         |     |       |     |     |     |     |              |
         -------       -------     -------      ---------------
         "
    REVISION        "200110050000Z"
    DESCRIPTION
        "Add object cilTargetModuleFramingType in cilConfTable table"
    REVISION        "200009140000Z"
    DESCRIPTION
       "Initial version of this MIB module"
    ::= { ciscoMgmt 175 }

cilConfigMIBObjects OBJECT IDENTIFIER ::= { ciscoIfLinkConfigMIB 1 }

cilConfig         OBJECT IDENTIFIER ::= { cilConfigMIBObjects 1 }

-- Interface Link configuration table

cilConfTable OBJECT-TYPE
    SYNTAX      SEQUENCE OF CilConfEntry
    MAX-ACCESS  not-accessible
    STATUS      current
    DESCRIPTION
        "The interface link configuration table."
    ::= { cilConfig 1 }

cilConfEntry OBJECT-TYPE
    SYNTAX     CilConfEntry
    MAX-ACCESS not-accessible
    STATUS     current
    DESCRIPTION
        "An entry in the cilConfTable. This entry is used for  
         linking an interface identified by cilSourceInterface
         to an interface identified by cilTaregetModuleInterface.
         The entries are created and deleted using the 
         cilRowStatus object. An interface on the bulk-distribution
         module cannot be linked to multiple interfaces in the
         target module."
    INDEX { cilSourceInterface }
    ::= { cilConfTable 1 }

CilConfEntry ::=
    SEQUENCE {
        cilSourceInterface       InterfaceIndex,
        cilTargetModuleInterface CiscoLocationSpecifier,
        cilRowStatus             RowStatus,
        cilTargetModuleFramingType   INTEGER
    }

cilSourceInterface OBJECT-TYPE
    SYNTAX     InterfaceIndex
    MAX-ACCESS not-accessible
    STATUS     current
    DESCRIPTION
        "An interface of the bulk-distribution module (Source) which
         will be linked with the interface of the target module. It
         represents an entry in the ifTable."
    ::= { cilConfEntry 1 }

cilTargetModuleInterface OBJECT-TYPE
    SYNTAX     CiscoLocationSpecifier
    MAX-ACCESS read-create
    STATUS     current
    DESCRIPTION
        "Location of the managed entity on the target module.
         Following is the supported  format for this object and
         all the values must be present.

         shelf=<value>, slot=<value>, subSlot=<value> port =<value>.

         The zero length value for this object is not supported."
    ::= { cilConfEntry 2 }

cilRowStatus OBJECT-TYPE
    SYNTAX     RowStatus
    MAX-ACCESS read-create
    STATUS     current
    DESCRIPTION
        "This object is used to create a new row or modify or delete
         an existing row in the table. The cilTargetModuleFramingType
         need not be specified to create a row. If cilTargetModuleFramingType
         is not specified, a default value will be assumed as described in the
         description of cilTargetModuleFramingType."
    ::= { cilConfEntry 3 }

cilTargetModuleFramingType OBJECT-TYPE
    SYNTAX    INTEGER {
                      notApplicable(1),
                      dsx1D4(2),
                      dsx1ESF(3)
                      } 
    MAX-ACCESS read-create
    STATUS     current
    DESCRIPTION
        "This object identifies the framing type of the target interface.
         notApplicable(1) can not be set.

             dsx1ESF         Extended SuperFrame DS1 (T1.107)
             dsx1D4          AT&T D4 format DS1 (T1.107)

         Default value is dsx1ESF(3) if cilTargetModuleInterface is a T1 interface 
         and sonet/sdh byte-synchronous mapping is used on the cilSourceInterface.
         Otherwise, the default value is notApplicable(1).
        "
    ::= { cilConfEntry 4 }

-- notifications

-- conformance information

cilConfigMIBConformance OBJECT IDENTIFIER ::= 
                { ciscoIfLinkConfigMIB 3 }

cilConfigMIBCompliances OBJECT IDENTIFIER ::= 
                { cilConfigMIBConformance 1 }

cilConfigMIBGroups  OBJECT IDENTIFIER ::= 
                { cilConfigMIBConformance 2 }

cilConfigMIBCompliance MODULE-COMPLIANCE
    STATUS deprecated 
    DESCRIPTION
       "The Compliance statement for interface link configuration group.
       This has been replaced by the cilConfigMIBComplianceRev1 statement."
    MODULE -- this module
    MANDATORY-GROUPS { cilConfMIBGroup }
    ::= { cilConfigMIBCompliances 1 }

cilConfigMIBComplianceRev1 MODULE-COMPLIANCE
    STATUS current
    DESCRIPTION
       "The Compliance statement for interface link configuration group.
        This statement replaces cilConfigMIBCompliance statement."
    MODULE -- this module
    MANDATORY-GROUPS { cilConfMIBGroupRev1 }

    OBJECT cilTargetModuleFramingType 
    MIN-ACCESS not-accessible
    DESCRIPTION
         "Required only for systems that support target interfaces
          whose types are T1 and whose source interfaces are
          sonet/sdh using byte-synchronous virtual tributary mapping."
    ::= { cilConfigMIBCompliances 2 }

-- units of conformance

cilConfMIBGroup OBJECT-GROUP
    OBJECTS {
        cilTargetModuleInterface,
        cilRowStatus
    }
    STATUS deprecated
    DESCRIPTION
        "These are objects related to interface link 
         configuration group. This group has been replaced
         by cilConfMIBGroupRev1."
    ::= { cilConfigMIBGroups 1}

cilConfMIBGroupRev1 OBJECT-GROUP
    OBJECTS {
        cilTargetModuleInterface,
        cilRowStatus,
        cilTargetModuleFramingType
    }
    STATUS current
    DESCRIPTION
        "These are objects related to interface link
         configuration group. This group replaces the
         cilConfMIBGroup."
    ::= { cilConfigMIBGroups 2}

END
