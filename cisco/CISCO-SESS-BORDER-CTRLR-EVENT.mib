CISCO-SESS-BORDER-CTRLR-EVENT-MIB DEFINITIONS ::= BEGIN

IMPORTS
    MODULE-IDENTITY,
    OBJECT-TYPE,
    NOTIFICATION-TYPE,
    Unsigned32,
    Integer32,
    Counter64,
    Gauge32,
    Counter32
        FROM SNMPv2-SMI
    MODULE-COMPLIANCE,
    NOTIFICATION-GROUP,
    OBJECT-GROUP
        FROM SNMPv2-CONF
    SnmpAdminString
        FROM SNMP-FRAMEWORK-MIB
    InetAddressType,
    InetAddress,
    InetPortNumber
        FROM INET-ADDRESS-MIB
    TEXTUAL-CONVENTION,
    TruthValue
        FROM SNMPv2-TC
    CiscoAlarmSeverity
        FROM CISCO-TC
    CiscoSbcPeriodicStatsInterval
        FROM CISCO-SESS-BORDER-CTRLR-CALL-STATS-MIB
    ciscoMgmt
        FROM CISCO-SMI;

ciscoSessBorderCtrlrEventMIB MODULE-IDENTITY
    LAST-UPDATED    "201012060000Z"
    ORGANIZATION    "Cisco Systems, Inc."
    CONTACT-INFO
            "Cisco Systems
            Customer Service
            Postal: 170 W Tasman Drive
            San Jose, CA  95134
            USA
            Tel: +1 800 553-NETS
            E-mail: sbc-dev@cisco.com"
    DESCRIPTION
        "The main purpose of this MIB is to define the SNMP
        notifications and alarms generated by Session Border Controller
        application and used to send these notifications to SNMP
        manager application. Each of these event/notification is
        explained in detail in the MIB file.

        The SBC service is implemented on a service card on CISCO
        routers. SBC application offer functionalities like
        firewall/NAT traversal, media bridging, policy-based call
        routing, signaling protocol inter-working, call billing and
        some degree of Call Admission Control. SBC looks to play an
        essential role in full-scale commercial deployment of VoIP and
        integration into the existing PSTN. 
        The Session Border Controller (SBC) enables direct IP-to-IP
        interconnect between multiple administrative domains for
        session-based services providing protocol inter-working,
        security, and admission control and management. The SBC is a
        voice over IP (VoIP) device that sits on the border
        of a network and controls call admission to that network.

        The primary purpose of an SBC is to protect the interior of 
        the network from excessive call load and malicious traffic.
        Additional functions provided by the SBC include media 
        bridging and billing services. 

        Various types of notifications required for SBC applications
        are
        as follows:
        1. When SIP/H2.48 calls are established and SBC application
        receives traffic (RTP/RTCP packets) from a source whose IP
        address or port is ambiguous, a source alert event is generated
        for the unwanted data packets received by SBC application.

        2. Blacklisting is the process of matching inbound packets based
        on some simple parameters (for example source IP address) and
        preventing packets that match those parameters from being
        processed. SBC detects an attempt to disrupt traffic flowing
        through it. When a source is blacklisted in SBC application, an
        event is generated to provide information of the blacklisted
        source like its IP address, port, VPN address etc.

        3. When there is a change in the state of any SBC service
        configured like a new SBC service is configured or the SBC card
        goes to standby state, reboot or offline state, a service is
        removed from SBC card, an event is generated by SBC.

        4. When a large number of SIP/H.248 calls are ongoing and 
        system is congested i.e. high CPU usage or high use of memory
        utilization, congestion event is generated at this point and
        when congestion is cleared means CPU usage comes to normal
        another event for congestion clear is generated.

        5. When a service is configured on SBC application, its call
        policies are defined during the configuration like maximum
        number of calls, maximum call rates etc. If any of these
        policies is violated, an event for violation of service level
        agreement is generated.

        6. When a radius server is attached/detached with SBC, a
        notification is generated to provide information of radius
        server type, IP address, port etc.

        7. When an adjacency is attached/detached with SBC, a
        notification is generated to provide its information like the
        adjacency type and state.

        8. When a H.248 controller is attached/detached with SBC to
        establish H.248 calls with SBC, a notification is generated to
        provide the information regarding the attached/detached H.248
        controller like controller index, IP address, port, state etc.

        GLOSSARY
        SBC: Session Border Controller

        CSB: CISCO Session Border Controller

        CAC: Call Admission Control - protects voice traffic from the
        negative effects of other voice traffic and to keep excess voice
        traffic off the network. It is used to prevent congestion in
        Voice traffic. It is used in the Call Setup phase.

        RTP: Real Time Transport Protocol - defines a standardized
        packet format for delivering audio and video over the Internet.

        RTCP: Real Time Control Protocol - It is a sister protocol of
        the Real-time Transport Protocol (RTP). RTCP provides
        out-of-band control information for an RTP flow. It partners RTP
        in the delivery and packaging of multimedia data, but does not
        transport any data itself. It is used periodically to transmit
        control packets to participants in a streaming multimedia
        session.

        VMG: Virtual Media Gateway - introduced to bridge between
        different transmission technologies and to add service to
        end-user connections. Its architecture separates control and
        connectivity functions into physically separate network layers.
        VPN: Virtual Private Network - It is a communications network
        tunneled through another network, and dedicated for a specific
        network.

        Gate Id - Context Identifiers assigned uniquely to a SIP/H.248
        call flows.

        Flow Pair Id: Stream Identifiers assigned uniquely to a
        SIP/H.248 call flows.

        Adjacency: An adjacency contains the system information to be
        transmitted to next HOP.

        SLA: Service Level Agreement - Service level agreement includes
        some call admission control policies which are defined during
        the SBC configurations like maximum number of calls, maximum
        call rates etc.

        Diameter Server: A Diameter Server is one that handles
        authentication, authorization and accounting requests for a
        particular realm.
        REFERENCES
        1. CISCO Session Border Controller Documents and FAQ
        http://zed.cisco.com/confluence/display/SBC/SBC"
    REVISION        "201012060000Z"
    DESCRIPTION
        "Added Notification csbQOSUnansweredCallRatioEvent,
        csbQOSUnansweredCallRatioClearEvent,
        csbQOSPercentPktLostEvent,
        csbQOSPercentPktLostClearEvent,
        csbQOSPercentPktDropEvent,
        csbQOSPercentPktDropClearEvent,
        csbQOSRoundTripDelayEvent,
        csbQOSRoundTripDelayClearEvent,
        csbQOSLocalJitterEvent,
        csbQOSLocalJitterClearEvent,
        csbQOSRemoteJitterEvent,
        csbQOSRemoteJitterClearEvent,
        csbQOSMoscqeEvent,
        csbQOSMoscqeClearEvent."
    REVISION        "200808270000Z"
    DESCRIPTION
        "Changes to correct problem were csbSLACurrentUsage and
        csbSLAPolicyLimit was incorrectly defined as Integer32.

        Deprecated the following objects and notification.
        csbSLACurrentUsage
        csbSLAPolicyLimit
        csbSLAViolationNotifEnabled
        csbSLAViolation

        Created the following objects and notification
        csbSLACurrentUsageRev1
        csbSLAPolicyLimitRev1
        csbSLAViolationNotifEnabledRev1
        csbSLAViolationRev1

        Correct definition of csbAlarmTime object."
    REVISION        "200805290000Z"
    DESCRIPTION
        "Initial version of the MIB module."
    ::= { ciscoMgmt 658 }

CsbQOSAlertScopeType ::= TEXTUAL-CONVENTION
    STATUS          current
    DESCRIPTION
        "This textual convention describes the scope to which value of
        QOS parameter is applicable. There are two scopes supported.
        QOS parameters can be reported for these two scopes global scope
         and adjacency scope. The values are:
        global - This scope represents the global level and does not
        corresponds to individual adjacency level scope.
        adjacency - This scope represents the QOS notifications
         for one particular adjacency."
    SYNTAX          INTEGER  {
                        global(1),
                        adjacency(2)
                    }

CsbDynamicBlackListedSrcSubFamily ::= TEXTUAL-CONVENTION
    STATUS          current
    DESCRIPTION
        "This textual convention represents the type of the source
        being blacklisted. Here source is the entity that sends the SIP
        call packets to SBC during a SIP call. The semantics are as
        follows.  
        blackVPN - Represents the VPN identifier of the blacklisted
        source.
        blackAddress - Represents the IP address of the blacklisted
        source.
        blackPort - Represents the port number of the blacklisted
        source."
    SYNTAX          INTEGER  {
                        blackVPN(1),
                        blackAddress(2),
                        blackPort(3)
                    }

CsbDynamicBlackListedTransPortType ::= TEXTUAL-CONVENTION
    STATUS          current
    DESCRIPTION
        "This textual convention describes the mode of the transport for
        the source that has been blacklisted.  The semantics are as
        follows:
        None - None is used if mode of transport of the packets
        being sent to SBC is not defined.
        UDP - This type is used when mode of transport of the
        packets being sent to SBC is UDP.
        TCP - This type is used when mode of transport the packets
        being sent to SBC is TCP."
    SYNTAX          INTEGER  {
                        none(1),
                        udp(2),
                        tcp(3)
                    }
-- This object contains different types of events/notifications which
-- can occur in SBC application and are needed to be informed.

ciscoSessBorderCtrlrMIBNotifs  OBJECT IDENTIFIER
    ::= { ciscoSessBorderCtrlrEventMIB 0 }

-- This object defines list of all parameters (or information) required
-- to be sent into different types of events/notifications which can
-- occur in SBC application.

ciscoSessBorderCtrlrMIBObjects  OBJECT IDENTIFIER
    ::= { ciscoSessBorderCtrlrEventMIB 1 }

-- This object defines the MIB compliance statement and the MIB
-- conformance groups in which different notification objects are
-- collected together.

ciscoSessBorderCtrlrMIBConform  OBJECT IDENTIFIER
    ::= { ciscoSessBorderCtrlrEventMIB 2 }

csbSourceAlertEvent NOTIFICATION-TYPE
    OBJECTS         {
                        csbAlarmSubsystem,
                        csbAlarmSeverity,
                        csbAlarmID,
                        csbAlarmTime,
                        csbSBCServiceName,
                        csbSrcAlertVdbeId,
                        csbSrcAlertGateId,
                        csbSrcAlertFlowPairId,
                        csbSrcAlertLocalAddressType,
                        csbSrcAlertLocalAddress,
                        csbSrcAlertLocalPort,
                        csbSrcAlertRemoteAddressType,
                        csbSrcAlertRemoteAddress,
                        csbSrcAlertRemotePort,
                        csbSrcAlertVpnId,
                        csbAlarmDescription
                    }
    STATUS          current
    DESCRIPTION
        "This notification is generated when after SIP/H.248 call
        establishment with one party, the media packets are received
        from some unexpected source/party (or some wrong/unexpected IP
        address).
        This is to alert that some unwanted data packets are received 
        by the system from an undesirable IP/port."
   ::= { ciscoSessBorderCtrlrMIBNotifs 1 }

csbDynamicBlackListEvent NOTIFICATION-TYPE
    OBJECTS         {
                        csbAlarmSubsystem,
                        csbAlarmSeverity,
                        csbAlarmID,
                        csbAlarmTime,
                        csbSBCServiceName,
                        csbDynamicBlackListSubFamily,
                        csbDynamicBlackListVpnId,
                        csbDynamicBlackListAddressType,
                        csbDynamicBlackListAddress,
                        csbDynamicBlackListTransportType,
                        csbDynamicBlackListPortNumber,
                        csbDynamicBlackListSrcBlocked,
                        csbAlarmDescription
                    }
    STATUS          current
    DESCRIPTION
        "This notification is generated when a source is added to or
        removed from the blacklist table. Dynamic blacklists put in
        place automatically (subject to a set of configurable
        constraints) by the SBC when it detects an attempt to disrupt
        traffic flowing through it. Dynamic blacklisting does not
        require management interference. Blacklist table is 
        restricted only to SBC service. This table is not made
        available to NM. For more Information on Dynamic Blacklisting
        refer to the following link:
        http://lbj.cisco.com/push_targets1/ucdit/cc/td/doc/product/ioxso

        ft/iox34/cgcr34/sbc_c34/sbc34dos.htm
        or 
        Search cisco.com using keywords 'DoS Prevention and Dynamic
        Blacklisting'."
   ::= { ciscoSessBorderCtrlrMIBNotifs 2 }

csbAdjacencyStatus NOTIFICATION-TYPE
    OBJECTS         {
                        csbAlarmSubsystem,
                        csbAlarmSeverity,
                        csbAlarmID,
                        csbAlarmTime,
                        csbSBCServiceName,
                        csbAdjacencyState,
                        csbAdjacencyType,
                        csbAdjacencyName,
                        csbAdjacencyAccountName,
                        csbAlarmDescription
                    }
    STATUS          current
    DESCRIPTION
        "This notification is generated when an Adjacency is attached
        to (or detached from) the SBC."
   ::= { ciscoSessBorderCtrlrMIBNotifs 3 }

csbServiceStateEvent NOTIFICATION-TYPE
    OBJECTS         {
                        csbAlarmSubsystem,
                        csbAlarmSeverity,
                        csbAlarmID,
                        csbAlarmTime,
                        csbSBCServiceName,
                        csbSBCServiceState,
                        csbSBCServiceSlot,
                        csbAlarmDescription
                    }
    STATUS          current
    DESCRIPTION
        "This notification is generated when there is a change in the
        state of a service card. The changes in the service state are:
        -Active 
        -Standby"
   ::= { ciscoSessBorderCtrlrMIBNotifs 4 }

csbSystemCongestionAlarmEvent NOTIFICATION-TYPE
    OBJECTS         {
                        csbAlarmSubsystem,
                        csbAlarmSeverity,
                        csbAlarmID,
                        csbAlarmTime,
                        csbSBCServiceName,
                        csbCongestionAlarmType,
                        csbCongestionAlarmState,
                        csbAlarmDescription
                    }
    STATUS          current
    DESCRIPTION
        "This notification is generated when CPU/Memory congestion in
        SBC is raised or cleared."
   ::= { ciscoSessBorderCtrlrMIBNotifs 5 }

csbSLAViolation NOTIFICATION-TYPE
    OBJECTS         {
                        csbAlarmSubsystem,
                        csbAlarmSeverity,
                        csbAlarmID,
                        csbAlarmTime,
                        csbSBCServiceName,
                        csbSLAPolicyAccountName,
                        csbSLAPolicyScope,
                        csbSLAPolicyLimit,
                        csbSLACurrentUsage,
                        csbSLAViolationEvent,
                        csbSLAPolicyRestriction,
                        csbAlarmDescription
                    }
    STATUS          deprecated
    DESCRIPTION
        "This notification is generated when there is a violation of
        Service Level Agreement as described in the policy tables. The
        typical service level agreements include maximum number of
        calls allowed, max call rate, max bandwidth etc.
        This notification has been replaced by the csbSLAViolationRev1 
        notification."
   ::= { ciscoSessBorderCtrlrMIBNotifs 6 }

csbRadiusConnectionStatus NOTIFICATION-TYPE
    OBJECTS         {
                        csbAlarmSubsystem,
                        csbAlarmSeverity,
                        csbAlarmID,
                        csbAlarmTime,
                        csbSBCServiceName,
                        csbRadiusConnectionState,
                        csbRadiusType,
                        csbRadiusServerName,
                        csbRadiusServerAddressType,
                        csbRadiusServerAddress,
                        csbRadiusServerPriority,
                        csbAlarmDescription
                    }
    STATUS          current
    DESCRIPTION
        "This notification is generated when the connection to the
        radius server changes (connected or disconnected)."
   ::= { ciscoSessBorderCtrlrMIBNotifs 7 }

csbDiameterConnectionStatus NOTIFICATION-TYPE
    OBJECTS         {
                        csbAlarmSubsystem,
                        csbAlarmSeverity,
                        csbAlarmID,
                        csbAlarmTime,
                        csbSBCServiceName,
                        csbDiameterConnectionState,
                        csbDiameterType,
                        csbDiameterGroupName,
                        csbDiameterServerName,
                        csbAlarmDescription
                    }
    STATUS          current
    DESCRIPTION
        "This notification is generated when the connection to the
        diameter server changes (connected or disconnected)."
   ::= { ciscoSessBorderCtrlrMIBNotifs 8 }

csbH248ControllerStatus NOTIFICATION-TYPE
    OBJECTS         {
                        csbAlarmSubsystem,
                        csbAlarmSeverity,
                        csbAlarmID,
                        csbAlarmTime,
                        csbSBCServiceName,
                        csbH248ControllerState,
                        csb248ControllerAddressType,
                        csbH248ControllerAddress,
                        csbH248ControllerPort,
                        csbAlarmDescription
                    }
    STATUS          current
    DESCRIPTION
        "This notification is generated when in distributed deployment
        model, a DBE is attached or detached from the SBC."
   ::= { ciscoSessBorderCtrlrMIBNotifs 9 }

csbSLAViolationRev1 NOTIFICATION-TYPE
    OBJECTS         {
                        csbAlarmSubsystem,
                        csbAlarmSeverity,
                        csbAlarmID,
                        csbAlarmTime,
                        csbSBCServiceName,
                        csbSLAPolicyAccountName,
                        csbSLAPolicyScope,
                        csbSLAPolicyLimitRev1,
                        csbSLACurrentUsageRev1,
                        csbSLAViolationEvent,
                        csbSLAPolicyRestriction,
                        csbAlarmDescription
                    }
    STATUS          current
    DESCRIPTION
        "This notification is generated when there is a violation of
        Service Level Agreement as described in the policy tables. The
        typical service level agreements include maximum number of
        alls allowed, max call rate, max bandwidth etc.
        This notification replaces the csbSLAViolation notification."
   ::= { ciscoSessBorderCtrlrMIBNotifs 10 }

csbQOSUnansweredCallRatioEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertCurrentLevel,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for Unanswered
        Call Ratio (UCR) crosses a configured threshold and attains
        either of minor, major or critical level."
   ::= { ciscoSessBorderCtrlrMIBNotifs 11 }

csbQOSUnansweredCallRatioClearEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for unanswered
        call ratio (UCR) reaches back to normal level from one of the
        major/minor/critical level."
   ::= { ciscoSessBorderCtrlrMIBNotifs 12 }

csbQOSPercentPktLostEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertCurrentLevel,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for percentage
        of media packets lost crosses a configured threshold and attains
        either of minor, major or critical level."
   ::= { ciscoSessBorderCtrlrMIBNotifs 13 }

csbQOSPercentPktLostClearEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is raised whenever QOS metric for percentage
        media packet lost reaches back to normal level from one of the
        major/minor/critical level."
   ::= { ciscoSessBorderCtrlrMIBNotifs 14 }

csbQOSPercentPktDropEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertCurrentLevel,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for percentage
        of media packets dropped crosses a configured threshold and
        attains either of minor, major or critical level."
   ::= { ciscoSessBorderCtrlrMIBNotifs 15 }

csbQOSPercentPktDropClearEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is raised whenever QOS metric for percentage
        media packet dropped reaches back to normal level from one of
        the major/minor/critical level."
   ::= { ciscoSessBorderCtrlrMIBNotifs 16 }

csbQOSRoundTripDelayEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertCurrentLevel,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for round trip
        delay(RTD) crosses a configured threshold and
        attains either of minor, major or critical level."
   ::= { ciscoSessBorderCtrlrMIBNotifs 17 }

csbQOSRoundTripDelayClearEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for round trip
        delay(RTD) reaches back to normal level from one of the
        major/minor/critical level."
   ::= { ciscoSessBorderCtrlrMIBNotifs 18 }

csbQOSLocalJitterEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertCurrentLevel,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for local media
        packet jitter crosses a configured threshold and attains either
        of minor, major or critical level."
   ::= { ciscoSessBorderCtrlrMIBNotifs 19 }

csbQOSLocalJitterClearEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for local media
        packet jitter reaches back to normal level from one of the
        major/minor/critical level."
   ::= { ciscoSessBorderCtrlrMIBNotifs 20 }

csbQOSRemoteJitterEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertCurrentLevel,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for remote media
        packet jitter crosses a configured threshold and attains either
        of minor, major or critical level."
   ::= { ciscoSessBorderCtrlrMIBNotifs 21 }

csbQOSRemoteJitterClearEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for remote media
        packet jitter reaches back to normal level from one of the
        major/minor/critical level."
   ::= { ciscoSessBorderCtrlrMIBNotifs 22 }

csbQOSMoscqeEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertCurrentLevel,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for moscqe -
        Mean Opinion Score(MOS) - value crosses a configured threshold
        and attains either of minor, major or critical level."
   ::= { ciscoSessBorderCtrlrMIBNotifs 23 }

csbQOSMoscqeClearEvent NOTIFICATION-TYPE
    OBJECTS         {
                        csbAlarmSubsystem,
                        csbAlarmSeverity,
                        csbAlarmID,
                        csbAlarmTime,
                        csbSBCServiceName,
                        csbQOSAlertType,
                        csbAdjacencyName,
                        csbQOSAlertSummaryPeriod,
                        csbQOSAlertCurrentValue,
                        csbQOSAlertPreviousLevel,
                        csbQOSNormalAlertCount,
                        csbQOSMinorAlertCount,
                        csbQOSCriticalAlertCount,
                        csbAlarmDescription,
                        csbQOSMajorAlertCount
                    }
    STATUS          current
    DESCRIPTION
        "This notification is generated when QOS metric for moscqe -
        Mean Opinion Score(MOS) -  value reaches back to normal level
        from one of the major/minor/critical level."
   ::= { ciscoSessBorderCtrlrMIBNotifs 24 }

csbAlarmSubsystem OBJECT-TYPE
    SYNTAX          INTEGER  {
                        signaling(1),
                        media(2),
                        cac(3)
                    }
    MAX-ACCESS      accessible-for-notify
    STATUS          current
    DESCRIPTION
        "This object identifies the subsystem or application module
        which generated the alarm. 
        The subsystem which is involved in call establishment only is
        of type signaling.
        The subsystem which handles the traffic/data (RTP/RTCP packets)
        is of type media.
        The subsystem which is involved in call admission control is of
        type CAC." 
    ::= { ciscoSessBorderCtrlrMIBObjects 1 }

csbAlarmSeverity OBJECT-TYPE
    SYNTAX          CiscoAlarmSeverity
    MAX-ACCESS      accessible-for-notify
    STATUS          current
    DESCRIPTION
        "This object identifies the perceived alarm severity associated
        with a service or safety affecting condition and/or event.  
        These are based on ITU severities except that info is added.

        cleared -
             Indicates a previous alarm condition has been cleared.  
             It is not required (unless specifically stated elsewhere 
             on a case by case basis) that an alarm condition that has 
             been cleared will produce a notification or other event 
             containing an alarm severity with this value.

        indeterminate -
             Indicates that the severity level cannot be determined. 

        critical -
             Indicates that a service or safety affecting condition has
             occurred and an immediate corrective action is required.

        major -
             Indicates that a service affecting condition has occurred 
             and an urgent corrective action is required.

        minor -
            Indicates the existence of a non-service affecting
            condition and that corrective action should be taken in 
            order to prevent a more serious (for example, service or 
            safety affecting) condition.

        warning -
            Indicates the detection of a potential or impending service
            or safety affecting condition, before any significant 
            effects have been felt.

        info -
            Indicates an alarm condition that does not meet any other 
            severity definition. This can include important, but 
            non-urgent, notices or informational events." 
    ::= { ciscoSessBorderCtrlrMIBObjects 2 }

csbAlarmID OBJECT-TYPE
    SYNTAX          Integer32 (0..2147483647)
    MAX-ACCESS      accessible-for-notify
    STATUS          current
    DESCRIPTION
        "This object identifies the alarm identification number. It is
        a unique number generated by agent in the incremented order 
        like for the first alarm it is 1, for second alarm it is 2 and
        so on." 
    ::= { ciscoSessBorderCtrlrMIBObjects 3 }

csbAlarmTime OBJECT-TYPE
    SYNTAX          OCTET STRING (SIZE  (0..80))
    MAX-ACCESS      accessible-for-notify
    STATUS          current
    DESCRIPTION
        "This object identifies the time when alarm was generated.  It
        is in the form: dow mon dd hh:mm:ss zzz yyyy

        where:
        dow is the day of the week (Sun, Mon, Tue, Wed,
        Thu, Fri, Sat).

        mon is the month (Jan, Feb, Mar, Apr, May, Jun,
        Jul, Aug, Sep, Oct, Nov, Dec).

        dd is the day of the month (01 through 31), as two decimal
        digits.

        hh is the hour of the day (00 through 23), as two decimal
        digits. 

        mm is the minute within the hour (00 through 59), as two
        decimal digits.

        ss is the second within the minute (00 through 61), as two
        decimal digits.

        zzz is the time zone (and may reflect daylight savings time).
        Standard time zone abbreviations include those recognized by
        the method parse. If time zone information is not available,
        then zzz is empty - that is, it consists of no characters at
        all.

        yyyy is the year, as four decimal digits." 
    ::= { ciscoSessBorderCtrlrMIBObjects 4 }

csbSBCServiceName OBJECT-TYPE
    SYNTAX          SnmpAdminString
    MAX-ACCESS      accessible-for-notify
    STATUS          current
    DESCRIPTION
        "This MIB object represents the name of the SBC service
        configured on the service card." 
    ::= { ciscoSessBorderCtrlrMIBObjects 5 }

csbAlarmDescription OBJECT-TYPE
    SYNTAX          OCTET STRING
    MAX-ACCESS      accessible-for-notify
    STATUS          current
    DESCRIPTION
        "This MIB object represents the description of the conditions
        due to which the notification is raised." 
    ::= { ciscoSessBorderCtrlrMIBObjects 6 }

csbSrcAlertVdbeId OBJECT-TYPE
    SYNTAX          SnmpAdminString (SIZE  (0..30))
    MAX-ACCESS      accessible-for-notify
    STATUS          current
    DESCRIPTION
        "This MIB object represents the name of the virtual media
        gateway. The length of this object will be zero if the virtual
        media gateway is not defined." 
    ::= { ciscoSessBorderCtrlrMIBObjects 7 }

csbSrcAlertGateId OBJECT-TYPE
    SYNTAX          Unsigned32
    MAX-ACCESS      accessible-for-notify
    STATUS          current
    DESCRIPTION
        "This MIB object represents the context identifier for a
        particular SIP/H.248 call flow. The context identifier for each
        call is unique. The context identifier is also called as gate
        identifier for the SIP/H.248 call flow." 
    ::= { ciscoSessBorderCtrlrMIBObjects 8 }

csbSrcAlertFlowPairId OBJECT-TYPE
    SYNTAX          Unsigned32
    MAX-ACCESS      accessible-for-notify
    STATUS          current
    DESCRIPTION
        "This MIB object represents the stream identifier given to a
        particular SIP/H.248 call flow. The stream identifier for each
        call is unique. The stream identifier is also called as flow
        pair identifier for the SIP/H.248 call flow." 
    ::= { ciscoSessBorderCtrlrMIBObjects 9 }

csbSrcAlertLocalAddressType OBJECT-TYPE
    SYNTAX          InetAddressType
    MAX-ACCESS      accessible-for-notify
    STATUS          current
    DESCRIPTION
        "This MIB object represents the address type of local source on
        which the media (RTP/RTCP) packets from an unexpected source 
        was received during a SIP/H.248 call flow. The IP address could
        be IPv4 as well as IPv6." 
    ::= { ciscoSessBorderCtrlrMIBObjects 10 }

csbSrcAlertLocalAddress OBJECT-TYPE
    SYNTAX          InetAddress (SIZE  (4 | 16..16))
    MAX-ACCESS      accessible-for-notify
    STATUS          current
    DESCRIPTION
        "This MIB object represents the local address on which the
        media (RTP/RTCP) packets from an unexpected source was received
        during a SIP/H.248 call flow. The IP address could be of type
        csbSrcAlertLocalAddressType." 
    ::= { ciscoSessBorderCtrlrMIBObjects 11 }

csbSrcAlertLocalPort OBJECT-TYPE
    SYNTAX          InetPortNumber
    MAX-ACCESS      accessible-for-notify
    STATUS          current
    DESCRIPTION
        "This MIB object represents the local RTP port number for the
        flow on which the unexpected source packet was received.
        Note the RTP port number is reported in the case where the
        unexpected packet was received on the RTCP port for the flow." 
    ::= { ciscoSessBorderCtrlrMIBObjects 12 }

csbSrcAlertRemoteAddressType OBJECT-TYPE
    SYNTAX          InetAddressType
    MAX-ACCESS      accessible-for-notify
    STATUS          current
    DESCRIPTION
        "This MIB object represents the type of address for the source
        address in media packets received from an unexpected source
        (not
        received from the source with which SIP/H.248 call is already
        established but are received from some other IP address)." 
    ::= { ciscoSessBorderCtrlrMIBObjects 13 }

csbSrcAlertRemoteAddress OBJECT-TYPE
    SYNTAX          InetAddress (SIZE  (4 | 16..16))
    MAX-ACCESS      accessible-for-notify
    STATUS          current
    DESCRIPTION
        "This MIB object represents the source address from which
        unexpected media packets are received during a SIP/H.248 
        call flow, i.e., media packets are not received from the source
        with which SIP/H.248 call is already established but are
        received from some other IP address. The IP address could be
        of type csbSrcAlertRemoteAddressType." 
    ::= { ciscoSessBorderCtrlrMIBObjects 14 }

csbSrcAlertRemotePort OBJECT-TYPE
    SYNTAX          InetPortNumber (0..65535)
    MAX-ACCESS      accessible-for-notify
    STATUS          current
    DESCRIPTION
        "This MIB object represents the source port from which
        unexpected media packets are received during a SIP/H.248 
        call flow (i.e. media packets are not received from the source
        with which SIP/H.248 call is already established but are
        received from some other IP address)." 
    ::= { ciscoSessBorderCtrlrMIBObjects 15 }

csbSrcAlertVpnId OBJECT-TYPE
    SYNTAX          OCTET STRING (SIZE  (0..32))
    MAX-ACCESS      accessible-for-notify
    STATUS          current
    DESCRIPTION
        "This MIB object represents the VPN Identifier for the Virtual
        Private Network within which the source flow is allocated. As
        this is an OCTET STRING, the MIB object will populate a NULL
        string if the source flow is not part of a VPN and in this case
        its length will be 0." 
    ::= { ciscoSessBorderCtrlrMIBObjects 16 }

csbDynamicBlackListSubFamily OBJECT-TYPE
    SYNTAX          CsbDynamicBlackListedSrcSubFamily
    MAX-ACCESS      accessible-for-notify
    STATUS          current
    DESCRIPTION
        "This MIB object represents the subfamily to which a blacklist
        source belongs." 
    ::= { ciscoSessBorderCtrlrMIBObjects 17 }

csbDynamicBlackListVpnId OBJECT-TYPE
    SYNTAX          OCTET STRING (SIZE  (0..32))
    MAX-ACCESS      accessible-for-notify
    STATUS          current
    DESCRIPTION
        "This MIB object represents the VPN Identifier for the Virtual
        Private Network that the source flow is allocated in. The value
        of this MIB object will be 0 if the source flow is not part of 
        a VPN." 
    ::= { ciscoSessBorderCtrlrMIBObjects 18 }

csbDynamicBlackListAddressType OBJECT-TYPE
    SYNTAX          InetAddressType
    MAX-ACCESS      accessible-for-notify
    STATUS          current
    DESCRIPTION
        "This MIB object represents the type of the address of the
        source. This MIB object is not applicable for subfamilies of
        type 'blackVpn' and hence a value of 'unknown' will be
        populated." 
    ::= { ciscoSessBorderCtrlrMIBObjects 19 }

csbDynamicBlackListAddress OBJECT-TYPE
    SYNTAX          InetAddress
    MAX-ACCESS      accessible-for-notify
    STATUS          current
    DESCRIPTION
        "This MIB object represents the address of the source. This
        object could be if type csbDynamicBlackListAddressType. This
        MIB object is not applicable for subfamilies of type 'blackVpn'
        and hence a value of 'unknown' will be populated." 
    ::= { ciscoSessBorderCtrlrMIBObjects 20 }

csbDynamicBlackListTransportType OBJECT-TYPE
    SYNTAX          CsbDynamicBlackListedTransPortType
    MAX-ACCESS      accessible-for-notify
    STATUS          current
    DESCRIPTION
        "This MIB object represents the transport type of the source
        port. This MIB object is not applicable for subfamilies of type
        'blackVpn' and 'blackAddr', hence a value 'unknown' will be 
        populated." 
    ::= { ciscoSessBorderCtrlrMIBObjects 21 }

csbDynamicBlackListPortNumber OBJECT-TYPE
    SYNTAX          InetPortNumber
    MAX-ACCESS      accessible-for-notify
    STATUS          current
    DESCRIPTION
        "This MIB object represents the source port number. This MIB
        object is not applicable for subfamilies of type 'blackVpn' and
        'blackAddr' and hence a value of 'unknown' will be populated." 
    ::= { ciscoSessBorderCtrlrMIBObjects 22 }

csbDynamicBlackListSrcBlocked OBJECT-TYPE
    SYNTAX          TruthValue
    MAX-ACCESS      accessible-for-notify
    STATUS          current
    DESCRIPTION
        "This MIB object represents the access control imposed on the
        blacklisted source by the controller. A value of 'true'
        indicates access is blocked and A value of 'false' indicates
        that the access is unblocked." 
    ::= { ciscoSessBorderCtrlrMIBObjects 23 }

csbAdjacencyType OBJECT-TYPE
    SYNTAX          INTEGER  {
                        sip(1),
                        h323(2)
                    }
    MAX-ACCESS      accessible-for-notify
    STATUS          current
    DESCRIPTION
        "This MIB object represents the protocol type of the adjacency.
        The adjacency are of two types - SIP and H.323." 
    ::= { ciscoSessBorderCtrlrMIBObjects 24 }

csbAdjacencyState OBJECT-TYPE
    SYNTAX          INTEGER  {
                        attached(1),
                        detached(2)
                    }
    MAX-ACCESS      accessible-for-notify
    STATUS          current
    DESCRIPTION
        "This MIB object represents the adjacency state. The adjacency
        state can either be attached or detached." 
    ::= { ciscoSessBorderCtrlrMIBObjects 25 }

csbAdjacencyName OBJECT-TYPE
    SYNTAX          SnmpAdminString
    MAX-ACCESS      accessible-for-notify
    STATUS          current
    DESCRIPTION
        "This MIB object represents the name of the adjacency. The
        length of this object will be zero if the adjacency name is not
        defined." 
    ::= { ciscoSessBorderCtrlrMIBObjects 26 }

csbAdjacencyAccountName OBJECT-TYPE
    SYNTAX          SnmpAdminString
    MAX-ACCESS      accessible-for-notify
    STATUS          current
    DESCRIPTION
        "This MIB object represents the account name associated with the
        adjacency." 
    ::= { ciscoSessBorderCtrlrMIBObjects 27 }

csbSBCServiceState OBJECT-TYPE
    SYNTAX          INTEGER  {
                        active(1),
                        standby(2),
                        offline(3)
                    }
    MAX-ACCESS      accessible-for-notify
    STATUS          current
    DESCRIPTION
        "This MIB object represents the current state of the service
        card.
        SBC service is in active state if it is configured on the
        primary card and the service card is in active state.
        The SBC service is in standby state if the service card on 
        which the service is configured goes to standby mode.
        The SBC service is in offline mode if the service card on which
        the service is configured is in reset state or reboot state." 
    ::= { ciscoSessBorderCtrlrMIBObjects 28 }

csbSBCServiceSlot OBJECT-TYPE
    SYNTAX          Integer32
    MAX-ACCESS      accessible-for-notify
    STATUS          current
    DESCRIPTION
        "This MIB object represents the slot identifier of the service
        card." 
    ::= { ciscoSessBorderCtrlrMIBObjects 29 }

csbCongestionAlarmType OBJECT-TYPE
    SYNTAX          INTEGER  {
                        unknown(1),
                        cpu(2),
                        memory(3)
                    }
    MAX-ACCESS      accessible-for-notify
    STATUS          current
    DESCRIPTION
        "This MIB object represents the type of the CSB system
        congestion alarm. The alarm is raised either due to 'high CPU
        usage' or 'high memory usage'." 
    ::= { ciscoSessBorderCtrlrMIBObjects 30 }

csbCongestionAlarmState OBJECT-TYPE
    SYNTAX          INTEGER  {
                        raised(1),
                        cleared(2)
                    }
    MAX-ACCESS      accessible-for-notify
    STATUS          current
    DESCRIPTION
        "This MIB object represents the CSB system congestion alarm
        state. The state is either 'raised' or 'cleared'." 
    ::= { ciscoSessBorderCtrlrMIBObjects 31 }

csbSLAPolicyAccountName OBJECT-TYPE
    SYNTAX          SnmpAdminString
    MAX-ACCESS      accessible-for-notify
    STATUS          current
    DESCRIPTION
        "This MIB object represents the account name of the source
        which was involved in policy violation." 
    ::= { ciscoSessBorderCtrlrMIBObjects 32 }

csbSLAPolicyScope OBJECT-TYPE
    SYNTAX          SnmpAdminString
    MAX-ACCESS      accessible-for-notify
    STATUS          current
    DESCRIPTION
        "This MIB object represents the scope of the SLA policy which
        has been violated." 
    ::= { ciscoSessBorderCtrlrMIBObjects 33 }

csbSLAPolicyLimit OBJECT-TYPE
    SYNTAX          Integer32
    MAX-ACCESS      accessible-for-notify
    STATUS          deprecated
    DESCRIPTION
        "This MIB object represents the currently defined policy
        limits." 
    ::= { ciscoSessBorderCtrlrMIBObjects 34 }

csbSLAViolationEvent OBJECT-TYPE
    SYNTAX          SnmpAdminString
    MAX-ACCESS      accessible-for-notify
    STATUS          current
    DESCRIPTION
        "This MIB object represents the type of SLA policy violation
        event." 
    ::= { ciscoSessBorderCtrlrMIBObjects 35 }

csbSLAPolicyRestriction OBJECT-TYPE
    SYNTAX          SnmpAdminString
    MAX-ACCESS      accessible-for-notify
    STATUS          current
    DESCRIPTION
        "This MIB object represents the SLA policy restriction
        description means the violation of the call policy has resulted
        into which type of restriction, like if maximum number of calls
        exceeds then it will restrict the number of concurrent calls." 
    ::= { ciscoSessBorderCtrlrMIBObjects 36 }

csbSLACurrentUsage OBJECT-TYPE
    SYNTAX          Integer32
    MAX-ACCESS      accessible-for-notify
    STATUS          deprecated
    DESCRIPTION
        "This MIB object represents the actual usage value for the event
        which leads to the SLA violation, like if maximum number of
        calls are more than SLA policy then actual value of this
        parameter/event." 
    ::= { ciscoSessBorderCtrlrMIBObjects 37 }

csbRadiusConnectionState OBJECT-TYPE
    SYNTAX          INTEGER  {
                        up(1),
                        down(2)
                    }
    MAX-ACCESS      accessible-for-notify
    STATUS          current
    DESCRIPTION
        "This MIB object represents the RADIUS server connection state.
        The connection state can either be up or down." 
    ::= { ciscoSessBorderCtrlrMIBObjects 38 }

csbRadiusType OBJECT-TYPE
    SYNTAX          INTEGER  {
                        accounting(1),
                        authentication(2)
                    }
    MAX-ACCESS      accessible-for-notify
    STATUS          current
    DESCRIPTION
        "This MIB object represents the type of RADIUS either for
        accounting or for authentication." 
    ::= { ciscoSessBorderCtrlrMIBObjects 39 }

csbRadiusServerName OBJECT-TYPE
    SYNTAX          SnmpAdminString
    MAX-ACCESS      accessible-for-notify
    STATUS          current
    DESCRIPTION
        "This MIB object represents the name of the RADIUS server." 
    ::= { ciscoSessBorderCtrlrMIBObjects 40 }

csbRadiusServerAddressType OBJECT-TYPE
    SYNTAX          InetAddressType
    MAX-ACCESS      accessible-for-notify
    STATUS          current
    DESCRIPTION
        "This MIB object represents the address type of RADIUS server
        (IPv4 or IPv6)." 
    ::= { ciscoSessBorderCtrlrMIBObjects 41 }

csbRadiusServerAddress OBJECT-TYPE
    SYNTAX          InetAddress (SIZE  (4 | 16..16))
    MAX-ACCESS      accessible-for-notify
    STATUS          current
    DESCRIPTION
        "This MIB object represents address of the RADIUS server. This
        object could be of type csbRadiusServerAddressType." 
    ::= { ciscoSessBorderCtrlrMIBObjects 42 }

csbRadiusServerPriority OBJECT-TYPE
    SYNTAX          Integer32
    MAX-ACCESS      accessible-for-notify
    STATUS          current
    DESCRIPTION
        "This MIB object represents the priority of the RADIUS server
        in case of the multiple servers. Higher the number, the higher
        is its priority." 
    ::= { ciscoSessBorderCtrlrMIBObjects 43 }

csbDiameterConnectionState OBJECT-TYPE
    SYNTAX          INTEGER  {
                        up(1),
                        down(2)
                    }
    MAX-ACCESS      accessible-for-notify
    STATUS          current
    DESCRIPTION
        "This MIB object represents the diameter server connection
        state. The connection state can either be up or down." 
    ::= { ciscoSessBorderCtrlrMIBObjects 44 }

csbDiameterType OBJECT-TYPE
    SYNTAX          INTEGER  {
                        accounting(1),
                        authentication(2)
                    }
    MAX-ACCESS      accessible-for-notify
    STATUS          current
    DESCRIPTION
        "This MIB object represents the type of diameter server used
        which can be either for accounting or for authentication here." 
    ::= { ciscoSessBorderCtrlrMIBObjects 45 }

csbDiameterGroupName OBJECT-TYPE
    SYNTAX          SnmpAdminString
    MAX-ACCESS      accessible-for-notify
    STATUS          current
    DESCRIPTION
        "This MIB object represents the diameter group name. The length
        of this object is zero if the diameter type is authentication." 
    ::= { ciscoSessBorderCtrlrMIBObjects 46 }

csbDiameterServerName OBJECT-TYPE
    SYNTAX          SnmpAdminString
    MAX-ACCESS      accessible-for-notify
    STATUS          current
    DESCRIPTION
        "This MIB object represents the diameter server name." 
    ::= { ciscoSessBorderCtrlrMIBObjects 47 }

csbH248ControllerState OBJECT-TYPE
    SYNTAX          INTEGER  {
                        attached(1),
                        detached(2)
                    }
    MAX-ACCESS      accessible-for-notify
    STATUS          current
    DESCRIPTION
        "This MIB object represents the current state of H.248
        controller with respect to SBC which is attached or detached
        state." 
    ::= { ciscoSessBorderCtrlrMIBObjects 48 }

csb248ControllerAddressType OBJECT-TYPE
    SYNTAX          InetAddressType
    MAX-ACCESS      accessible-for-notify
    STATUS          current
    DESCRIPTION
        "This MIB object represents the address type of the H.248
        controller." 
    ::= { ciscoSessBorderCtrlrMIBObjects 49 }

csbH248ControllerAddress OBJECT-TYPE
    SYNTAX          InetAddress (SIZE  (4 | 16..16))
    MAX-ACCESS      accessible-for-notify
    STATUS          current
    DESCRIPTION
        "This MIB object represents the address of the H.248
        controller. This object is of the type
        csb248ControllerAddressType." 
    ::= { ciscoSessBorderCtrlrMIBObjects 50 }

csbH248ControllerPort OBJECT-TYPE
    SYNTAX          InetPortNumber
    MAX-ACCESS      accessible-for-notify
    STATUS          current
    DESCRIPTION
        "This MIB object represents the port of the H.248 controller." 
    ::= { ciscoSessBorderCtrlrMIBObjects 51 }

csbSourceAlertNotifEnabled OBJECT-TYPE
    SYNTAX          TruthValue
    MAX-ACCESS      read-write
    STATUS          current
    DESCRIPTION
        "The source alert linkset notification truth value.
        'true' - Indicates that csbSourceAlertEvent notification is to
        be generated when the state changes. That is, the notification
        generation is enabled.
        'false' - Indicates that csbSourceAlertEvent notification
        generation is disabled." 
    ::= { ciscoSessBorderCtrlrMIBObjects 52 }

csbBlackListNotifEnabled OBJECT-TYPE
    SYNTAX          TruthValue
    MAX-ACCESS      read-write
    STATUS          current
    DESCRIPTION
        "The dynamic blacklist linkset notification truth value.
        'true' - Indicates that csbDynamicBlackListEvent notification is
        to be generated when the state changes. That is, the
        notification generation is enabled.
        'false' - Indicates that csbDynamicBlackListEvent notification
        generation is disabled." 
    ::= { ciscoSessBorderCtrlrMIBObjects 53 }

csbAdjacencyStatusNotifEnabled OBJECT-TYPE
    SYNTAX          TruthValue
    MAX-ACCESS      read-write
    STATUS          current
    DESCRIPTION
        "The adjacency status linkset notification truth value.
        'true' - Indicates that csbAdjacencyStatus notification is
        to be generated when the state changes. That is, the
        notification generation is enabled.
        'false' - Indicates that csbAdjacencyStatus notification
        generation is disabled." 
    ::= { ciscoSessBorderCtrlrMIBObjects 54 }

csbServiceStateNotifEnabled OBJECT-TYPE
    SYNTAX          TruthValue
    MAX-ACCESS      read-write
    STATUS          current
    DESCRIPTION
        "The service state linkset notification truth value.
        'true' - Indicates that csbServiceStateEvent notification is
        to be generated when the state changes. That is, the
        notification generation is enabled.
        'false' - Indicates that csbServiceStateEvent notification
        generation is disabled." 
    ::= { ciscoSessBorderCtrlrMIBObjects 55 }

csbCongestionAlarmNotifEnabled OBJECT-TYPE
    SYNTAX          TruthValue
    MAX-ACCESS      read-write
    STATUS          current
    DESCRIPTION
        "The system congestion alarm linkset notification truth value.
        'true' - Indicates that csbSystemCongestionAlarmEvent
        notification is to be generated when the state changes. That is,
        the notification generation is enabled.
        'false' - Indicates that csbSystemCongestionAlarmEvent
        notification generation is disabled." 
    ::= { ciscoSessBorderCtrlrMIBObjects 56 }

csbSLAViolationNotifEnabled OBJECT-TYPE
    SYNTAX          TruthValue
    MAX-ACCESS      read-write
    STATUS          deprecated
    DESCRIPTION
        "The SLA violation linkset notification truth value.
        'true' - Indicates that csbSLAViolation notification is to be
        generated when the state changes. That is, the notification
        generation is enabled.
        'false' - Indicates that csbSLAViolation notification generation
        is disabled." 
    ::= { ciscoSessBorderCtrlrMIBObjects 57 }

csbRadiusConnectionStatusNotifEnabled OBJECT-TYPE
    SYNTAX          TruthValue
    MAX-ACCESS      read-write
    STATUS          current
    DESCRIPTION
        "The radius connection status linkset notification truth value.
        'true' - Indicates that csbRadiusConnectionStatus notification
        is to be generated when the state changes. That is, the
        notification generation is enabled.
        'false' - Indicates that csbRadiusConnectionStatus notification
        generation is disabled." 
    ::= { ciscoSessBorderCtrlrMIBObjects 58 }

csbDiameterConnectionStatusNotifEnabled OBJECT-TYPE
    SYNTAX          TruthValue
    MAX-ACCESS      read-write
    STATUS          current
    DESCRIPTION
        "The diameter connection status linkset notification truth
        value.
        'true' - Indicates that csbDiameterConnectionStatus notification
        is to be generated when the state changes. That is, the
        notification generation is enabled.
        'false' - Indicates that csbDiameterConnectionStatus
        notification generation is disabled." 
    ::= { ciscoSessBorderCtrlrMIBObjects 59 }

csbH248ControllerStatusNotifEnabled OBJECT-TYPE
    SYNTAX          TruthValue
    MAX-ACCESS      read-write
    STATUS          current
    DESCRIPTION
        "The H248 controller status linkset notification truth
        value.
        'true' - Indicates that csbH248ControllerStatus notification is
        to be generated when the state changes. That is, the
        notification generation is enabled.
        'false' - Indicates that csbH248ControllerStatus notification
        generation is disabled." 
    ::= { ciscoSessBorderCtrlrMIBObjects 60 }

csbSLAPolicyLimitRev1 OBJECT-TYPE
    SYNTAX          Counter64
    MAX-ACCESS      accessible-for-notify
    STATUS          current
    DESCRIPTION
        "This MIB object represents the currently defined policy limits.
        If the SLA is for max-num-calls, this value is the configured
        maximum number of calls. If the SLA is for max-call-rate, this
        value is the configured maximum number of calls per minute. If
        the SLA is for max-bandwidth, this value is the configured
        maximum bidirection bandwidth in bps.
        This object replaces the csbSLAPolicyLimit object." 
    ::= { ciscoSessBorderCtrlrMIBObjects 61 }

csbSLACurrentUsageRev1 OBJECT-TYPE
    SYNTAX          Counter64
    MAX-ACCESS      accessible-for-notify
    STATUS          current
    DESCRIPTION
        "This MIB object represents the actual usage value for the event
        which leads to the SLA violation, like if maximum number of
        calls are more than SLA policy then actual value of this
        parameter/event. If the SLA is for max-num-calls, this value is
        the current number of calls. If the SLA is for max-call-rate,
        this value is the current number of calls per minute. If the SLA
        is for max-bandwidth, this value is the current bidirection
        bandwidth in bps.
        This object replaces the csbSLACurrentUsage object." 
    ::= { ciscoSessBorderCtrlrMIBObjects 62 }

csbSLAViolationNotifEnabledRev1 OBJECT-TYPE
    SYNTAX          TruthValue
    MAX-ACCESS      read-write
    STATUS          current
    DESCRIPTION
        "The SLA violation linkset notification truth value.
        'true' - Indicates that csbSLAViolationRev1 notification is to 
        be generated when the state changes. That is, the notification
        generation is enabled.
        'false' - Indicates that csbSLAViolationReve1 notification
        generation
        is disabled." 
    ::= { ciscoSessBorderCtrlrMIBObjects 63 }

csbQOSAlertCurrentValue OBJECT-TYPE
    SYNTAX          Unsigned32
    MAX-ACCESS      accessible-for-notify
    STATUS          current
    DESCRIPTION
        "This object indicates the current measured value of the QOS
        object." 
    ::= { ciscoSessBorderCtrlrMIBObjects 64 }

csbQOSAlertCurrentLevel OBJECT-TYPE
    SYNTAX          CiscoAlarmSeverity
    MAX-ACCESS      accessible-for-notify
    STATUS          current
    DESCRIPTION
        "The current Threshold Level of the measured object. The levels
        are Major, Minor, Critical." 
    ::= { ciscoSessBorderCtrlrMIBObjects 65 }

csbQOSAlertPreviousLevel OBJECT-TYPE
    SYNTAX          CiscoAlarmSeverity
    MAX-ACCESS      accessible-for-notify
    STATUS          current
    DESCRIPTION
        "The previous threshold level of the measured object. The levels
        are Major, Minor, Critical." 
    ::= { ciscoSessBorderCtrlrMIBObjects 66 }

csbQOSNormalAlertCount OBJECT-TYPE
    SYNTAX          Counter32
    UNITS           "occurrences"
    MAX-ACCESS      accessible-for-notify
    STATUS          current
    DESCRIPTION
        "This object represents the number of times this QOS object,
        has entered normal level." 
    ::= { ciscoSessBorderCtrlrMIBObjects 67 }

csbQOSMinorAlertCount OBJECT-TYPE
    SYNTAX          Counter32
    UNITS           "occurrences"
    MAX-ACCESS      accessible-for-notify
    STATUS          current
    DESCRIPTION
        "This object represents number of times the QOS object, has
        entered minor level." 
    ::= { ciscoSessBorderCtrlrMIBObjects 68 }

csbQOSCriticalAlertCount OBJECT-TYPE
    SYNTAX          Counter32
    UNITS           "occurrences"
    MAX-ACCESS      accessible-for-notify
    STATUS          current
    DESCRIPTION
        "This object represents the number of times the QOS object, has
        entered critical level." 
    ::= { ciscoSessBorderCtrlrMIBObjects 69 }

csbQOSMajorAlertCount OBJECT-TYPE
    SYNTAX          Counter32
    UNITS           "occurrences"
    MAX-ACCESS      accessible-for-notify
    STATUS          current
    DESCRIPTION
        "This object represents number the of times the QOS object, has
        entered major level." 
    ::= { ciscoSessBorderCtrlrMIBObjects 70 }

csbQOSAlertType OBJECT-TYPE
    SYNTAX          CsbQOSAlertScopeType
    MAX-ACCESS      accessible-for-notify
    STATUS          current
    DESCRIPTION
        "This object represents that the value of QOS parameter is
        applicable at which scope. QOS parameters can be calculated
        both at global as well as adjacency scope." 
    ::= { ciscoSessBorderCtrlrMIBObjects 71 }

csbQOSAlertSummaryPeriod OBJECT-TYPE
    SYNTAX          CiscoSbcPeriodicStatsInterval
    MAX-ACCESS      accessible-for-notify
    STATUS          current
    DESCRIPTION
        "This object indicates the interval for which the periodic
        statistics information is to be displayed. The interval      
        values can be 5 min, 15 mins, 1 hour or 1 day." 
    ::= { ciscoSessBorderCtrlrMIBObjects 72 }

csbQOSAlertUnansweredCallRatioNotifEnabled OBJECT-TYPE
    SYNTAX          TruthValue
    MAX-ACCESS      read-write
    STATUS          current
    DESCRIPTION
        "The Unanswered Call Ratio notification truth value.
        'true' - Indicates that csbQOSUnansweredCallRatioEvent
        notification is to be generated when the state changes. That is,
        the notification generation is enabled.
        'false' - Indicates that csbQOSUnansweredCallRatioEvent 
        notification generation is disabled." 
    ::= { ciscoSessBorderCtrlrMIBObjects 73 }

csbQOSAlertPercentPktDropNotifEnabled OBJECT-TYPE
    SYNTAX          TruthValue
    MAX-ACCESS      read-write
    STATUS          current
    DESCRIPTION
        "The percent media packet drop notification truth value.
        'true' - Indicates that csbQOSPercentPktDropEvent notification
        is to be generated when the state changes. That is, the
        notification generation is enabled.
        'false' - Indicates that csbQOSPercentPktDropEvent notification
        generation is disabled." 
    ::= { ciscoSessBorderCtrlrMIBObjects 74 }

csbQOSAlertRoundTripDelayNotifEnabled OBJECT-TYPE
    SYNTAX          TruthValue
    MAX-ACCESS      read-write
    STATUS          current
    DESCRIPTION
        "The round trip delay notification truth value.
        'true' - Indicates that csbQOSRoundTripDelayEvent notification
        is to be generated when the state changes. That is, the
        notification generation is enabled.
        'false' - Indicates that csbQOSRoundTripDelayEvent notification
        generation is disabled." 
    ::= { ciscoSessBorderCtrlrMIBObjects 75 }

csbQOSAlertMoscqeNotifEnabled OBJECT-TYPE
    SYNTAX          TruthValue
    MAX-ACCESS      read-write
    STATUS          current
    DESCRIPTION
        "The moscqe notification truth value.
        'true' - Indicates that csbQOSMoscqeEvent notification is to be
        generated when the state changes. That is, the notification
        generation is enabled.
        'false' - Indicates that csbQOSMoscqeEvent notification
        generation is disabled." 
    ::= { ciscoSessBorderCtrlrMIBObjects 76 }

csbQOSAlertLocalJitterNotifEnabled OBJECT-TYPE
    SYNTAX          TruthValue
    MAX-ACCESS      read-write
    STATUS          current
    DESCRIPTION
        "The remote media packet jitter notification truth value.
        'true' - Indicates that csbQOSLocalJitterEvent notification is
        to be generated when the state changes. That is, the
        notification generation is enabled.
        'false' - Indicates that csbQOSLocalJitterEvent notification
        generation is disabled." 
    ::= { ciscoSessBorderCtrlrMIBObjects 77 }

csbQOSAlertRemoteJitterNotifEnabled OBJECT-TYPE
    SYNTAX          TruthValue
    MAX-ACCESS      read-write
    STATUS          current
    DESCRIPTION
        "The remote media packet jitter notification truth value.
        'true' - Indicates that csbQOSRemoteJitterEvent notification is
        to be generated when the state changes. That is, the
        notification generation is enabled.
        'false' - Indicates that csbQOSRemoteJitterEvent notification
        generation is disabled." 
    ::= { ciscoSessBorderCtrlrMIBObjects 78 }

csbQOSAlertPercentPktLostNotifEnabled OBJECT-TYPE
    SYNTAX          TruthValue
    MAX-ACCESS      read-write
    STATUS          current
    DESCRIPTION
        "The percent media packet drop notification truth value.
        'true' - Indicates that csbQOSPercentPktLostEvent notification
        is to be generated when the state changes. That is, the
        notification generation is enabled.
        'false' - Indicates that csbQOSPercentPktLostEvent notification
        generation is disabled." 
    ::= { ciscoSessBorderCtrlrMIBObjects 79 }
-- Conformance

ciscoSessBorderCtrlrMIBCompliances  OBJECT IDENTIFIER
    ::= { ciscoSessBorderCtrlrMIBConform 1 }

ciscoSessBorderCtrlrMIBGroups  OBJECT IDENTIFIER
    ::= { ciscoSessBorderCtrlrMIBConform 2 }

csbCompliance MODULE-COMPLIANCE
    STATUS          deprecated
    DESCRIPTION
        "The compliance statement for the SNMP entities that implement
        this MIB module."
    MODULE          -- this module
    MANDATORY-GROUPS {
                        csbSourceAlertGroup,
                        csbDynamicBlackListGroup,
                        csbNotificationGroup,
                        csbNotificationManadatoryParams,
                        csbAdjacencyGroup,
                        csbSBCServiceGroup,
                        csbSLAGroup,
                        csbRadiusConnectionGroup,
                        csbDiameterConnectionGroup,
                        csbH248StatusGroup,
                        csbCongestionGroup,
                        csbNotifEnabledGroup
                    }
    ::= { ciscoSessBorderCtrlrMIBCompliances 1 }

csbComplianceRev1 MODULE-COMPLIANCE
    STATUS          deprecated
    DESCRIPTION
        "The compliance statement for the SNMP entities that implement
        this MIB module."
    MODULE          -- this module
    MANDATORY-GROUPS {
                        csbSourceAlertGroup,
                        csbDynamicBlackListGroup,
                        csbNotificationGroupRev1,
                        csbNotificationManadatoryParams,
                        csbAdjacencyGroup,
                        csbSBCServiceGroup,
                        csbSLAGroupRev1,
                        csbRadiusConnectionGroup,
                        csbDiameterConnectionGroup,
                        csbH248StatusGroup,
                        csbCongestionGroup,
                        csbNotifEnabledGroupRev1
                    }
    ::= { ciscoSessBorderCtrlrMIBCompliances 2 }

csbComplianceRev2 MODULE-COMPLIANCE
    STATUS          current
    DESCRIPTION
        "The compliance statement for the SNMP entities that implement
        this MIB module."
    MODULE          -- this module
    MANDATORY-GROUPS {
                        csbSourceAlertGroup,
                        csbDynamicBlackListGroup,
                        csbNotificationGroupRev1,
                        csbNotificationManadatoryParams,
                        csbAdjacencyGroup,
                        csbSBCServiceGroup,
                        csbSLAGroupRev1,
                        csbRadiusConnectionGroup,
                        csbDiameterConnectionGroup,
                        csbH248StatusGroup,
                        csbCongestionGroup,
                        csbNotifEnabledGroupRev1,
                        csbQOSAlertGroup,
                        csbNotificationGroupSup1,
                        csbNotifEnabledGroupSup1
                    }
    ::= { ciscoSessBorderCtrlrMIBCompliances 3 }

csbNotificationGroup NOTIFICATION-GROUP
   NOTIFICATIONS    {
                        csbSourceAlertEvent,
                        csbDynamicBlackListEvent,
                        csbAdjacencyStatus,
                        csbServiceStateEvent,
                        csbSystemCongestionAlarmEvent,
                        csbSLAViolation,
                        csbRadiusConnectionStatus,
                        csbDiameterConnectionStatus,
                        csbH248ControllerStatus
                    }
    STATUS          deprecated
    DESCRIPTION
        "This collection of objects represents the notifications
        generated by the agent."
    ::= { ciscoSessBorderCtrlrMIBGroups 1 }

csbNotificationManadatoryParams OBJECT-GROUP
    OBJECTS         {
                        csbAlarmSubsystem,
                        csbAlarmSeverity,
                        csbAlarmID,
                        csbAlarmTime,
                        csbSBCServiceName,
                        csbAlarmDescription
                    }
    STATUS          current
    DESCRIPTION
        "This collection of objects represents the information which
        must be included in every notification."
    ::= { ciscoSessBorderCtrlrMIBGroups 2 }

-- Units of Conformance

csbSourceAlertGroup OBJECT-GROUP
    OBJECTS         {
                        csbSrcAlertVdbeId,
                        csbSrcAlertGateId,
                        csbSrcAlertFlowPairId,
                        csbSrcAlertLocalAddress,
                        csbSrcAlertLocalPort,
                        csbSrcAlertRemoteAddressType,
                        csbSrcAlertRemoteAddress,
                        csbSrcAlertRemotePort,
                        csbSrcAlertVpnId,
                        csbSrcAlertLocalAddressType
                    }
    STATUS          current
    DESCRIPTION
        "This collection of objects represents the information about
        flows and unknown sources from which media packets have arrived
        at the respective flows."
    ::= { ciscoSessBorderCtrlrMIBGroups 3 }

csbDynamicBlackListGroup OBJECT-GROUP
    OBJECTS         {
                        csbDynamicBlackListSubFamily,
                        csbDynamicBlackListVpnId,
                        csbDynamicBlackListAddressType,
                        csbDynamicBlackListAddress,
                        csbDynamicBlackListTransportType,
                        csbDynamicBlackListPortNumber,
                        csbDynamicBlackListSrcBlocked
                    }
    STATUS          current
    DESCRIPTION
        "This collection of objects represents the information about
        black-listed sources."
    ::= { ciscoSessBorderCtrlrMIBGroups 4 }

csbAdjacencyGroup OBJECT-GROUP
    OBJECTS         {
                        csbAdjacencyType,
                        csbAdjacencyName,
                        csbAdjacencyAccountName,
                        csbAdjacencyState
                    }
    STATUS          current
    DESCRIPTION
        "This collection of objects represents the information about
        the adjacency notification."
    ::= { ciscoSessBorderCtrlrMIBGroups 5 }

csbSBCServiceGroup OBJECT-GROUP
    OBJECTS         {
                        csbSBCServiceSlot,
                        csbSBCServiceState
                    }
    STATUS          current
    DESCRIPTION
        "This collection of objects represents the information related
        to the SBC service configured on a router."
    ::= { ciscoSessBorderCtrlrMIBGroups 6 }

csbCongestionGroup OBJECT-GROUP
    OBJECTS         {
                        csbCongestionAlarmState,
                        csbCongestionAlarmType
                    }
    STATUS          current
    DESCRIPTION
        "This collection of objects represents the information about
        the congestion state of the SBC system."
    ::= { ciscoSessBorderCtrlrMIBGroups 7 }

csbSLAGroup OBJECT-GROUP
    OBJECTS         {
                        csbSLAPolicyAccountName,
                        csbSLAPolicyScope,
                        csbSLAPolicyLimit,
                        csbSLACurrentUsage,
                        csbSLAViolationEvent,
                        csbSLAPolicyRestriction
                    }
    STATUS          deprecated
    DESCRIPTION
        "This collection of objects represents the information related
        to the Service Level Agreement (SLA) violation notification."
    ::= { ciscoSessBorderCtrlrMIBGroups 8 }

csbRadiusConnectionGroup OBJECT-GROUP
    OBJECTS         {
                        csbRadiusConnectionState,
                        csbRadiusType,
                        csbRadiusServerName,
                        csbRadiusServerAddressType,
                        csbRadiusServerAddress,
                        csbRadiusServerPriority
                    }
    STATUS          current
    DESCRIPTION
        "This collection of objects represents the information about
        the radius server connection state."
    ::= { ciscoSessBorderCtrlrMIBGroups 9 }

csbDiameterConnectionGroup OBJECT-GROUP
    OBJECTS         {
                        csbDiameterConnectionState,
                        csbDiameterType,
                        csbDiameterGroupName,
                        csbDiameterServerName
                    }
    STATUS          current
    DESCRIPTION
        "This collection of objects represents the information about
        the diameter server connection state."
    ::= { ciscoSessBorderCtrlrMIBGroups 10 }

csbH248StatusGroup OBJECT-GROUP
    OBJECTS         {
                        csbH248ControllerState,
                        csb248ControllerAddressType,
                        csbH248ControllerAddress,
                        csbH248ControllerPort
                    }
    STATUS          current
    DESCRIPTION
        "This collection of objects represents the information about
        the H.248 associations in distributed deployment model."
    ::= { ciscoSessBorderCtrlrMIBGroups 11 }

csbNotifEnabledGroup OBJECT-GROUP
    OBJECTS         {
                        csbSourceAlertNotifEnabled,
                        csbBlackListNotifEnabled,
                        csbAdjacencyStatusNotifEnabled,
                        csbServiceStateNotifEnabled,
                        csbCongestionAlarmNotifEnabled,
                        csbSLAViolationNotifEnabled,
                        csbRadiusConnectionStatusNotifEnabled,
                        csbDiameterConnectionStatusNotifEnabled,
                        csbH248ControllerStatusNotifEnabled
                    }
    STATUS          deprecated
    DESCRIPTION
        "This collection of objects represent the information about
        the standalone object which are used to tell the linkset
        notification truth value for each of the notification type."
    ::= { ciscoSessBorderCtrlrMIBGroups 12 }

csbNotificationGroupRev1 NOTIFICATION-GROUP
   NOTIFICATIONS    {
                        csbSourceAlertEvent,
                        csbDynamicBlackListEvent,
                        csbAdjacencyStatus,
                        csbServiceStateEvent,
                        csbSystemCongestionAlarmEvent,
                        csbSLAViolationRev1,
                        csbRadiusConnectionStatus,
                        csbDiameterConnectionStatus,
                        csbH248ControllerStatus
                    }
    STATUS          current
    DESCRIPTION
        "This collection of objects represents the notifications
        generated by the agent."
    ::= { ciscoSessBorderCtrlrMIBGroups 13 }

csbSLAGroupRev1 OBJECT-GROUP
    OBJECTS         {
                        csbSLAPolicyAccountName,
                        csbSLAPolicyScope,
                        csbSLAPolicyLimitRev1,
                        csbSLACurrentUsageRev1,
                        csbSLAViolationEvent,
                        csbSLAPolicyRestriction
                    }
    STATUS          current
    DESCRIPTION
        "This collection of objects represents the information related
        to the Service Level Agreement (SLA) violation notification."
    ::= { ciscoSessBorderCtrlrMIBGroups 14 }

csbNotifEnabledGroupRev1 OBJECT-GROUP
    OBJECTS         {
                        csbSourceAlertNotifEnabled,
                        csbBlackListNotifEnabled,
                        csbAdjacencyStatusNotifEnabled,
                        csbServiceStateNotifEnabled,
                        csbCongestionAlarmNotifEnabled,
                        csbSLAViolationNotifEnabledRev1,
                        csbRadiusConnectionStatusNotifEnabled,
                        csbDiameterConnectionStatusNotifEnabled,
                        csbH248ControllerStatusNotifEnabled
                    }
    STATUS          current
    DESCRIPTION
        "This collection of objects represent the information about
        the standalone object which are used to tell the linkset
        notification truth value for each of the notification type."
    ::= { ciscoSessBorderCtrlrMIBGroups 15 }

csbQOSAlertGroup OBJECT-GROUP
    OBJECTS         {
                        csbQOSAlertCurrentValue,
                        csbQOSAlertCurrentLevel,
                        csbQOSAlertPreviousLevel,
                        csbQOSNormalAlertCount,
                        csbQOSMinorAlertCount,
                        csbQOSCriticalAlertCount,
                        csbQOSMajorAlertCount,
                        csbQOSAlertType,
                        csbQOSAlertSummaryPeriod
                    }
    STATUS          current
    DESCRIPTION
        "This collection of objects representing the information about
        QOS statistics Alert traps."
    ::= { ciscoSessBorderCtrlrMIBGroups 16 }

csbNotificationGroupSup1 NOTIFICATION-GROUP
   NOTIFICATIONS    {
                        csbQOSUnansweredCallRatioClearEvent,
                        csbQOSPercentPktLostEvent,
                        csbQOSPercentPktLostClearEvent,
                        csbQOSPercentPktDropEvent,
                        csbQOSPercentPktDropClearEvent,
                        csbQOSRoundTripDelayEvent,
                        csbQOSRoundTripDelayClearEvent,
                        csbQOSLocalJitterEvent,
                        csbQOSLocalJitterClearEvent,
                        csbQOSRemoteJitterEvent,
                        csbQOSRemoteJitterClearEvent,
                        csbQOSMoscqeEvent,
                        csbQOSMoscqeClearEvent,
                        csbQOSUnansweredCallRatioEvent
                    }
    STATUS          current
    DESCRIPTION
        "This collection of objects represents the additional
        notifications generated by the agent."
    ::= { ciscoSessBorderCtrlrMIBGroups 17 }

csbNotifEnabledGroupSup1 OBJECT-GROUP
    OBJECTS         {
                        csbQOSAlertUnansweredCallRatioNotifEnabled,
                        csbQOSAlertPercentPktDropNotifEnabled,
                        csbQOSAlertRoundTripDelayNotifEnabled,
                        csbQOSAlertLocalJitterNotifEnabled,
                        csbQOSAlertRemoteJitterNotifEnabled,
                        csbQOSAlertPercentPktLostNotifEnabled,
                        csbQOSAlertMoscqeNotifEnabled
                    }
    STATUS          current
    DESCRIPTION
        "This collection of objects represent the information about
        the standalone object which are used to tell the linkset
        notification truth value for each of the notification type."
    ::= { ciscoSessBorderCtrlrMIBGroups 18 }

END
