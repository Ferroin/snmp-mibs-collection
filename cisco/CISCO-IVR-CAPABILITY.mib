CISCO-IVR-CAPABILITY DEFINITIONS ::= BEGIN

IMPORTS
        MODULE-IDENTITY
                FROM SNMPv2-SMI
        AGENT-CAPABILITIES
                FROM SNMPv2-CONF
        ciscoAgentCapability
                FROM CISCO-SMI;

ciscoIvrCapability MODULE-IDENTITY
        LAST-UPDATED    "200602020000Z"
        ORGANIZATION    "Cisco Systems, Inc."
        CONTACT-INFO
                "       Cisco Systems
                        Customer Service

                Postal: 170 W Tasman Drive
                        San Jose, CA  95134
                        USA

                   Tel: +1 800 553-NETS

                E-mail: cs-san@cisco.com"
        DESCRIPTION
                "Agent capabilities for
                 CISCO-IVR-MIB"

        REVISION  "200602020000Z"
        DESCRIPTION
                "Initial version of this MIB."
        ::= { ciscoAgentCapability 491 }

--
-- Agent capability for SanOS 3.0 (on MDS 9000 Platform)
--
ciscoIvrCapSanOSV30R1MDS9000 AGENT-CAPABILITIES
    PRODUCT-RELEASE "Cisco SanOS 3.0(1) on Cisco MDS 9000
                     series devices."
    STATUS          current
    DESCRIPTION     "Cisco Inter Virutal Storage Area
                     Network (Inter-VSAN) Routing
                     MIB capabilities"

    SUPPORTS        CISCO-IVR-MIB
    INCLUDES        {
                        civrZoneConfigurationGroup,
                        civrTopologyGroup,
                        civrStatsGroup,
                        civrNotificationGroup,
                        civrVirtualDomainsGroup,
                        civrGenericGroup,
                        civrTopologyGroupRev2,
                        civrZoneConfigurationGroupRev2,
                        civrNotificationGroupRev2
                    }
    ::= { ciscoIvrCapability 1 }

END
