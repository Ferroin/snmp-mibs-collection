CISCO-IETF-PW-MPLS-CAPABILITY DEFINITIONS ::= BEGIN

IMPORTS 
   MODULE-IDENTITY
       FROM SNMPv2-SMI 

   AGENT-CAPABILITIES
       FROM SNMPv2-CONF

   ciscoAgentCapability
       FROM CISCO-SMI;

  cpwVcMplsCapability MODULE-IDENTITY 
     LAST-UPDATED "200410061200Z"  -- 10 Oct 2004 12:00:00 GMT 
     ORGANIZATION 
        "Cisco Systems, Inc."
     CONTACT-INFO 
         "Thomas D. Nadeau 
          Postal: Cisco Systems, Inc. 
                  250 Apollo Drive 
                  Chelmsford, MA 01824 
          Tel:    +1-978-497-3051 
          Email:  tnadeau@cisco.com 

          MPLS MIB Development Team
          Postal: Cisco Systems, Inc.
                  250 Apollo Drive
                  Chelmsford, MA 01924
          Tel:    +1-978-497-3989
          Email:  ch-mpls-mib-dev@cisco.com " 
     DESCRIPTION 
         "Agent capabilities for CISCO-IETF-PW-MPLS-MIB"

-- Revision history. 
     REVISION "200410061200Z"  -- 10 Oct 2004 12:00:00 GMT
     DESCRIPTION
           "Made Cisco proprietary based on the PW-MPLS-MIB.my file
            extracted from draft-ietf-pwe3-pw-mpls-mib-00.txt"
     ::= { ciscoAgentCapability 429 } 

cpwVcMplsCapability AGENT-CAPABILITIES

PRODUCT-RELEASE "Cisco IOS 12.0(29)S"
STATUS      current
DESCRIPTION "pseudowire over MPLS MIB capabilities"

SUPPORTS   CISCO-IETF-PW-MPLS-MIB
INCLUDES    { cpwVcMplsGroup, cpwVcMplsNotificationGroup }

-- PW VC MPLS OBJECTS 

  VARIATION cpwVcMplsMplsType
    ACCESS read-only
    DESCRIPTION "read-only implementation"

  VARIATION cpwVcMplsExpBitsMode 
    ACCESS read-only
    DESCRIPTION "read-only implementation"

  VARIATION cpwVcMplsExpBits 
    ACCESS read-only
    DESCRIPTION "read-only implementation"

  VARIATION cpwVcMplsTtl 
    ACCESS read-only
    DESCRIPTION "read-only implementation"

  VARIATION cpwVcMplsLocalLdpID 
    ACCESS read-only
    DESCRIPTION "read-only implementation"

  VARIATION cpwVcMplsLocalLdpEntityID 
    ACCESS read-only
    DESCRIPTION "read-only implementation"

  VARIATION cpwVcMplsStorageType 
    ACCESS read-only
    DESCRIPTION "read-only implementation"

-- Pseudo Wire VC MPLS Outbound Objects 

  VARIATION cpwVcMplsOutboundLsrXcIndex 
    ACCESS read-only
    DESCRIPTION "read-only implementation"

  VARIATION cpwVcMplsOutboundTunnelIndex         
    ACCESS read-only
    DESCRIPTION "read-only implementation"

  VARIATION cpwVcMplsOutboundTunnelInstance      
    ACCESS read-only
    DESCRIPTION "read-only implementation"

  VARIATION cpwVcMplsOutboundTunnelLclLSR
    ACCESS read-only
    DESCRIPTION "read-only implementation"

  VARIATION cpwVcMplsOutboundTunnelPeerLSR      
    ACCESS read-only
    DESCRIPTION "read-only implementation"

  VARIATION cpwVcMplsOutboundIfIndex
    ACCESS read-only
    DESCRIPTION "read-only implementation"

  VARIATION cpwVcMplsOutboundRowStatus
    ACCESS read-only
    DESCRIPTION "read-only implementation"

  VARIATION cpwVcMplsOutboundStorageType
    ACCESS read-only
    DESCRIPTION "read-only implementation"

-- Pseudo Wire VC MPLS Inbound Tunnel Table 

  VARIATION cpwVcMplsInboundTunnelIndex        
    ACCESS read-only
    DESCRIPTION "read-only implementation"

  VARIATION cpwVcMplsInboundTunnelInstance  
    ACCESS read-only
    DESCRIPTION "read-only implementation"

  VARIATION cpwVcMplsInboundTunnelLclLSR
    ACCESS read-only
    DESCRIPTION "read-only implementation"

  VARIATION cpwVcMplsInboundTunnelPeerLSR
    ACCESS read-only
    DESCRIPTION "read-only implementation"

  VARIATION cpwVcMplsInboundIfIndex     
    ACCESS read-only
    DESCRIPTION "read-only implementation"

  VARIATION cpwVcMplsInboundRowStatus  
    ACCESS read-only
    DESCRIPTION "read-only implementation"

  VARIATION cpwVcMplsInboundStorageType
    ACCESS read-only
    DESCRIPTION "read-only implementation"

-- MPLS to VC Mapping Table is fully supported. 

-- TE MPLS Tunnel to VC Mapping Table is fully supported. 
     ::= { cpwVcMplsCapability 1 } 

END
