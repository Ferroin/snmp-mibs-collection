CISCO-VOICE-ENABLED-LINK-MIB DEFINITIONS ::= BEGIN

IMPORTS
        MODULE-IDENTITY,
        OBJECT-TYPE
                FROM SNMPv2-SMI
        DisplayString,
        MacAddress
                FROM SNMPv2-TC
        MODULE-COMPLIANCE,
        OBJECT-GROUP
                FROM SNMPv2-CONF
        ciscoExperiment
                FROM CISCO-SMI;

ciscoVoiceEnabledLinkMIB MODULE-IDENTITY
    LAST-UPDATED    "9905070000Z"
    ORGANIZATION    "Cisco Systems, Inc."
    CONTACT-INFO
        "       Cisco Systems
                Customer Service

        Postal: 170 W. Tasman Drive
                San Jose, CA  95134
                USA

        Tel: +1 800 553-NETS

        E-mail: cs-voice@cisco.com"
    DESCRIPTION
        "This MIB module provides information about Voice Enabled
         ATM and Frame Relay Links used by the Cisco Switched
         voice protocol.
         The Cisco Switched voice protocol passes the default MAC
         address for its node to the next node in the path, in both
         call setup messages and keepalive requests and responses.
         This MAC address is stored at the remote node to identify
         where the incoming pvc originates. This information is then
         used by the Cisco Voice Manager Application to determine
         the voice network topology."
    ::= { ciscoExperiment 53 }

-- Voice Enabled Link MIB objects definitions

cvenabledlinkMIBObjects OBJECT IDENTIFIER ::=
                                     { ciscoVoiceEnabledLinkMIB 1 }

-- The Voice Enabled Link MIB consists of the following group
-- [1] Voice Enabled Link Group (cvEnabledLink)

cvEnabledLink  OBJECT IDENTIFIER ::= { cvenabledlinkMIBObjects 1 }

--******************************************************************
-- Voice Enabled Link Group
--******************************************************************

--
-- Nodes Default MAC Address
--

cvEnabledDefaultMacAddr OBJECT-TYPE
        SYNTAX      MacAddress
        MAX-ACCESS  read-only
        STATUS      current
        DESCRIPTION
            "This item defines the Default MAC Address used by this
             node in call set up messages, keepalive requests and
             responses."
        ::= { cvEnabledLink 1 }

--
-- Voice Enabled Link Table
-- 

cvEnabledLinkTable OBJECT-TYPE
        SYNTAX      SEQUENCE OF CvEnabledLinkEntry
        MAX-ACCESS  not-accessible
        STATUS      current
        DESCRIPTION
            "This table contains information about ATM and Frame
             Relay Links used by voice over ATM and voice over Frame
             Relay calls." 
        ::= { cvEnabledLink 2 }

cvEnabledLinkEntry OBJECT-TYPE
        SYNTAX      CvEnabledLinkEntry
        MAX-ACCESS  not-accessible
        STATUS      current
        DESCRIPTION
            "The information regarding a single ATM or Frame Relay
             Link. An entry of this table is created when its
             associated pvc is enabled for carrying Cisco Switched
             voice traffic. The entry is deleted when its associated
             pvc is no longer enabled for Cisco Switched voice
             traffic."
        INDEX       { cvEnabledLinkIndex }
        ::= { cvEnabledLinkTable 1 }

CvEnabledLinkEntry ::=
        SEQUENCE {
            cvEnabledLinkIndex                         INTEGER,
            cvEnabledLinkType                          INTEGER,
            cvEnabledLinkInterfaceName                 DisplayString,
            cvEnabledLinkVpiDlci                       INTEGER,
            cvEnabledLinkVci                           INTEGER,
            cvEnabledLinkRemoteMacAddr                 MacAddress
        }

cvEnabledLinkIndex OBJECT-TYPE
        SYNTAX      INTEGER (0..2147483648)
        MAX-ACCESS  read-only
        STATUS      current
        DESCRIPTION
            "A monotonically increasing number, starting from zero,
             that is assigned to each link that is currently
             configured to carry Cisco Switched voice traffic. If a
             link is later unconfigured for voice traffic, the
             number assigned to it will not be reused. When the
             maximum value is reached, the value will wrap to zero
             and use a currently unassigned value."
        ::= { cvEnabledLinkEntry 1 }

cvEnabledLinkType OBJECT-TYPE
        SYNTAX      INTEGER {
             atm          (1),
             framerelay   (2)
        } 
        MAX-ACCESS  read-only
        STATUS      current
        DESCRIPTION
            "The object defines the type of link, either ATM or
             Frame Relay."
        ::= { cvEnabledLinkEntry 2 }

cvEnabledLinkInterfaceName OBJECT-TYPE
        SYNTAX      DisplayString 
        MAX-ACCESS  read-only
        STATUS      current
        DESCRIPTION
            "The object specifies the iFName of the peer interface
             that is used for the voice over ATM/FR call. A zero
             length string indicates that the value is unavailable."
        ::= { cvEnabledLinkEntry 3 }

cvEnabledLinkVpiDlci OBJECT-TYPE
        SYNTAX      INTEGER (0..4095)
        MAX-ACCESS  read-only
        STATUS      current
        DESCRIPTION
            "The VPI or DLCI used for this ATM/Frame Relay
             connection."
        ::= { cvEnabledLinkEntry 4 }

cvEnabledLinkVci OBJECT-TYPE
        SYNTAX      INTEGER (0..65535)
        MAX-ACCESS  read-only
        STATUS      current
        DESCRIPTION
            "The VCI used, if it is an ATM connection."
        ::= { cvEnabledLinkEntry 5 }

cvEnabledLinkRemoteMacAddr OBJECT-TYPE
        SYNTAX      MacAddress
        MAX-ACCESS  read-only 
        STATUS      current
        DESCRIPTION
            "The default MAC address of the node at the other end of
             the link."
        ::= { cvEnabledLinkEntry 6 }

--
-- Notification
--

ciscoVoiceEnabledLinkMIBNotificationPrefix OBJECT IDENTIFIER ::=
        { ciscoVoiceEnabledLinkMIB 2 }
ciscoVoiceEnabledLinkMIBNotifications OBJECT IDENTIFIER ::=
        { ciscoVoiceEnabledLinkMIBNotificationPrefix 0 }

--
-- Conformancy, Compliance and Group Objects
--

ciscoVoiceEnabledlinkMIBConformance OBJECT IDENTIFIER ::=
                            { ciscoVoiceEnabledLinkMIB 3 }
ciscoVoiceEnabledlinkMIBCompliances OBJECT IDENTIFIER ::=
                            { ciscoVoiceEnabledlinkMIBConformance 1 }
ciscoVoiceEnabledlinkMIBGroups      OBJECT IDENTIFIER ::=
                            { ciscoVoiceEnabledlinkMIBConformance 2 }

-- compliance statements

ciscoVoiceEnabledlinkMIBCompliance MODULE-COMPLIANCE
        STATUS      current
        DESCRIPTION
            "The compliance statement for entities which
             implement the CISCO VOICE ENABLED LINK MIB"
        MODULE      -- this module
        MANDATORY-GROUPS
            { cvEnabledMacAddrGroup,
              cvEnabledLinkGroup }
        ::= { ciscoVoiceEnabledlinkMIBCompliances 1 }

-- units of conformance

cvEnabledMacAddrGroup OBJECT-GROUP
        OBJECTS {
            cvEnabledDefaultMacAddr
        }
        STATUS      current
        DESCRIPTION
            "A collection of objects providing the Default Mac 
             Address capability."
        ::= { ciscoVoiceEnabledlinkMIBGroups 1 }

cvEnabledLinkGroup OBJECT-GROUP
        OBJECTS {
            cvEnabledLinkIndex,
            cvEnabledLinkType,
            cvEnabledLinkInterfaceName,            
            cvEnabledLinkVpiDlci,                      
            cvEnabledLinkVci,                      
            cvEnabledLinkRemoteMacAddr
        }
        STATUS      current
        DESCRIPTION
            "A collection of objects providing the Voice Enabled Link
             entry capability."
        ::= { ciscoVoiceEnabledlinkMIBGroups 2 }

END
