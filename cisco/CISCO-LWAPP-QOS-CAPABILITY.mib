CISCO-LWAPP-QOS-CAPABILITY DEFINITIONS ::= BEGIN

IMPORTS
        MODULE-IDENTITY
                FROM SNMPv2-SMI
        AGENT-CAPABILITIES
                FROM SNMPv2-CONF
        ciscoAgentCapability
                FROM CISCO-SMI;

ciscoLwappQosCapability      MODULE-IDENTITY  
        LAST-UPDATED         "200605150000Z"
        ORGANIZATION         "Cisco Systems, Inc."
        CONTACT-INFO
                "             Cisco Systems
                              Customer Service

                      Postal: 170 W Tasman Drive
                              San Jose, CA  95134
                              USA

                         Tel: +1 800 553-NETS

                      E-mail: cs-wnbu-snmp@cisco.com"
        DESCRIPTION
                "Agent capabilities for CISCO-LWAPP-QOS-MIB. "
        REVISION      "200605150000Z"
        DESCRIPTION
                "Initial version of this MIB module. "
        ::= { ciscoAgentCapability 505 }

ciscoLwappQosCapabilityCUWNSV4R0 AGENT-CAPABILITIES

PRODUCT-RELEASE         "Cisco Unified Wireless Network Software
                        Release 4.0 for Cisco WLAN Controllers"
        STATUS          current
        DESCRIPTION     "CISCO-LWAPP-QOS-MIB capabilities. "
        SUPPORTS        CISCO-LWAPP-QOS-MIB
        INCLUDES        {
                        ciscoLwappQosDot11aConfigGroup,
                        ciscoLwappQosDot11bConfigGroup,
                        ciscoLwappQosDot11WlanConfigGroup,
                        ciscoLwappQosDot11CacStatsGroup
                        }   

        VARIATION       cLQd11aVoiceMaxAdmBandwidth
        DESCRIPTION
                        "The range of values supported are
                        40 to 85. "

        VARIATION       cLQd11aVoiceMaxRoamBandwidth
        DESCRIPTION
                        "The range of values supported are
                        0 to 25. "

        VARIATION       cLQd11aVideoMaxRoamBandwidth
        DESCRIPTION
                        "The range of values supported are
                        0 to 25. "

        VARIATION       cLQd11bVoiceMaxAdmBandwidth                        
        DESCRIPTION
                        "The range of values supported are
                        40 to 85. "

        VARIATION       cLQd11bVoiceMaxRoamBandwidth
        DESCRIPTION
                        "The range of values supported are
                        0 to 25. "

        VARIATION       cLQd11bVideoMaxRoamBandwidth
        DESCRIPTION
                        "The range of values supported are
                        0 to 25. "

        VARIATION       cLQd11aGprProbeInterval
        DESCRIPTION
                        "The range of values supported are
                        10 to 50. "

        VARIATION       cLQd11bGprProbeInterval
        DESCRIPTION
                        "The range of values supported are
                        10 to 50. "
        ::= { ciscoLwappQosCapability 1 }
END
