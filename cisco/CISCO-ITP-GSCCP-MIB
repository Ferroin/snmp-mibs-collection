CISCO-ITP-GSCCP-MIB DEFINITIONS ::= BEGIN

IMPORTS
    Counter32,
    Gauge32,
    MODULE-IDENTITY,
    NOTIFICATION-TYPE,
    OBJECT-TYPE,
    Unsigned32
        FROM SNMPv2-SMI
    MODULE-COMPLIANCE,
    NOTIFICATION-GROUP,
    OBJECT-GROUP
        FROM SNMPv2-CONF
    RowStatus,
    TimeStamp,
    TruthValue,
    TEXTUAL-CONVENTION
        FROM SNMPv2-TC
    CItpTcDisplayPC,
    CItpTcGtaLongAddr,
    CItpTcGtaLongDisplay,
    CItpTcGtaLongDisplayLen,
    CItpTcNAI,
    CItpTcNetworkName,
    CItpTcNumberingPlan,
    CItpTcPointCode,
    CItpTcSubSystemNumber,
    CItpTcTranslationType,
    CItpTcTableLoadStatus,
    CItpTcURL,
    CItpTcXuaName
        FROM CISCO-ITP-TC-MIB
    cgspCLLICode,
    cgspEventSequenceNumber,
    cgspInstNetwork
        FROM CISCO-ITP-GSP-MIB
    EntPhysicalIndexOrZero
        FROM CISCO-TC
    ciscoMgmt
        FROM CISCO-SMI;

ciscoGsccpMIB MODULE-IDENTITY
    LAST-UPDATED    "201003050000Z"
    ORGANIZATION    "Cisco Systems, Inc."
    CONTACT-INFO
            "Cisco Systems, Inc
            Customer Service

            Postal: 170 W. Tasman Drive
            San Jose, CA  95134
            USA

            Tel: +1 800 553-NETS

            E-mail: cs-ss7@cisco.com"
    DESCRIPTION
        "The MIB for signalling Connection Control Part(SCCP)
        messages transported over Signalling System
        No. 7 (SS7) Network via Cisco IP Transfer
        Point.

        This MIB provides information specified
        in ITU Q752 Monitoring and Measurements for
        Signalling System No. 7(SS7) Network.

        The Cisco IP Transfer Point (ITP) is a hardware
        and software solution that transports SS7 traffic
        using IP. Each ITP node provides function similar
        to SS7 Signalling point.

        The relevant ITU documents describing this technology
        is the ITU Q series, including ITU Q.700: Introduction
        to CCITT Signalling System No. 7 and ITU Q.701
        Functional description of the message transfer part
        (MTP) of Signalling System No. 7.

        The IETF Working Group Signalling Transport (SIGTRAN)
        has defined MTP3 User Adaptation (M3UA) and SCCP
        User Adaptation (SUA) protocols. The drafts can be
        found at:
        http://www.ietf.org/html.charters/sigtran-charter.html

        This MIB consists of the following tables:
          Instance Table
          Concerned Point Code List Table
          Mated Application (MAP) Table
          Global Title Translation (GTT) Selector Table
          Global Title Address (GTA) Table
          Application Group Table
          Prefix Conversion Table
          Translation Entries Table
          Global Title Errors Table

        Abbreviations:
          CDPA  - Called Party Address
          CGPA  - Calling Party Address
          CLLI  - Common Language Location Codes
          CR    - Connection Request message
          CREF  - Connection Refusal message
          DPC   - Destination Point Code
          ERR   - Error message
          GTA   - Global Title Address
          GTI   - Global Title Indicator
          GTT   - Global Title Translation
          LUDT  - long unitdata message
          LUDTS - long unitdata service message
          M2PA  - MTP2 Peer-to-Peer Adaptation Layer
          M3UA  - MTP3-User Adaptation
          MAP   - Mated Application Table
          MSU   - Message Signal Unit
          MTP   - Message Transport Protocol
          MTP2  - Layer 2 of Message Transport Protocol
          MTP3  - Layer 3 of Message Transport Protocol
          NAI   - Nature of Address Indicator
          NP    - Numbering Plan
          OPC   - Originating Point Code
          PC    - Point Code
          RTN   - Route Table Name
          RSR   - Reset Request message
          SCCP  - Signalling Connection Control Part
          SCTP  - Stream Transmission Protocol(RFC 2960)
          SI    - Signalling Indicator
          SP    - Signalling Point
          SLC   - Signalling Link Code
          SLS   - Signalling Link Selector
          SSN   - Subsystem Number
          SUA   - SCCP-User Adaptation
          TFR   - Transfer Restricted messages
          TT    - Title Translation
          UDT   - unitdata message
          UDTS  - unitdata service message
          XUDT  - extended unitdata message
          XUDTS - extended unitdata service message"
    REVISION        "200911080000Z"
    DESCRIPTION
        "Following additional objects are added.
        cgsccpGttSelTable object:
            cgsccpGttNextSelName,cgsccpGttNextSelRefed"
    REVISION        "200905250000Z"
    DESCRIPTION
        "Added wrr(6) into CgsccpGttMultInd for GTT
        weighted loadshare"
    REVISION        "200811240000Z"
    DESCRIPTION
        "Following additional objects are added.
        cgsccpInstTable objects:
        cgsccpInstReassUnsup, cgsccpInstReassFail
        cgsccpInstSegUnsup, cgsccpInstSegFail.

        CgsccpGttMapTable objects:
        cgsccpGttMapCongLvl1, cgsccpGttMapCongLvl2,
        cgsccpGttMapCongLvl3, cgsccpGttMapSSPRcvd,
        cgsccpGttMapSSARcvd.

        CgsccpGttErrorsTable objects:
        cgsccpGttErrorsReassUnsupported,
        cgsccpGttErrorsReassFailure,
        cgsccpGttErrorsSegUnsupported,
        cgsccpGttErrorsSegFailure.

        cgsccpSSNTable objects:
        cgsccpSSNNumProhibits,
        cgsccpSSNClassNumAllows

        cgsccpSSNClassTable objects:
        cgsccpSSNClassUDTMsgsSent, cgsccpSSNClassUDTMsgsRcvd,
        cgsccpSSNClassXUDTMsgsSent, cgsccpSSNClassXUDTMsgsRcvd,
        cgsccpSSNClassLUDTMsgsSent, cgsccpSSNClassLUDTMsgsRcvd.

        Notification objects:
        ciscoGsccpSegReassUnsup, ciscoGsccpSOGReceived,
        ciscoGsccpRmtCongestion, ciscoGsccpLocalSsStateChange."
    REVISION        "200511100000Z"
    DESCRIPTION
        "Clarify description for CgsccpGttQOS textual
        convention and ciscoGsccpGttErrors object.
        Added cgsccpGttTranslatePhysicalIndex object to
        the cgsccpGttTranslateTable.  Change default value
        cgsccpGttSelQOS and cgsccpGttGtaQOS objects to
        255."
    REVISION        "200412220000Z"
    DESCRIPTION
        "New cgsccpGttPref2EncodingScheme object to allow
        customer to specify encoding scheme when
        performing internation translation."
    REVISION        "200411160000Z"
    DESCRIPTION
        "New ciscoGsccpGttErrors notification to indicate
        global title translation errors.

        The following objects were added to support new
        notification.

        cgsccpGttErrorPeriod,
        cgsccpGttErrorRecoveryCount,
        cgsccpInstErrorIndicator,
        cgsccpGttTransErrorsNotifEnabled,
        cgsccpGttErrorsSelectorNotFound,
        cgsccpGttErrorsIncorrectFormat,
        cgsccpGttErrorsGtaNotFound,
        cgsccpGttErrorsHopViolation,
        cgsccpGttErrorsMapNotFound,
        cgsccpGttErrorsUnequipedSS,
        cgsccpGttErrorsSccpUnavailable,
        cgsccpGttErrorsDpcUnavailable,
        cgsccpGttErrorsSsUnavailable,
        cgsccpGttErrorsDpcCongested,
        cgsccpGttErrorsSsCongested,
        cgsccpGttErrorsRouteFailure,
        cgsccpGttErrorsSccpUnqualified"
    REVISION        "200404300000Z"
    DESCRIPTION
        "Deprecated table cgsccpGttAppGrTable and added
        cgsccpGttAppGr2Table.
        Also added 'cgpa' enumeration to CgsccpGttMultInd
        textual-convention."
    REVISION        "200309300000Z"
    DESCRIPTION
        "Changes to allow cross instance Global title
        translation.

        Added following objects:
             cgsccpGttAppGrNetwork
             cgsccpGttGtaNetwork"
    REVISION        "200308210000Z"
    DESCRIPTION
        "Changes to allow GTT prefix conversion
        to be specified per instance.

        Added the following table:
           cgsccpGttPref2Table

        Deprecated the following table:
           cgsccpGttPrefTable"
    REVISION        "200303030000Z"
    DESCRIPTION
        "Initial version of this MIB module."
    ::= { ciscoMgmt 335 }

-- Top-level structure of the MIB

ciscoGsccpMIBNotifs  OBJECT IDENTIFIER
    ::= { ciscoGsccpMIB 0 }

ciscoGsccpMIBObjects  OBJECT IDENTIFIER
    ::= { ciscoGsccpMIB 1 }

ciscoGsccpMIBConform  OBJECT IDENTIFIER
    ::= { ciscoGsccpMIB 2 }

cgsccpScalars  OBJECT IDENTIFIER
    ::= { ciscoGsccpMIBObjects 1 }

cgsccpInst  OBJECT IDENTIFIER
    ::= { ciscoGsccpMIBObjects 2 }

cgsccpGttConPc  OBJECT IDENTIFIER
    ::= { ciscoGsccpMIBObjects 3 }

cgsccpGttMap  OBJECT IDENTIFIER
    ::= { ciscoGsccpMIBObjects 4 }

cgsccpGttSel  OBJECT IDENTIFIER
    ::= { ciscoGsccpMIBObjects 5 }

cgsccpGttGta  OBJECT IDENTIFIER
    ::= { ciscoGsccpMIBObjects 6 }

cgsccpGttAppGr  OBJECT IDENTIFIER
    ::= { ciscoGsccpMIBObjects 7 }

cgsccpGttPref  OBJECT IDENTIFIER
    ::= { ciscoGsccpMIBObjects 8 }

cgsccpGttTranslate  OBJECT IDENTIFIER
    ::= { ciscoGsccpMIBObjects 9 }

cgsccpGttPref2  OBJECT IDENTIFIER
    ::= { ciscoGsccpMIBObjects 10 }

cgsccpGttAppGr2  OBJECT IDENTIFIER
    ::= { ciscoGsccpMIBObjects 11 }

cgsccpGttErrors  OBJECT IDENTIFIER
    ::= { ciscoGsccpMIBObjects 12 }

cgsccpSSN  OBJECT IDENTIFIER
    ::= { ciscoGsccpMIBObjects 13 }

cgsccpClassSsn  OBJECT IDENTIFIER
    ::= { ciscoGsccpMIBObjects 14 }

cgsccpNotificationsInfo  OBJECT IDENTIFIER
    ::= { ciscoGsccpMIBObjects 15 }

-- ********************************************************************
-- *                                                                  *
-- * Textual Conventions                                              *
-- *                                                                  *
-- ********************************************************************

CgsccpConPcListName ::= TEXTUAL-CONVENTION
    STATUS          current
    DESCRIPTION
        "The configured name associated with SCCP GTT
        Concerned Point Code list name."
    SYNTAX          OCTET STRING (SIZE (0..12))

CgsccpGttSelName ::= TEXTUAL-CONVENTION
    STATUS          current
    DESCRIPTION
        "The configured name associated with SCCP GTT
        Selector."
    SYNTAX          OCTET STRING (SIZE (0..12))

CgsccpGttAppName ::= TEXTUAL-CONVENTION
    STATUS          current
    DESCRIPTION
        "The configured name associated with SCCP GTT
        Application Group."
    SYNTAX          OCTET STRING (SIZE (0..12))

CgsccpGttPrefName ::= TEXTUAL-CONVENTION
    STATUS          current
    DESCRIPTION
        "The configured name associated with SCCP GTT
        Prefix Conversion table.

        This name is supported as octet string containing
        administrative information in human-readable form.

        The use of control codes should be avoided.

        The use of newline should be avoided.

        The use of leading or trailing white space should
        be avoided."
    SYNTAX          OCTET STRING (SIZE (0..12))

CgsccpGttDisplaySS ::= TEXTUAL-CONVENTION
    STATUS          current
    DESCRIPTION
        "The subsystem number in display format."
    SYNTAX          OCTET STRING (SIZE (0..3))

CgsccpGttAppCost ::= TEXTUAL-CONVENTION
    STATUS          current
    DESCRIPTION
        "The cost associated with an entry in SCCP GTT
        Application Group."
    SYNTAX          Unsigned32 (1..8)

CgsccpGttAppType ::= TEXTUAL-CONVENTION
    STATUS          current
    DESCRIPTION
        "The list of application types in Application Group
        'pc'    : The application type is a point code.
        'pcssn' : The application type is a point code
                  and subsystem number (SSN).
        'as'    : The application type is an M3UA or SUA
                  Application Server (AS)."
    SYNTAX          INTEGER  {
                        pc(1),
                        pcssn(2),
                        as(3)
                    }

CgsccpGttMapType ::= TEXTUAL-CONVENTION
    STATUS          current
    DESCRIPTION
        "The list of SCCP GTT Mated Application type
        'primary' : The mated application is primary
        'backup'  : The mated application is backup."
    SYNTAX          INTEGER  {
                        primary(1),
                        backup(2)
                    }

CgsccpGttGtaResType ::= TEXTUAL-CONVENTION
    STATUS          current
    DESCRIPTION
        "The list of SCCP GTT Result Type
        'pc'    : The GTA translates to a point code.
        'pcssn' : The GTA translates to a point code
                  and optional SSN
        'app'   : The GTA translates to a GTT
                  Application Group.
        'as'    : The GTA translates to an M3UA or
                  SUA Application Server (AS) name."
    SYNTAX          INTEGER  {
                        pc(1),
                        pcssn(2),
                        app(3),
                        as(4)
                    }

CgsccpGttRoutingInd ::= TEXTUAL-CONVENTION
    STATUS          current
    DESCRIPTION
        "The SCCP GTT Routing Indicator
        'ri2gt'     : Set RI to GT
        'ri2ssn'    : Set RI to SSN
        'ssnRI2ssn' : Replace SSN and set RI to GT
        'ssnRI2gt'  : Replace SSN and set RI to SSN
        'replTT'    : Replace the TT
        'riNotAppl' : RI is not applicable
        'riUndef'   : RI is undefined."
    SYNTAX          INTEGER  {
                        ri2gt(1),
                        ri2ssn(2),
                        ssnRI2gt(3),
                        ssnRI2ssn(4),
                        replTT(5),
                        riNotAppl(6),
                        riUndef(7)
                    }

CgsccpGttMapPcStatus ::= TEXTUAL-CONVENTION
    STATUS          current
    DESCRIPTION
        "The list of SCCP GTT Mated App point code status
        'allowed'    : The mated application is allowed
        'prohibited' : The mated application is prohibited."
    SYNTAX          INTEGER  {
                        allowed(1),
                        prohibited(2)
                    }

CgsccpGttMapSsStatus ::= TEXTUAL-CONVENTION
    STATUS          current
    DESCRIPTION
        "The list of SCCP GTT Mated App subsystem status
        'allowed' : The mated application is allowed
        'prohibited'   : The mated application is prohibited."
    SYNTAX          INTEGER  {
                        allowed(1),
                        prohibited(2)
                    }

CgsccpGttMultInd ::= TEXTUAL-CONVENTION
    STATUS          current
    DESCRIPTION
        "The list of SCCP GTT Multiplicity Indicator
        'solitary' : The application is solitary
        'shared'   : The application is shared
        'dominant' : The application is dominant
        'cost'     : The application uses cost
        'cgpa'     : The application is shared and uses calling
                     party address and weighting factor.
        'wrr'      : The application is shared and uses weighting
                     factor"
    SYNTAX          INTEGER  {
                        solitary(1),
                        shared(2),
                        dominant(3),
                        cost(4),
                        cgpa(5),
                        wrr(6)
                    }

CgsccpGttMapCongStatus ::= TEXTUAL-CONVENTION
    STATUS          current
    DESCRIPTION
        "The list of SCCP GTT Mated App congestion status
        'NotCong'    : The point code not congested
        'CongLevel1' : The congestion level 1
        'CongLevel2' : The congestion level 2
        'CongLevel3' : The congestion level 3."
    SYNTAX          INTEGER  {
                        notCong(1),
                        congLevel1(2),
                        congLevel2(3),
                        congLevel3(4)
                    }

CgsccpGttTransType ::= TEXTUAL-CONVENTION
    STATUS          current
    DESCRIPTION
        "The SCCP GTT Translation Type (TT)."
    SYNTAX          Unsigned32 (0..255)

CgsccpGttQOS ::= TEXTUAL-CONVENTION
    STATUS          current
    DESCRIPTION
        "The SCCP GTT Quality of Service (QOS).  The '255' value
        indicates that QOS is not configured."
    SYNTAX          Unsigned32 (0..255)

CgsccpGttGlobalTitleInd ::= TEXTUAL-CONVENTION
    STATUS          current
    DESCRIPTION
        "The SCCP GTT Global Title Indicator (GTI).
        The following values are generally used:
         No global title included (0),
         For ITU,  GT includes NAI only (1),
         For ANSI, GT includes TT, NP and encoding scheme (1),
         GT includes only TT (2),
         GT includes TT, NP and encoding scheme (3),
         GT includes TT, NP, encoding scheme, NAI (4),
         Maximum GTI (15),
         Invalid GTI (253),
         Wild    GTI (254)."
    REFERENCE
        "The Global Title Indicator is defined in the
         International Telecommunication Union standard Q.713:
         Specifications of Signalling System No. 7 - Signalling
         Connection Control Part (SCCP) section 3.4.1 Address
         Indicator."
    SYNTAX          Unsigned32 (0..255)

CgsccpClass ::= TEXTUAL-CONVENTION
    STATUS          current
    DESCRIPTION
        "The SCCP class of service involved
        'class0' : class 0 of SCCP 
        'class1' : class 1 of SCCP 
        'class2' : class 2 of SCCP 
        'class3' : class 3 of SCCP 
        'class4' : class 4 of SCCP"
    SYNTAX          INTEGER  {
                        class0(1),
                        class1(2),
                        class2(3),
                        class3(4),
                        class4(5)
                    }

-- *************************************************************
-- *                                                           *
-- * Scalars                                                   *
-- *                                                           *
-- *************************************************************

cgsccpGttTranslateSample OBJECT-TYPE
    SYNTAX          Unsigned32 (1..60)
    UNITS           "seconds"
    MAX-ACCESS      read-write
    STATUS          current
    DESCRIPTION
        "The length of the sample interval used to collect
        number of maximum Global Title Translations per second." 
    ::= { cgsccpScalars 1 }

cgsccpGttTranslatePeriod OBJECT-TYPE
    SYNTAX          Unsigned32 (1..3600)
    UNITS           "seconds"
    MAX-ACCESS      read-write
    STATUS          current
    DESCRIPTION
        "The length of the period used to collect the maximum
        Global Title Translations rate.  Samples are calculated
        for the time period specified by the
        cgsccpGttTranslateSample object." 
    ::= { cgsccpScalars 2 }

cgsccpGttMapStateNotifEnabled OBJECT-TYPE
    SYNTAX          TruthValue
    MAX-ACCESS      read-write
    STATUS          current
    DESCRIPTION
        "The Map state notification truth value.
        'true'  Indicates that the ciscoGsccpGttMapStateChange
                notification is to be generated when the
                state changes. That is, the notification
                generation is enabled.
        'false' Indicates that the ciscoGsccpGttMapStateChange
                notification generation is disabled."
    DEFVAL          { false } 
    ::= { cgsccpScalars 3 }

cgsccpGttLoadTableNotifEnabled OBJECT-TYPE
    SYNTAX          TruthValue
    MAX-ACCESS      read-write
    STATUS          current
    DESCRIPTION
        "The GTT load table notification truth value.
        'true'  Indicates that the ciscoGsccpGttLoadTable
                notification is to be generated when the
                a configuration is loaded. That is, the
                notification generation is enabled.
        'false' Indicates that the ciscoGsccpGttLoadTable
                notification generation is disabled."
    DEFVAL          { false } 
    ::= { cgsccpScalars 4 }

cgsccpGttTransErrorsNotifEnabled OBJECT-TYPE
    SYNTAX          TruthValue
    MAX-ACCESS      read-write
    STATUS          current
    DESCRIPTION
        "The global title translation errors notification truth
        value as follows.

        'true'  Indicates that the ciscoGsccpGttErrors
               notification is to be generated when the
               a configuration is loaded. That is, the
               notification generation is enabled.
        'false' Indicates that the ciscoGsccpGttErrors
               notification generation is disabled."
    DEFVAL          { false } 
    ::= { cgsccpScalars 5 }

cgsccpGttErrorPeriod OBJECT-TYPE
    SYNTAX          Unsigned32 (30..3600)
    UNITS           "seconds"
    MAX-ACCESS      read-write
    STATUS          current
    DESCRIPTION
        "The length of the sample window used to collect
        global title translations errors."
    DEFVAL          { 300 } 
    ::= { cgsccpScalars 6 }

cgsccpGttErrorRecoveryCount OBJECT-TYPE
    SYNTAX          Unsigned32 (1..10)
    UNITS           "windows"
    MAX-ACCESS      read-write
    STATUS          current
    DESCRIPTION
        "The number contiguous sample windows that have to be
        error free before the ciscoGsccpGttErrors notifications
        will be generated indicating end of global title
        translation errors condition."
    DEFVAL          { 3 } 
    ::= { cgsccpScalars 7 }
-- *************************************************************
-- *                                                           *
-- * Information per Signalling Point                          *
-- *                                                           *
-- *************************************************************

cgsccpInstTable OBJECT-TYPE
    SYNTAX          SEQUENCE OF CgsccpInstTableEntry 
    MAX-ACCESS      not-accessible
    STATUS          current
    DESCRIPTION
        "SCCP information per instance of signalling
        point."
    ::= { cgsccpInst 1 }

cgsccpInstTableEntry OBJECT-TYPE
    SYNTAX          CgsccpInstTableEntry
    MAX-ACCESS      not-accessible
    STATUS          current
    DESCRIPTION
        "Global Title information per instance of
        signalling point."
    INDEX           { cgspInstNetwork } 
    ::= { cgsccpInstTable 1 }

CgsccpInstTableEntry ::= SEQUENCE {
        cgsccpInstTotalMsgs          Counter32,
        cgsccpInstLocalMsgs          Counter32,
        cgsccpInstTotalGttMsgs       Counter32,
        cgsccpInstUDTMsgsSent        Counter32,
        cgsccpInstUDTSMsgsSent       Counter32,
        cgsccpInstUDTSMsgsAttempted  Counter32,
        cgsccpInstUDTMsgsRcvd        Counter32,
        cgsccpInstUDTSMsgsRcvd       Counter32,
        cgsccpInstXUDTMsgsSent       Counter32,
        cgsccpInstXUDTSMsgsAttempted Counter32,
        cgsccpInstXUDTSMsgsSent      Counter32,
        cgsccpInstXUDTMsgsRcvd       Counter32,
        cgsccpInstXUDTSMsgsRcvd      Counter32,
        cgsccpInstLUDTMsgsSent       Counter32,
        cgsccpInstLUDTSMsgsSent      Counter32,
        cgsccpInstLUDTMsgsRcvd       Counter32,
        cgsccpInstLUDTSMsgsRcvd      Counter32,
        cgsccpInstCrToMtp            Counter32,
        cgsccpInstCrefToMtp          Counter32,
        cgsccpInstCrFromMtp          Counter32,
        cgsccpInstCrefFromMtp        Counter32,
        cgsccpInstRsrToMtp           Counter32,
        cgsccpInstRsrFromMtp         Counter32,
        cgsccpInstErrToMtp           Counter32,
        cgsccpInstErrFromMtp         Counter32,
        cgsccpInstQ752T7E1           Counter32,
        cgsccpInstInvalidGttFormat   Counter32,
        cgsccpInstQ752T7E13          Counter32,
        cgsccpInstMapNotFound        Counter32,
        cgsccpInstQ752T7E7           Counter32,
        cgsccpInstGttConfigStatus    CItpTcTableLoadStatus,
        cgsccpInstConfigTS           TimeStamp,
        cgsccpInstGttConfigTS        TimeStamp,
        cgsccpInstLastURL            CItpTcURL,
        cgsccpInstConPcTableEntries  Gauge32,
        cgsccpInstMapTableEntries    Gauge32,
        cgsccpInstGtaTableEntries    Gauge32,
        cgsccpInstSelTableEntries    Gauge32,
        cgsccpInstAppGrTableEntries  Gauge32,
        cgsccpInstRowStatus          RowStatus,
        cgsccpInstPrefTableEntries   Gauge32,
        cgsccpInstQ752Unqualified    Counter32,
        cgsccpInstErrorIndicator     TruthValue,
        cgsccpInstReassUnsup         Counter32,
        cgsccpInstReassFail          Counter32,
        cgsccpInstSegUnsup           Counter32,
        cgsccpInstSegFail            Counter32
}

cgsccpInstTotalMsgs OBJECT-TYPE
    SYNTAX          Counter32
    UNITS           "packets"
    MAX-ACCESS      read-only
    STATUS          current
    DESCRIPTION
        "This counter is incremented every time a message is
        handled from a local or remote subsystem(Q752/9.3)."
    REFERENCE
        "ITU  Q752 Monitoring and Measurements for Signalling
         System No. 7(SS7) Network Table 9.  ANSI GR-82-CORE
         6.4.3 Translation Type Measurements item 1." 
    ::= { cgsccpInstTableEntry 1 }

cgsccpInstLocalMsgs OBJECT-TYPE
    SYNTAX          Counter32
    UNITS           "packets"
    MAX-ACCESS      read-only
    STATUS          current
    DESCRIPTION
        "This counter is incremented every time a message is
        handled from a local subsystem(Q752/9.4)."
    REFERENCE
        "ITU  Q752 Monitoring and Measurements for Signalling
         System No. 7(SS7) Network Table 9." 
    ::= { cgsccpInstTableEntry 2 }

cgsccpInstTotalGttMsgs OBJECT-TYPE
    SYNTAX          Counter32
    UNITS           "packets"
    MAX-ACCESS      read-only
    STATUS          current
    DESCRIPTION
        "This counter is incremented every time a message
        requiring global title translation (Q752/9.5) is
        handled."
    REFERENCE
        "ITU  Q752 Monitoring and Measurements for Signalling
         System No. 7(SS7) Network Table 9.  ANSI GR-82-CORE
         6.4.2 System Total Measurements Item 7." 
    ::= { cgsccpInstTableEntry 3 }

cgsccpInstUDTMsgsSent OBJECT-TYPE
    SYNTAX          Counter32
    UNITS           "packets"
    MAX-ACCESS      read-only
    STATUS          current
    DESCRIPTION
        "This counter is incremented every time a
        unitdata (UDT) message is sent (Q752/9 bis.1)."
    REFERENCE
        "ITU  Q752 Monitoring and Measurements for Signalling
         System No. 7(SS7) Network Table 9." 
    ::= { cgsccpInstTableEntry 4 }

cgsccpInstUDTSMsgsSent OBJECT-TYPE
    SYNTAX          Counter32
    UNITS           "packets"
    MAX-ACCESS      read-only
    STATUS          current
    DESCRIPTION
        "This counter is incremented every time a unitdata
        service (UDTS) message is sent (Q752/9 bis.2)."
    REFERENCE
        "ITU  Q752 Monitoring and Measurements for Signalling
         System No. 7(SS7) Network Table 9." 
    ::= { cgsccpInstTableEntry 5 }

cgsccpInstUDTSMsgsAttempted OBJECT-TYPE
    SYNTAX          Counter32
    UNITS           "packets"
    MAX-ACCESS      read-only
    STATUS          current
    DESCRIPTION
        "This counter is incremented every time a unitdata
        service (UDTS) message attempted, but may or may
        not be sent.  The actual number of unitdata
        service (UDTS) message sent is reflected in the
        cgsccpInstUDTSMsgsSent object." 
    ::= { cgsccpInstTableEntry 6 }

cgsccpInstUDTMsgsRcvd OBJECT-TYPE
    SYNTAX          Counter32
    UNITS           "packets"
    MAX-ACCESS      read-only
    STATUS          current
    DESCRIPTION
        "This counter is incremented every time a unitdata
        (UDT) message is received (Q752/9 bis.3)."
    REFERENCE
        "ITU  Q752 Monitoring and Measurements for Signalling
         System No. 7(SS7) Network Table 9." 
    ::= { cgsccpInstTableEntry 7 }

cgsccpInstUDTSMsgsRcvd OBJECT-TYPE
    SYNTAX          Counter32
    UNITS           "packets"
    MAX-ACCESS      read-only
    STATUS          current
    DESCRIPTION
        "This counter is incremented every time a unitdata
        service (UDTS) message is received  (Q752/9 bis.4)."
    REFERENCE
        "ITU  Q752 Monitoring and Measurements for Signalling
         System No. 7(SS7) Network Table 9." 
    ::= { cgsccpInstTableEntry 8 }

cgsccpInstXUDTMsgsSent OBJECT-TYPE
    SYNTAX          Counter32
    UNITS           "packets"
    MAX-ACCESS      read-only
    STATUS          current
    DESCRIPTION
        "This counter is incremented every time an extended
        unitdata (XUDT) message is sent (Q752/9 bis.13)."
    REFERENCE
        "ITU  Q752 Monitoring and Measurements for Signalling
         System No. 7(SS7) Network Table 9." 
    ::= { cgsccpInstTableEntry 9 }

cgsccpInstXUDTSMsgsAttempted OBJECT-TYPE
    SYNTAX          Counter32
    UNITS           "packets"
    MAX-ACCESS      read-only
    STATUS          current
    DESCRIPTION
        "This counter is incremented every time an extended
        unitdata service (XUDTS) message attempted, but may
        or may not be sent.  The actual number of extended
        unitdata service (UDTS) message sent is reflected
        in the cgsccpInstXUDTMsgsSent object." 
    ::= { cgsccpInstTableEntry 10 }

cgsccpInstXUDTSMsgsSent OBJECT-TYPE
    SYNTAX          Counter32
    UNITS           "packets"
    MAX-ACCESS      read-only
    STATUS          current
    DESCRIPTION
        "This counter is incremented every time an extended
        unitdata service (XUDTS) message is sent
        (Q752/9 bis.14)."
    REFERENCE
        "ITU  Q752 Monitoring and Measurements for Signalling
         System No. 7(SS7) Network Table 9." 
    ::= { cgsccpInstTableEntry 11 }

cgsccpInstXUDTMsgsRcvd OBJECT-TYPE
    SYNTAX          Counter32
    UNITS           "packets"
    MAX-ACCESS      read-only
    STATUS          current
    DESCRIPTION
        "This counter is incremented every time a extended
        unitdata (XUDT) message is received (Q752/9 bis.15)."
    REFERENCE
        "ITU  Q752 Monitoring and Measurements for Signalling
         System No. 7(SS7) Network Table 9." 
    ::= { cgsccpInstTableEntry 12 }

cgsccpInstXUDTSMsgsRcvd OBJECT-TYPE
    SYNTAX          Counter32
    UNITS           "packets"
    MAX-ACCESS      read-only
    STATUS          current
    DESCRIPTION
        "This counter is incremented every time a extended
        unitdata service (XUDTS) message is received
        (Q752/9 bis.16)."
    REFERENCE
        "ITU  Q752 Monitoring and Measurements for Signalling
         System No. 7(SS7) Network Table 9." 
    ::= { cgsccpInstTableEntry 13 }

cgsccpInstLUDTMsgsSent OBJECT-TYPE
    SYNTAX          Counter32
    UNITS           "packets"
    MAX-ACCESS      read-only
    STATUS          current
    DESCRIPTION
        "This counter is incremented every time a long
        unitdata (LUDT) message is sent (Q752/9 bis.17)."
    REFERENCE
        "ITU  Q752 Monitoring and Measurements for Signalling
         System No. 7(SS7) Network Table 9." 
    ::= { cgsccpInstTableEntry 14 }

cgsccpInstLUDTSMsgsSent OBJECT-TYPE
    SYNTAX          Counter32
    UNITS           "packets"
    MAX-ACCESS      read-only
    STATUS          current
    DESCRIPTION
        "This counter is incremented every time a long
        unitdata (LUDT) service message is sent
        (Q752/9 bis.18)."
    REFERENCE
        "ITU  Q752 Monitoring and Measurements for Signalling
         System No. 7(SS7) Network Table 9." 
    ::= { cgsccpInstTableEntry 15 }

cgsccpInstLUDTMsgsRcvd OBJECT-TYPE
    SYNTAX          Counter32
    UNITS           "packets"
    MAX-ACCESS      read-only
    STATUS          current
    DESCRIPTION
        "This counter is incremented every time a long
        unitdata (LUDT) message is received (Q752/9 bis.19)."
    REFERENCE
        "ITU  Q752 Monitoring and Measurements for Signalling
         System No. 7(SS7) Network Table 9." 
    ::= { cgsccpInstTableEntry 16 }

cgsccpInstLUDTSMsgsRcvd OBJECT-TYPE
    SYNTAX          Counter32
    UNITS           "packets"
    MAX-ACCESS      read-only
    STATUS          current
    DESCRIPTION
        "This counter is incremented every time a long
        unitdata (LUDT) service message is received
        (Q752/9 bis.20)."
    REFERENCE
        "ITU  Q752 Monitoring and Measurements for Signalling
         System No. 7(SS7) Network Table 9." 
    ::= { cgsccpInstTableEntry 17 }

cgsccpInstCrToMtp OBJECT-TYPE
    SYNTAX          Counter32
    UNITS           "packets"
    MAX-ACCESS      read-only
    STATUS          current
    DESCRIPTION
        "This counter is incremented every time a Connection
        Request(CR) messages sent to MTP.  This count
        include ISDN-UP with embedded CRs (Q752/9 bis.5)."
    REFERENCE
        "ITU  Q752 Monitoring and Measurements for Signalling
         System No. 7(SS7) Network Table 9." 
    ::= { cgsccpInstTableEntry 18 }

cgsccpInstCrefToMtp OBJECT-TYPE
    SYNTAX          Counter32
    UNITS           "packets"
    MAX-ACCESS      read-only
    STATUS          current
    DESCRIPTION
        "This counter is incremented every time a Connection
        Refusal (CREF) message is sent to MTP (Q752/9 bis.6)."
    REFERENCE
        "ITU  Q752 Monitoring and Measurements for Signalling
         System No. 7(SS7) Network Table 9." 
    ::= { cgsccpInstTableEntry 19 }

cgsccpInstCrFromMtp OBJECT-TYPE
    SYNTAX          Counter32
    UNITS           "packets"
    MAX-ACCESS      read-only
    STATUS          current
    DESCRIPTION
        "This counter is incremented every time a Connection
        Request messages received from MTP. This count
        includes ISDN- UP with embedded CRs (Q752/9 bis.7)."
    REFERENCE
        "ITU  Q752 Monitoring and Measurements for Signalling
         System No. 7(SS7) Network Table 9." 
    ::= { cgsccpInstTableEntry 20 }

cgsccpInstCrefFromMtp OBJECT-TYPE
    SYNTAX          Counter32
    UNITS           "packets"
    MAX-ACCESS      read-only
    STATUS          current
    DESCRIPTION
        "This counter is incremented every time a Connection
        Refusal (CREF) message is received from
        MTP (Q752/9 bis.8)."
    REFERENCE
        "ITU  Q752 Monitoring and Measurements for Signalling
         System No. 7(SS7) Network Table 9." 
    ::= { cgsccpInstTableEntry 21 }

cgsccpInstRsrToMtp OBJECT-TYPE
    SYNTAX          Counter32
    UNITS           "packets"
    MAX-ACCESS      read-only
    STATUS          current
    DESCRIPTION
        "This counter is incremented every time a Reset Request
        (RSR) message is sent to MTP (Q752/9 bis.9)."
    REFERENCE
        "ITU  Q752 Monitoring and Measurements for Signalling
         System No. 7(SS7) Network Table 9." 
    ::= { cgsccpInstTableEntry 22 }

cgsccpInstRsrFromMtp OBJECT-TYPE
    SYNTAX          Counter32
    UNITS           "packets"
    MAX-ACCESS      read-only
    STATUS          current
    DESCRIPTION
        "This counter is incremented every time a Reset Request
        (RSR) message is received from MTP (Q752/9 bis.10)."
    REFERENCE
        "ITU  Q752 Monitoring and Measurements for Signalling
         System No. 7(SS7) Network Table 9." 
    ::= { cgsccpInstTableEntry 23 }

cgsccpInstErrToMtp OBJECT-TYPE
    SYNTAX          Counter32
    UNITS           "packets"
    MAX-ACCESS      read-only
    STATUS          current
    DESCRIPTION
        "This counter is incremented every time a Error Message
        (ERR) message is sent to MTP (Q752/9 bis.11)."
    REFERENCE
        "ITU  Q752 Monitoring and Measurements for Signalling
         System No. 7(SS7) Network Table 9." 
    ::= { cgsccpInstTableEntry 24 }

cgsccpInstErrFromMtp OBJECT-TYPE
    SYNTAX          Counter32
    UNITS           "packets"
    MAX-ACCESS      read-only
    STATUS          current
    DESCRIPTION
        "This counter is incremented every time a Error Message
        (ERR) message is received from MTP (Q752/9 bis.12)."
    REFERENCE
        "ITU  Q752 Monitoring and Measurements for Signalling
         System No. 7(SS7) Network Table 9." 
    ::= { cgsccpInstTableEntry 25 }

cgsccpInstQ752T7E1 OBJECT-TYPE
    SYNTAX          Counter32
    UNITS           "packets"
    MAX-ACCESS      read-only
    STATUS          current
    DESCRIPTION
        "This counter is incremented every time a translation
        was requested for a combination of Translation Type,
        Numbering Plan and Nature of Address for which no
        translation exists in the signalling point.  This
        occurs when no selector is available for the
        combination of parameters provided in the MSU."
    REFERENCE
        "Q752 - Monitoring and measurements for SS7 Network
         table 7 entry 1. ANSI GR-82-CORE 6.4.2 System Total
         Measurements Item 8." 
    ::= { cgsccpInstTableEntry 26 }

cgsccpInstInvalidGttFormat OBJECT-TYPE
    SYNTAX          Counter32
    UNITS           "packets"
    MAX-ACCESS      read-only
    STATUS          current
    DESCRIPTION
        "This counter is incremented every time an invalid
        Global Title format is found while performing the
        global title translation.  This counter provides
        information related to the Q752 table 7 entry 8
        measurement indicating syntax error detected in MSU"
    REFERENCE
        "Q752 - Monitoring and measurements for SS7 Network
         table 7 entry 8. ANSI GR-82-CORE
         6.4.2 System Total Measurements Item 9." 
    ::= { cgsccpInstTableEntry 27 }

cgsccpInstQ752T7E13 OBJECT-TYPE
    SYNTAX          Counter32
    UNITS           "packets"
    MAX-ACCESS      read-only
    STATUS          current
    DESCRIPTION
        "This counter is incremented every time a
        hop count violation is found in the MSU."
    REFERENCE
        "Q752 - Monitoring and measurements for SS7 Network
         table 7 entry 13" 
    ::= { cgsccpInstTableEntry 28 }

cgsccpInstMapNotFound OBJECT-TYPE
    SYNTAX          Counter32
    UNITS           "packets"
    MAX-ACCESS      read-only
    STATUS          current
    DESCRIPTION
        "This counter is incremented every time a global
        title translation is successful to a certain
        PC/SSN but it was not found in the GTT
        Mated Application table." 
    ::= { cgsccpInstTableEntry 29 }

cgsccpInstQ752T7E7 OBJECT-TYPE
    SYNTAX          Counter32
    UNITS           "packets"
    MAX-ACCESS      read-only
    STATUS          current
    DESCRIPTION
        "This counter is incremented every time a global
        title translation could not be performed due to an
        unequipped subsystem (SS)."
    REFERENCE
        "Q752 - Monitoring and measurements for SS7 Network
         table 7 entry 13" 
    ::= { cgsccpInstTableEntry 30 }

cgsccpInstGttConfigStatus OBJECT-TYPE
    SYNTAX          CItpTcTableLoadStatus
    MAX-ACCESS      read-only
    STATUS          current
    DESCRIPTION
        "The status of the current load or status from
        the prior load operation." 
    ::= { cgsccpInstTableEntry 31 }

cgsccpInstConfigTS OBJECT-TYPE
    SYNTAX          TimeStamp
    MAX-ACCESS      read-only
    STATUS          current
    DESCRIPTION
        "The value of sysUpTime at the time of the last creation
        or deletion or modification of an entry in the
        cgsccpGttConPcTable, cgsccpGttMapTable,
        cgsccpGttSelTable, cgsccpGttGtaTable,
        cgsccpGttAppGr2Table, or cgsccpGttPref2Table.

        If the local network management subsystem is
        re-initialization, then this object contains the
        sysUpTime at the time when this occurred. This value
        can be used to prevent unnecessary walks of the
        these tables." 
    ::= { cgsccpInstTableEntry 32 }

cgsccpInstGttConfigTS OBJECT-TYPE
    SYNTAX          TimeStamp
    MAX-ACCESS      read-only
    STATUS          current
    DESCRIPTION
        "The value of sysUpTime at the time of the last
        load of the GTT table using file format." 
    ::= { cgsccpInstTableEntry 33 }

cgsccpInstLastURL OBJECT-TYPE
    SYNTAX          CItpTcURL
    MAX-ACCESS      read-only
    STATUS          current
    DESCRIPTION
        "The URL used to load GTT tables." 
    ::= { cgsccpInstTableEntry 34 }

cgsccpInstConPcTableEntries OBJECT-TYPE
    SYNTAX          Gauge32
    UNITS           "entries"
    MAX-ACCESS      read-only
    STATUS          current
    DESCRIPTION
        "The number of entries in the cgsccpGttConPcTable
        Table for this instance.  Or in other words,
        the number concerned point-code entries for this
        signalling point." 
    ::= { cgsccpInstTableEntry 35 }

cgsccpInstMapTableEntries OBJECT-TYPE
    SYNTAX          Gauge32
    UNITS           "entries"
    MAX-ACCESS      read-only
    STATUS          current
    DESCRIPTION
        "The number of entries in the cgsccpGttMapTable
        Table for this instance.  Or in other words,
        the number of GTT Mated Application entries
        for this signalling point." 
    ::= { cgsccpInstTableEntry 36 }

cgsccpInstGtaTableEntries OBJECT-TYPE
    SYNTAX          Gauge32
    UNITS           "entries"
    MAX-ACCESS      read-only
    STATUS          current
    DESCRIPTION
        "The number of entries in the cgsccpGttGtaTable
        Table for this instance.  Or in other words,
        the number of GTT Global Title Address Table
        entries for this signalling point." 
    ::= { cgsccpInstTableEntry 37 }

cgsccpInstSelTableEntries OBJECT-TYPE
    SYNTAX          Gauge32
    UNITS           "entries"
    MAX-ACCESS      read-only
    STATUS          current
    DESCRIPTION
        "The number of entries in the cgsccpGttSelTable
        Table for this instance.  Or in other words,
        the number of GTT Selector Table entries for
        this signalling point." 
    ::= { cgsccpInstTableEntry 38 }

cgsccpInstAppGrTableEntries OBJECT-TYPE
    SYNTAX          Gauge32
    UNITS           "entries"
    MAX-ACCESS      read-only
    STATUS          current
    DESCRIPTION
        "The number of entries in the cgsccpGttAppGrTable
        Table for this instance.  Or in other words,
        the number of GTT Application Group Table entries
        for this signalling point." 
    ::= { cgsccpInstTableEntry 39 }

cgsccpInstRowStatus OBJECT-TYPE
    SYNTAX          RowStatus
    MAX-ACCESS      read-create
    STATUS          current
    DESCRIPTION
        "The object is used by a management station to
        create or delete the row entry in cgsccpInstTable
        following the RowStatus textual convention." 
    ::= { cgsccpInstTableEntry 40 }

cgsccpInstPrefTableEntries OBJECT-TYPE
    SYNTAX          Gauge32
    UNITS           "entries"
    MAX-ACCESS      read-only
    STATUS          current
    DESCRIPTION
        "The number of entries in the cgsccpGttPref2Table
        Table for this instance.  Or in other words,
        the number of GTT prefix conversion table entries
        for this signalling point." 
    ::= { cgsccpInstTableEntry 41 }

cgsccpInstQ752Unqualified OBJECT-TYPE
    SYNTAX          Counter32
    UNITS           "packets"
    MAX-ACCESS      read-only
    STATUS          current
    DESCRIPTION
        "This counter is incremented every time a global
        title translation is unsuccessful and the error
        type not covered by other specific error types." 
    ::= { cgsccpInstTableEntry 42 }

cgsccpInstErrorIndicator OBJECT-TYPE
    SYNTAX          TruthValue
    MAX-ACCESS      read-only
    STATUS          current
    DESCRIPTION
        "This object indicates whether global title
        translation errors have occurred in last interval
        specified by the cgsccpGttErrorPeriod object."
    DEFVAL          { false } 
    ::= { cgsccpInstTableEntry 43 }

cgsccpInstReassUnsup OBJECT-TYPE
    SYNTAX          Counter32
    MAX-ACCESS      read-only
    STATUS          current
    DESCRIPTION
        "This counter is incremented every time a SCCP message
        is dropped due to an unsupported reassembly feature
        at this instance." 
    ::= { cgsccpInstTableEntry 44 }

cgsccpInstReassFail OBJECT-TYPE
    SYNTAX          Counter32
    MAX-ACCESS      read-only
    STATUS          current
    DESCRIPTION
        "This counter is incremented every time a SCCP message
        is dropped due to a reassembly failure at this instance." 
    ::= { cgsccpInstTableEntry 45 }

cgsccpInstSegUnsup OBJECT-TYPE
    SYNTAX          Counter32
    MAX-ACCESS      read-only
    STATUS          current
    DESCRIPTION
        "This counter is incremented every time a SCCP message
        is dropped due to an unsupported segmentation feature
        at this instance." 
    ::= { cgsccpInstTableEntry 46 }

cgsccpInstSegFail OBJECT-TYPE
    SYNTAX          Counter32
    MAX-ACCESS      read-only
    STATUS          current
    DESCRIPTION
        "This counter is incremented every time a SCCP message
        is dropped due to a segmentation failure at this instance." 
    ::= { cgsccpInstTableEntry 47 }

-- *************************************************************
-- *                                                           *
-- * SCCP - GTT Concerned Point Code Table                     *
-- *                                                           *
-- *************************************************************

cgsccpGttConPcTable OBJECT-TYPE
    SYNTAX          SEQUENCE OF CgsccpGttConPcTableEntry 
    MAX-ACCESS      not-accessible
    STATUS          current
    DESCRIPTION
        "A table of concerned point codes."
    ::= { cgsccpGttConPc 1 }

cgsccpGttConPcTableEntry OBJECT-TYPE
    SYNTAX          CgsccpGttConPcTableEntry
    MAX-ACCESS      not-accessible
    STATUS          current
    DESCRIPTION
        "A list of concerned point codes."
    INDEX           {
                        cgspInstNetwork,
                        cgsccpGttConPcListName,
                        cgsccpGttConPointCode
                    } 
    ::= { cgsccpGttConPcTable 1 }

CgsccpGttConPcTableEntry ::= SEQUENCE {
        cgsccpGttConPcListName  CgsccpConPcListName,
        cgsccpGttConPointCode   CItpTcPointCode,
        cgsccpGttConPcRowStatus RowStatus
}

cgsccpGttConPcListName OBJECT-TYPE
    SYNTAX          CgsccpConPcListName
    MAX-ACCESS      not-accessible
    STATUS          current
    DESCRIPTION
        "The name of the Concerned Point Code list." 
    ::= { cgsccpGttConPcTableEntry 1 }

cgsccpGttConPointCode OBJECT-TYPE
    SYNTAX          CItpTcPointCode
    MAX-ACCESS      not-accessible
    STATUS          current
    DESCRIPTION
        "The concerned point code for SCCP GTT." 
    ::= { cgsccpGttConPcTableEntry 2 }

cgsccpGttConPcRowStatus OBJECT-TYPE
    SYNTAX          RowStatus
    MAX-ACCESS      read-create
    STATUS          current
    DESCRIPTION
        "The object is used by a management station to
        create or delete the row entry in cgsccpGttConPcTable
        following the RowStatus textual convention." 
    ::= { cgsccpGttConPcTableEntry 3 }

-- *************************************************************
-- *                                                           *
-- * SCCP - GTT Application Group Table                        *
-- *                                                           *
-- * When the new multiplicity indicator 'cgpa' is introduced, *
-- * the range for the index cgsccpGttAppGrCost is changed from*
-- * 1..8 to 0..999. In order to support this change this table*
-- * is deprecated and replaced by cgsccpGttAppGr2Table.       *
-- *************************************************************

cgsccpGttAppGrTable OBJECT-TYPE
    SYNTAX          SEQUENCE OF CgsccpGttAppGrTableEntry 
    MAX-ACCESS      not-accessible
    STATUS          deprecated
    DESCRIPTION
        "A table of SCCP GTT Application Group Table entries."
    ::= { cgsccpGttAppGr 1 }

cgsccpGttAppGrTableEntry OBJECT-TYPE
    SYNTAX          CgsccpGttAppGrTableEntry
    MAX-ACCESS      not-accessible
    STATUS          deprecated
    DESCRIPTION
        "A list of SCCP GTT Application Group attributes."
    INDEX           {
                        cgspInstNetwork,
                        cgsccpGttAppGrName,
                        cgsccpGttAppGrCost,
                        cgsccpGttAppGrEntNum
                    } 
    ::= { cgsccpGttAppGrTable 1 }

CgsccpGttAppGrTableEntry ::= SEQUENCE {
        cgsccpGttAppGrName      CgsccpGttAppName,
        cgsccpGttAppGrCost      CgsccpGttAppCost,
        cgsccpGttAppGrEntNum    Unsigned32,
        cgsccpGttAppGrType      CgsccpGttAppType,
        cgsccpGttAppGrPc        CItpTcPointCode,
        cgsccpGttAppGrSsn       CItpTcSubSystemNumber,
        cgsccpGttAppGrRi        CgsccpGttRoutingInd,
        cgsccpGttAppGrMult      CgsccpGttMultInd,
        cgsccpGttAppGrRefCount  Gauge32,
        cgsccpGttAppGrAsName    CItpTcXuaName,
        cgsccpGttAppGrNewSsn    CItpTcSubSystemNumber,
        cgsccpGttAppGrNumUsed   Counter32,
        cgsccpGttAppGrRowStatus RowStatus,
        cgsccpGttAppGrNetwork   CItpTcNetworkName
}

cgsccpGttAppGrName OBJECT-TYPE
    SYNTAX          CgsccpGttAppName
    MAX-ACCESS      not-accessible
    STATUS          deprecated
    DESCRIPTION
        "The GTT Application Group name." 
    ::= { cgsccpGttAppGrTableEntry 1 }

cgsccpGttAppGrCost OBJECT-TYPE
    SYNTAX          CgsccpGttAppCost
    MAX-ACCESS      not-accessible
    STATUS          deprecated
    DESCRIPTION
        "The cost for the item in the GTT Application Group." 
    ::= { cgsccpGttAppGrTableEntry 2 }

cgsccpGttAppGrEntNum OBJECT-TYPE
    SYNTAX          Unsigned32 (0..65535)
    MAX-ACCESS      not-accessible
    STATUS          deprecated
    DESCRIPTION
        "The entry number used to identify each application
        group entry that have the same cost." 
    ::= { cgsccpGttAppGrTableEntry 3 }

cgsccpGttAppGrType OBJECT-TYPE
    SYNTAX          CgsccpGttAppType
    MAX-ACCESS      read-create
    STATUS          deprecated
    DESCRIPTION
        "The type of the item in the GTT Application Group." 
    ::= { cgsccpGttAppGrTableEntry 4 }

cgsccpGttAppGrPc OBJECT-TYPE
    SYNTAX          CItpTcPointCode
    MAX-ACCESS      read-create
    STATUS          deprecated
    DESCRIPTION
        "The point code specified by the item in the GTT
        Application Group.  When the cgsccpGttAppGrType
        object has 'pc' or pcssn' values this object
        is required when entry is created.  Otherwise,
        this value does not apply and can default to
        zero."
    DEFVAL          { 0 } 
    ::= { cgsccpGttAppGrTableEntry 5 }

cgsccpGttAppGrSsn OBJECT-TYPE
    SYNTAX          CItpTcSubSystemNumber
    MAX-ACCESS      read-create
    STATUS          deprecated
    DESCRIPTION
        "The subsystem number (SSN) specified by the item
        in the GTT Application Group. It is valid only when
        cgsccpGttAppGrType is 'pcssn'. Otherwise it is zero."
    DEFVAL          { 0 } 
    ::= { cgsccpGttAppGrTableEntry 6 }

cgsccpGttAppGrRi OBJECT-TYPE
    SYNTAX          CgsccpGttRoutingInd
    MAX-ACCESS      read-create
    STATUS          deprecated
    DESCRIPTION
        "The routing indicator (RI) specified by the item
        in the GTT Application Group." 
    ::= { cgsccpGttAppGrTableEntry 7 }

cgsccpGttAppGrMult OBJECT-TYPE
    SYNTAX          CgsccpGttMultInd
    MAX-ACCESS      read-create
    STATUS          deprecated
    DESCRIPTION
        "The multiplicity of the GTT Application Group." 
    ::= { cgsccpGttAppGrTableEntry 8 }

cgsccpGttAppGrRefCount OBJECT-TYPE
    SYNTAX          Gauge32 (0..2147483647)
    MAX-ACCESS      read-only
    STATUS          deprecated
    DESCRIPTION
        "The number of global title addresses referring to
        this application group." 
    ::= { cgsccpGttAppGrTableEntry 9 }

cgsccpGttAppGrAsName OBJECT-TYPE
    SYNTAX          CItpTcXuaName
    MAX-ACCESS      read-create
    STATUS          deprecated
    DESCRIPTION
        "The Application Server (AS) name specified by the item
        in the GTT Application Group. It is valid only when
        cgsccpGttAppGrType is 'as'. Otherwise it
        is a zero length string."
    DEFVAL          { "" } 
    ::= { cgsccpGttAppGrTableEntry 10 }

cgsccpGttAppGrNewSsn OBJECT-TYPE
    SYNTAX          CItpTcSubSystemNumber
    MAX-ACCESS      read-create
    STATUS          deprecated
    DESCRIPTION
        "The new subsystem number (SSN) specified by the item
        in the GTT Application Group.  It is valid only when
        cgsccpGttAppGrType is 'as'.  Otherwise it is zero."
    DEFVAL          { 0 } 
    ::= { cgsccpGttAppGrTableEntry 11 }

cgsccpGttAppGrNumUsed OBJECT-TYPE
    SYNTAX          Counter32
    MAX-ACCESS      read-only
    STATUS          deprecated
    DESCRIPTION
        "The number of times this item in the GTT Application
        Group is used successfully." 
    ::= { cgsccpGttAppGrTableEntry 12 }

cgsccpGttAppGrRowStatus OBJECT-TYPE
    SYNTAX          RowStatus
    MAX-ACCESS      read-create
    STATUS          deprecated
    DESCRIPTION
        "The object is used by a management station to
        create or delete the row entry in cgsccpGttAppGrTable
        following the RowStatus textual convention." 
    ::= { cgsccpGttAppGrTableEntry 13 }

cgsccpGttAppGrNetwork OBJECT-TYPE
    SYNTAX          CItpTcNetworkName
    MAX-ACCESS      read-create
    STATUS          deprecated
    DESCRIPTION
        "The processing of global title translation may
        result in a packet being transferred from one
        network to another.  This object specifies
        the target network." 
    ::= { cgsccpGttAppGrTableEntry 14 }

-- *************************************************************
-- *                                                           *
-- * SCCP - GTT Mated Application Table                        *
-- *                                                           *
-- *************************************************************

cgsccpGttMapTable OBJECT-TYPE
    SYNTAX          SEQUENCE OF CgsccpGttMapTableEntry 
    MAX-ACCESS      not-accessible
    STATUS          current
    DESCRIPTION
        "A table of SCCP GTT Mated Application (MAP) entries."
    ::= { cgsccpGttMap 1 }

cgsccpGttMapTableEntry OBJECT-TYPE
    SYNTAX          CgsccpGttMapTableEntry
    MAX-ACCESS      not-accessible
    STATUS          current
    DESCRIPTION
        "A list of SCCP GTT MAP attributes."
    INDEX           {
                        cgspInstNetwork,
                        cgsccpGttMapPc,
                        cgsccpGttMapSsn
                    } 
    ::= { cgsccpGttMapTable 1 }

CgsccpGttMapTableEntry ::= SEQUENCE {
        cgsccpGttMapPc            CItpTcPointCode,
        cgsccpGttMapSsn           CItpTcSubSystemNumber,
        cgsccpGttMapDisplayPC     CItpTcDisplayPC,
        cgsccpGttMapDisplaySS     CgsccpGttDisplaySS,
        cgsccpGttMapType          CgsccpGttMapType,
        cgsccpGttMapPcStatus      CgsccpGttMapPcStatus,
        cgsccpGttMapSsStatus      CgsccpGttMapSsStatus,
        cgsccpGttMapMultInd       CgsccpGttMultInd,
        cgsccpGttMapBackupPc      CItpTcPointCode,
        cgsccpGttMapBackupSsn     CItpTcSubSystemNumber,
        cgsccpGttMapConPcList     CgsccpConPcListName,
        cgsccpGttMapReRouteOnCong TruthValue,
        cgsccpGttMapAdjacent      TruthValue,
        cgsccpGttMapLastSsUsed    TruthValue,
        cgsccpGttMapUsed          Counter32,
        cgsccpGttMapAltUsed       Counter32,
        cgsccpGttMapSccpUnavail   Counter32,
        cgsccpGttMapQ752T7E3Fail  Counter32,
        cgsccpGttMapQ752T7E3Un    Counter32,
        cgsccpGttMapQ752T7E4      Counter32,
        cgsccpGttMapQ752T7E5      Counter32,
        cgsccpGttMapQ752T7E6      Counter32,
        cgsccpGttMapRefCount      Gauge32,
        cgsccpGttMapCongStatus    CgsccpGttMapCongStatus,
        cgsccpGttMapRowStatus     RowStatus,
        cgsccpGttMapCongLvl1      Counter32,
        cgsccpGttMapCongLvl2      Counter32,
        cgsccpGttMapCongLvl3      Counter32,
        cgsccpGttMapSSPRcvd       Counter32,
        cgsccpGttMapSSARcvd       Counter32
}

cgsccpGttMapPc OBJECT-TYPE
    SYNTAX          CItpTcPointCode
    MAX-ACCESS      not-accessible
    STATUS          current
    DESCRIPTION
        "The point code for GTT MAP entry." 
    ::= { cgsccpGttMapTableEntry 1 }

cgsccpGttMapSsn OBJECT-TYPE
    SYNTAX          CItpTcSubSystemNumber
    MAX-ACCESS      not-accessible
    STATUS          current
    DESCRIPTION
        "The subsystem number (SSN) for GTT MAP entry." 
    ::= { cgsccpGttMapTableEntry 2 }

cgsccpGttMapDisplayPC OBJECT-TYPE
    SYNTAX          CItpTcDisplayPC
    MAX-ACCESS      read-only
    STATUS          current
    DESCRIPTION
        "The MAP point code in display format." 
    ::= { cgsccpGttMapTableEntry 3 }

cgsccpGttMapDisplaySS OBJECT-TYPE
    SYNTAX          CgsccpGttDisplaySS
    MAX-ACCESS      read-only
    STATUS          current
    DESCRIPTION
        "The MAP subsystem number in display format." 
    ::= { cgsccpGttMapTableEntry 4 }

cgsccpGttMapType OBJECT-TYPE
    SYNTAX          CgsccpGttMapType
    MAX-ACCESS      read-create
    STATUS          current
    DESCRIPTION
        "The GTT MAP subsystem type." 
    ::= { cgsccpGttMapTableEntry 5 }

cgsccpGttMapPcStatus OBJECT-TYPE
    SYNTAX          CgsccpGttMapPcStatus
    MAX-ACCESS      read-only
    STATUS          current
    DESCRIPTION
        "The GTT MAP point code status." 
    ::= { cgsccpGttMapTableEntry 6 }

cgsccpGttMapSsStatus OBJECT-TYPE
    SYNTAX          CgsccpGttMapSsStatus
    MAX-ACCESS      read-only
    STATUS          current
    DESCRIPTION
        "The GTT MAP subsystem status." 
    ::= { cgsccpGttMapTableEntry 7 }

cgsccpGttMapMultInd OBJECT-TYPE
    SYNTAX          CgsccpGttMultInd
    MAX-ACCESS      read-create
    STATUS          current
    DESCRIPTION
        "The GTT mated application multiplicity indicator." 
    ::= { cgsccpGttMapTableEntry 8 }

cgsccpGttMapBackupPc OBJECT-TYPE
    SYNTAX          CItpTcPointCode
    MAX-ACCESS      read-create
    STATUS          current
    DESCRIPTION
        "The backup point code for the mated Application.
        The special value of zero indicates that no backup
        point code has been specified."
    DEFVAL          { 0 } 
    ::= { cgsccpGttMapTableEntry 9 }

cgsccpGttMapBackupSsn OBJECT-TYPE
    SYNTAX          CItpTcSubSystemNumber
    MAX-ACCESS      read-create
    STATUS          current
    DESCRIPTION
        "The backup subsystem number for the mated
        Application.  The special value of zero indicates
        that no backup subsystem number has been
        specified."
    DEFVAL          { 0 } 
    ::= { cgsccpGttMapTableEntry 10 }

cgsccpGttMapConPcList OBJECT-TYPE
    SYNTAX          CgsccpConPcListName
    MAX-ACCESS      read-create
    STATUS          current
    DESCRIPTION
        "The concerned point code list for the mated
        Application.  The null string indicates that
        no concerned point code list has been specified."
    DEFVAL          { "" } 
    ::= { cgsccpGttMapTableEntry 11 }

cgsccpGttMapReRouteOnCong OBJECT-TYPE
    SYNTAX          TruthValue
    MAX-ACCESS      read-create
    STATUS          current
    DESCRIPTION
        "The GTT Mated App re-route on congestion truth value.
        'true'  Re-routing on congestion is enabled.
        'false' Re-routing on congestion is disabled."
    DEFVAL          { false } 
    ::= { cgsccpGttMapTableEntry 12 }

cgsccpGttMapAdjacent OBJECT-TYPE
    SYNTAX          TruthValue
    MAX-ACCESS      read-create
    STATUS          current
    DESCRIPTION
        "The GTT Mated App Point Code adjacent truth value.
        'true'  Indicates that MAP PC is adjacent.
        'false' Indicates that MAP PC is not adjacent."
    DEFVAL          { false } 
    ::= { cgsccpGttMapTableEntry 13 }

cgsccpGttMapLastSsUsed OBJECT-TYPE
    SYNTAX          TruthValue
    MAX-ACCESS      read-only
    STATUS          current
    DESCRIPTION
        "The GTT MAP last subsystem used truth value.
        'true'  It is the last used subsystem.
        'false' It is not the last used subsystem." 
    ::= { cgsccpGttMapTableEntry 14 }

cgsccpGttMapUsed OBJECT-TYPE
    SYNTAX          Counter32
    UNITS           "messages"
    MAX-ACCESS      read-only
    STATUS          current
    DESCRIPTION
        "This counter is incremented every time a message is
        routed by the GTT Mated Application." 
    ::= { cgsccpGttMapTableEntry 15 }

cgsccpGttMapAltUsed OBJECT-TYPE
    SYNTAX          Counter32
    UNITS           "messages"
    MAX-ACCESS      read-only
    STATUS          current
    DESCRIPTION
        "This counter is incremented every time a message is
        re-routed on congestion by the GTT Mated Application."
    REFERENCE
        "ANSI GR-82-CORE 6.4.2 System Total Measurements Item 12." 
    ::= { cgsccpGttMapTableEntry 16 }

cgsccpGttMapSccpUnavail OBJECT-TYPE
    SYNTAX          Counter32
    UNITS           "occurrences"
    MAX-ACCESS      read-only
    STATUS          current
    DESCRIPTION
        "This counter is incremented every time a SCCP
        is unavailable at the GTT Mated Application." 
    ::= { cgsccpGttMapTableEntry 17 }

cgsccpGttMapQ752T7E3Fail OBJECT-TYPE
    SYNTAX          Counter32
    UNITS           "occurrences"
    MAX-ACCESS      read-only
    STATUS          current
    DESCRIPTION
        "This counter is incremented every time a the MTP3
        layer failed at the GTT Mated Application."
    REFERENCE
        "Q752 - Monitoring and measurements for SS7 Network
         table 7 entry 3" 
    ::= { cgsccpGttMapTableEntry 18 }

cgsccpGttMapQ752T7E3Un OBJECT-TYPE
    SYNTAX          Counter32
    UNITS           "occurrences"
    MAX-ACCESS      read-only
    STATUS          current
    DESCRIPTION
        "This counter is incremented every time a point code
        is unavailable at the GTT Mated Application." 
    ::= { cgsccpGttMapTableEntry 19 }

cgsccpGttMapQ752T7E4 OBJECT-TYPE
    SYNTAX          Counter32
    UNITS           "occurrences"
    MAX-ACCESS      read-only
    STATUS          current
    DESCRIPTION
        "This counter is incremented every time a point code
        is congested at the GTT Mated Application."
    REFERENCE
        "Q752 - Monitoring and measurements for SS7 Network
         table 7 entry 4" 
    ::= { cgsccpGttMapTableEntry 20 }

cgsccpGttMapQ752T7E5 OBJECT-TYPE
    SYNTAX          Counter32
    UNITS           "occurrences"
    MAX-ACCESS      read-only
    STATUS          current
    DESCRIPTION
        "This counter is incremented every time a subsystem
        is unavailable at the GTT Mated Application."
    REFERENCE
        "Q752 - Monitoring and measurements for SS7 Network
         table 7 entry 5" 
    ::= { cgsccpGttMapTableEntry 21 }

cgsccpGttMapQ752T7E6 OBJECT-TYPE
    SYNTAX          Counter32
    UNITS           "occurrences"
    MAX-ACCESS      read-only
    STATUS          current
    DESCRIPTION
        "This counter is incremented every time a subsystem
        is congested at the GTT Mated Application."
    REFERENCE
        "Q752 - Monitoring and measurements for SS7 Network
         table 7 entry 6" 
    ::= { cgsccpGttMapTableEntry 22 }

cgsccpGttMapRefCount OBJECT-TYPE
    SYNTAX          Gauge32 (0..2147483647)
    MAX-ACCESS      read-only
    STATUS          current
    DESCRIPTION
        "The number of global title addresses referring to this
        MAP entry." 
    ::= { cgsccpGttMapTableEntry 23 }

cgsccpGttMapCongStatus OBJECT-TYPE
    SYNTAX          CgsccpGttMapCongStatus
    MAX-ACCESS      read-only
    STATUS          current
    DESCRIPTION
        "The status of congestion level for this MAP point code." 
    ::= { cgsccpGttMapTableEntry 24 }

cgsccpGttMapRowStatus OBJECT-TYPE
    SYNTAX          RowStatus
    MAX-ACCESS      read-create
    STATUS          current
    DESCRIPTION
        "The object is used by a management station to
        create or delete the row entry in cgsccpGttMapTable
        following the RowStatus textual convention." 
    ::= { cgsccpGttMapTableEntry 25 }

cgsccpGttMapCongLvl1 OBJECT-TYPE
    SYNTAX          Counter32
    MAX-ACCESS      read-only
    STATUS          current
    DESCRIPTION
        "This counter is incremented every time a congestion
        of level 1 is experienced by the remote Signalling  
        point corresponding to this MAP entry." 
    ::= { cgsccpGttMapTableEntry 26 }

cgsccpGttMapCongLvl2 OBJECT-TYPE
    SYNTAX          Counter32
    MAX-ACCESS      read-only
    STATUS          current
    DESCRIPTION
        "This counter is incremented every time a congestion
        of level 2 is experienced by the remote Signalling
        point corresponding to this MAP entry." 
    ::= { cgsccpGttMapTableEntry 27 }

cgsccpGttMapCongLvl3 OBJECT-TYPE
    SYNTAX          Counter32
    MAX-ACCESS      read-only
    STATUS          current
    DESCRIPTION
        "This counter is incremented every time a congestion
        of level 3 is experienced by the remote Signalling
        point corresponding to this MAP entry." 
    ::= { cgsccpGttMapTableEntry 28 }

cgsccpGttMapSSPRcvd OBJECT-TYPE
    SYNTAX          Counter32
    MAX-ACCESS      read-only
    STATUS          current
    DESCRIPTION
        "This counter is incremented every time a subsystem
        prohibited message is received from the remote Signalling
        point corresponding to this MAP entry." 
    ::= { cgsccpGttMapTableEntry 29 }

cgsccpGttMapSSARcvd OBJECT-TYPE
    SYNTAX          Counter32
    MAX-ACCESS      read-only
    STATUS          current
    DESCRIPTION
        "This counter is incremented every time a subsystem
        allowed message is received from the remote Signalling
        point corresponding to this MAP entry." 
    ::= { cgsccpGttMapTableEntry 30 }

-- *************************************************************
-- *                                                           *
-- * SCCP - GTT Selector Table                                 *
-- *                                                           *
-- *************************************************************

cgsccpGttSelTable OBJECT-TYPE
    SYNTAX          SEQUENCE OF CgsccpGttSelTableEntry 
    MAX-ACCESS      not-accessible
    STATUS          current
    DESCRIPTION
        "A table of SCCP GTT Selector entries."
    ::= { cgsccpGttSel 1 }

cgsccpGttSelTableEntry OBJECT-TYPE
    SYNTAX          CgsccpGttSelTableEntry
    MAX-ACCESS      not-accessible
    STATUS          current
    DESCRIPTION
        "A list of SCCP GTT Selector attributes."
    INDEX           {
                        cgspInstNetwork,
                        cgsccpGttSelTT,
                        cgsccpGttSelNAI,
                        cgsccpGttSelNP,
                        cgsccpGttSelGTI
                    } 
    ::= { cgsccpGttSelTable 1 }

CgsccpGttSelTableEntry ::= SEQUENCE {
        cgsccpGttSelTT           CgsccpGttTransType,
        cgsccpGttSelNAI          CItpTcNAI,
        cgsccpGttSelNP           CItpTcNumberingPlan,
        cgsccpGttSelGTI          CgsccpGttGlobalTitleInd,
        cgsccpGttSelName         CgsccpGttSelName,
        cgsccpGttSelNumPerf      Counter32,
        cgsccpGttQ752T7E2        Counter32,
        cgsccpGttSelQOS          CgsccpGttQOS,
        cgsccpGttSelRefCount     Gauge32,
        cgsccpGttSelPrePrefConv  CgsccpGttPrefName,
        cgsccpGttSelPostPrefConv CgsccpGttPrefName,
        cgsccpGttSelRowStatus    RowStatus,
        cgsccpGttNextSelName     CgsccpGttSelName,
        cgsccpGttNextSelRefed    Gauge32
}

cgsccpGttSelTT OBJECT-TYPE
    SYNTAX          CgsccpGttTransType
    MAX-ACCESS      not-accessible
    STATUS          current
    DESCRIPTION
        "Translation Type (TT) for this GTT Selector." 
    ::= { cgsccpGttSelTableEntry 1 }

cgsccpGttSelNAI OBJECT-TYPE
    SYNTAX          CItpTcNAI
    MAX-ACCESS      not-accessible
    STATUS          current
    DESCRIPTION
        "Nature of Address Indicator (NAI) for GTT Selector." 
    ::= { cgsccpGttSelTableEntry 2 }

cgsccpGttSelNP OBJECT-TYPE
    SYNTAX          CItpTcNumberingPlan
    MAX-ACCESS      not-accessible
    STATUS          current
    DESCRIPTION
        "Numbering Plan (NP) for this GTT Selector." 
    ::= { cgsccpGttSelTableEntry 3 }

cgsccpGttSelGTI OBJECT-TYPE
    SYNTAX          CgsccpGttGlobalTitleInd
    MAX-ACCESS      not-accessible
    STATUS          current
    DESCRIPTION
        "Global Title Indicator (GTI) for
        this GTT Selector." 
    ::= { cgsccpGttSelTableEntry 4 }

cgsccpGttSelName OBJECT-TYPE
    SYNTAX          CgsccpGttSelName
    MAX-ACCESS      read-create
    STATUS          current
    DESCRIPTION
        "The name of the GTT selector." 
    ::= { cgsccpGttSelTableEntry 5 }

cgsccpGttSelNumPerf OBJECT-TYPE
    SYNTAX          Counter32
    MAX-ACCESS      read-only
    STATUS          current
    DESCRIPTION
        "This counter is incremented every time a global title
        translations is performed using this GTT Selector." 
    ::= { cgsccpGttSelTableEntry 6 }

cgsccpGttQ752T7E2 OBJECT-TYPE
    SYNTAX          Counter32
    MAX-ACCESS      read-only
    STATUS          current
    DESCRIPTION
        "This counter is incremented every time a global title
        title translations was required and a selector was
        not found."
    REFERENCE
        "Q752 - Monitoring and measurements for SS7 Network
           table 7 entry 2. ANSI GR-82-CORE 6.4.2 System
           Total Measurements Item 10." 
    ::= { cgsccpGttSelTableEntry 7 }

cgsccpGttSelQOS OBJECT-TYPE
    SYNTAX          CgsccpGttQOS
    MAX-ACCESS      read-create
    STATUS          current
    DESCRIPTION
        "The SCCP GTT Selector specifies the QOS."
    DEFVAL          { 255 } 
    ::= { cgsccpGttSelTableEntry 8 }

cgsccpGttSelRefCount OBJECT-TYPE
    SYNTAX          Gauge32 (0..2147483647)
    MAX-ACCESS      read-only
    STATUS          current
    DESCRIPTION
        "The number of entries in the global title addresses
        that belong to this selector." 
    ::= { cgsccpGttSelTableEntry 9 }

cgsccpGttSelPrePrefConv OBJECT-TYPE
    SYNTAX          CgsccpGttPrefName
    MAX-ACCESS      read-create
    STATUS          current
    DESCRIPTION
        "The Prefix Conversion Table is used to convert
        GTA digits.  This object specifies that the
        conversion occurs 'before' global title
        translation.  The null string indicates
        that a prefix conversion table has not been
        specified."
    DEFVAL          { "" } 
    ::= { cgsccpGttSelTableEntry 10 }

cgsccpGttSelPostPrefConv OBJECT-TYPE
    SYNTAX          CgsccpGttPrefName
    MAX-ACCESS      read-create
    STATUS          current
    DESCRIPTION
        "The Post Prefix Conversion Table is used to convert
        GTA digits.  This object specifies that the
        conversion occurs 'after' global title
        translation.  The null string indicates
        that a post conversion table has not been
        specified."
    DEFVAL          { "" } 
    ::= { cgsccpGttSelTableEntry 11 }

cgsccpGttSelRowStatus OBJECT-TYPE
    SYNTAX          RowStatus
    MAX-ACCESS      read-create
    STATUS          current
    DESCRIPTION
        "The object is used by a management station to
        create or delete the row entry in cgsccpGttSelTable
        following the RowStatus textual convention." 
    ::= { cgsccpGttSelTableEntry 12 }

cgsccpGttNextSelName OBJECT-TYPE
    SYNTAX          CgsccpGttSelName
    MAX-ACCESS      read-create
    STATUS          current
    DESCRIPTION
        "The name of GTT next selector table." 
    ::= { cgsccpGttSelTableEntry 13 }

cgsccpGttNextSelRefed OBJECT-TYPE
    SYNTAX          Gauge32
    MAX-ACCESS      read-only
    STATUS          current
    DESCRIPTION
        "The counter that table was referenced." 
    ::= { cgsccpGttSelTableEntry 14 }

-- *************************************************************
-- *                                                           *
-- * SCCP - GTT Global Title Address Table                     *
-- *                                                           *
-- *************************************************************

cgsccpGttGtaTable OBJECT-TYPE
    SYNTAX          SEQUENCE OF CgsccpGttGtaTableEntry 
    MAX-ACCESS      not-accessible
    STATUS          current
    DESCRIPTION
        "A table of SCCP Global Title Address entries."
    ::= { cgsccpGttGta 1 }

cgsccpGttGtaTableEntry OBJECT-TYPE
    SYNTAX          CgsccpGttGtaTableEntry
    MAX-ACCESS      not-accessible
    STATUS          current
    DESCRIPTION
        "A list of SCCP Global Title Address attributes."
    INDEX           {
                        cgspInstNetwork,
                        cgsccpGttSelTT,
                        cgsccpGttSelNAI,
                        cgsccpGttSelNP,
                        cgsccpGttSelGTI,
                        cgsccpGttGtaAddr
                    } 
    ::= { cgsccpGttGtaTable 1 }

CgsccpGttGtaTableEntry ::= SEQUENCE {
        cgsccpGttGtaAddr         CItpTcGtaLongAddr,
        cgsccpGttGtaSelName      CgsccpGttSelName,
        cgsccpGttGtaResType      CgsccpGttGtaResType,
        cgsccpGttGtaResPc        CItpTcPointCode,
        cgsccpGttGtaResMap       CItpTcPointCode,
        cgsccpGttGtaResAppGroup  CgsccpGttAppName,
        cgsccpGttGtaTTorSSN      CItpTcTranslationType,
        cgsccpGttGtaTTorSSNvalue Unsigned32,
        cgsccpGttGtaRoutingInd   CgsccpGttRoutingInd,
        cgsccpGttGtaQOS          CgsccpGttQOS,
        cgsccpGttGtaAddrDisp     CItpTcGtaLongDisplay,
        cgsccpGttGtaAddrLen      CItpTcGtaLongDisplayLen,
        cgsccpGttGtaAsName       CItpTcXuaName,
        cgsccpGttGtaRowStatus    RowStatus,
        cgsccpGttGtaNetwork      CItpTcNetworkName
}

cgsccpGttGtaAddr OBJECT-TYPE
    SYNTAX          CItpTcGtaLongAddr
    MAX-ACCESS      not-accessible
    STATUS          current
    DESCRIPTION
        "The Global Title Address is 8 octets
        of the Called Party Address (CDPA)." 
    ::= { cgsccpGttGtaTableEntry 1 }

cgsccpGttGtaSelName OBJECT-TYPE
    SYNTAX          CgsccpGttSelName
    MAX-ACCESS      read-create
    STATUS          current
    DESCRIPTION
        "The Global Title Address selector name from
        cgsccpGttSelTable." 
    ::= { cgsccpGttGtaTableEntry 2 }

cgsccpGttGtaResType OBJECT-TYPE
    SYNTAX          CgsccpGttGtaResType
    MAX-ACCESS      read-create
    STATUS          current
    DESCRIPTION
        "The SCCP Global Title Translation result type." 
    ::= { cgsccpGttGtaTableEntry 3 }

cgsccpGttGtaResPc OBJECT-TYPE
    SYNTAX          CItpTcPointCode
    MAX-ACCESS      read-create
    STATUS          current
    DESCRIPTION
        "When the GTA translates to a point code,
        it has a valid point code and cgsccpGttGtaResType
        is 'pc'. Otherwise it is zero."
    DEFVAL          { 0 } 
    ::= { cgsccpGttGtaTableEntry 4 }

cgsccpGttGtaResMap OBJECT-TYPE
    SYNTAX          CItpTcPointCode
    MAX-ACCESS      read-create
    STATUS          current
    DESCRIPTION
        "When the GTA translates to a point code and an
        optional SSN, it has a valid point code and
        cgsccpGttGtaResType is 'pcssn'. Otherwise it is
        zero."
    DEFVAL          { 0 } 
    ::= { cgsccpGttGtaTableEntry 5 }

cgsccpGttGtaResAppGroup OBJECT-TYPE
    SYNTAX          CgsccpGttAppName
    MAX-ACCESS      read-create
    STATUS          current
    DESCRIPTION
        "When the GTA translates to an application group,
        it has a valid application group name and
        cgsccpGttGtaResType is 'app'.  The null string
        indicates that an application group has not been
        specified."
    DEFVAL          { "" } 
    ::= { cgsccpGttGtaTableEntry 6 }

cgsccpGttGtaTTorSSN OBJECT-TYPE
    SYNTAX          CItpTcTranslationType
    MAX-ACCESS      read-create
    STATUS          current
    DESCRIPTION
        "When this object is 'tt', the object
        cgsccpGttGtaTTorSSNvalue specifies the SCCP GTT
        Translation Type (TT). When this object is 'ssn',
        the object cgsccpGttGtaTTorSSNvalue specifies
        the SCCP SubSystem Number (SSN)." 
    ::= { cgsccpGttGtaTableEntry 7 }

cgsccpGttGtaTTorSSNvalue OBJECT-TYPE
    SYNTAX          Unsigned32 (0..255)
    MAX-ACCESS      read-create
    STATUS          current
    DESCRIPTION
        "This object specifies SCCP GTT Translation Type (TT)
        value when cgsccpGttGtaTTorSSN is 'tt'.
        It specifies SCCP SubSystem Number (SSN) value when
        cgsccpGttGtaTTorSSN is 'ssn'.
        A zero value specifies that the TT or the SSN is not
        applicable for this GTA entry."
    DEFVAL          { 0 } 
    ::= { cgsccpGttGtaTableEntry 8 }

cgsccpGttGtaRoutingInd OBJECT-TYPE
    SYNTAX          CgsccpGttRoutingInd
    MAX-ACCESS      read-create
    STATUS          current
    DESCRIPTION
        "The SCCP GTT GTA specifies the routing indicator.

        When cgsccpGttGtaResType is 'pc' or 'pcssn',
        this object has a valid routing indicator.

        When cgsccpGttGtaResType is 'app' or 'as',
        the routing indicator is not applicable." 
    ::= { cgsccpGttGtaTableEntry 9 }

cgsccpGttGtaQOS OBJECT-TYPE
    SYNTAX          CgsccpGttQOS
    MAX-ACCESS      read-create
    STATUS          current
    DESCRIPTION
        "The SCCP GTT GTA specifies the QOS."
    DEFVAL          { 255 } 
    ::= { cgsccpGttGtaTableEntry 10 }

cgsccpGttGtaAddrDisp OBJECT-TYPE
    SYNTAX          CItpTcGtaLongDisplay
    MAX-ACCESS      read-only
    STATUS          current
    DESCRIPTION
        "The ASCII display string of Global Title Address
        up to 64 hex digits of the Called Party Address
        (CDPA). A zero length string specifies a
        default GTA value for the selector." 
    ::= { cgsccpGttGtaTableEntry 11 }

cgsccpGttGtaAddrLen OBJECT-TYPE
    SYNTAX          CItpTcGtaLongDisplayLen
    MAX-ACCESS      read-only
    STATUS          current
    DESCRIPTION
        "The number of hex digits in the Global Title
        Address of the Called Party Address (CDPA).
        For a default GTA, the address length is zero." 
    ::= { cgsccpGttGtaTableEntry 12 }

cgsccpGttGtaAsName OBJECT-TYPE
    SYNTAX          CItpTcXuaName
    MAX-ACCESS      read-create
    STATUS          current
    DESCRIPTION
        "The Application Server (AS) name specified by the GTA.
        It is valid only when cgsccpGttGtaResType is 'as'.
        Otherwise it is a zero length string.  The null string
        indicates that a application server name has not been
        specified."
    DEFVAL          { "" } 
    ::= { cgsccpGttGtaTableEntry 13 }

cgsccpGttGtaRowStatus OBJECT-TYPE
    SYNTAX          RowStatus
    MAX-ACCESS      read-create
    STATUS          current
    DESCRIPTION
        "The object is used by a management station to
        create or delete the row entry in cgsccpGttGtaTable
        following the RowStatus textual convention." 
    ::= { cgsccpGttGtaTableEntry 14 }

cgsccpGttGtaNetwork OBJECT-TYPE
    SYNTAX          CItpTcNetworkName
    MAX-ACCESS      read-create
    STATUS          current
    DESCRIPTION
        "The processing of global title translation may
        result in a packet being transferred from one
        network to another.  This object specifies
        the target network." 
    ::= { cgsccpGttGtaTableEntry 15 }

-- *************************************************************
-- *                                                           *
-- * SCCP - GTT Prefix Conversion Table                        *
-- *                                                           *
-- * This table has been deprecated and replaced by the        *
-- * cgsccpGttPrefTable table in order to support prefix       *
-- * conversion tables per instance.                           *
-- *************************************************************

cgsccpGttPrefTable OBJECT-TYPE
    SYNTAX          SEQUENCE OF CgsccpGttPrefTableEntry 
    MAX-ACCESS      not-accessible
    STATUS          deprecated
    DESCRIPTION
        "A table of SCCP GTT Prefix Conversion Table entries.

        When a packet with GTA is received, it may need
        global title translation depending on Translation
        Type (TT), Numbering Plan (NP), Network Address
        Indicator (NAI) and Global Title Indicator (GTI)
        present in the packet. To perform the translation
        a selector (cgsccpGttSelTable) corresponding to
        TT, NP, NAI and GTI is used. The selector also
        specifies prefix conversion of the GTA before (pre)
        performing the global title translation or after
        (post) performing the global title translation.

        A selector can specify any or both (pre and post)
        prefix conversion tables.

        The prefix conversion involves matching of GTA digits
        in the cgsccpGttPrefInAddr and then replacing those
        digits with the digits in cgsccpGttPrefOutAddr."
    ::= { cgsccpGttPref 1 }

cgsccpGttPrefTableEntry OBJECT-TYPE
    SYNTAX          CgsccpGttPrefTableEntry
    MAX-ACCESS      not-accessible
    STATUS          deprecated
    DESCRIPTION
        "A list of SCCP GTT Prefix Conversion attributes."
    INDEX           {
                        cgsccpGttPrefName,
                        cgsccpGttPrefInAddr
                    } 
    ::= { cgsccpGttPrefTable 1 }

CgsccpGttPrefTableEntry ::= SEQUENCE {
        cgsccpGttPrefName      CgsccpGttPrefName,
        cgsccpGttPrefInAddr    CItpTcGtaLongAddr,
        cgsccpGttPrefOutAddr   CItpTcGtaLongAddr,
        cgsccpGttPrefTblNAI    CItpTcNAI,
        cgsccpGttPrefTblNP     CItpTcNumberingPlan,
        cgsccpGttPrefItemNAI   CItpTcNAI,
        cgsccpGttPrefItemNP    CItpTcNumberingPlan,
        cgsccpGttPrefRowStatus RowStatus
}

cgsccpGttPrefName OBJECT-TYPE
    SYNTAX          CgsccpGttPrefName
    MAX-ACCESS      not-accessible
    STATUS          deprecated
    DESCRIPTION
        "The GTT Prefix Conversion table name." 
    ::= { cgsccpGttPrefTableEntry 1 }

cgsccpGttPrefInAddr OBJECT-TYPE
    SYNTAX          CItpTcGtaLongAddr
    MAX-ACCESS      not-accessible
    STATUS          deprecated
    DESCRIPTION
        "If the GTA of the Called Party Address (CDPA)
        matches the digits in this object, then the
        prefix conversion is performed." 
    ::= { cgsccpGttPrefTableEntry 2 }

cgsccpGttPrefOutAddr OBJECT-TYPE
    SYNTAX          CItpTcGtaLongAddr
    MAX-ACCESS      read-create
    STATUS          deprecated
    DESCRIPTION
        "If the GTA of the Called Party Address (CDPA)
        matches the digits in cgsccpGttPrefInAddr
        then this object is used in the prefix
        conversion." 
    ::= { cgsccpGttPrefTableEntry 3 }

cgsccpGttPrefTblNAI OBJECT-TYPE
    SYNTAX          CItpTcNAI
    MAX-ACCESS      read-create
    STATUS          deprecated
    DESCRIPTION
        "Nature of Address Indicator (NAI) for the Prefix
        Conversion Table."
    DEFVAL          { 253 } 
    ::= { cgsccpGttPrefTableEntry 4 }

cgsccpGttPrefTblNP OBJECT-TYPE
    SYNTAX          CItpTcNumberingPlan
    MAX-ACCESS      read-create
    STATUS          deprecated
    DESCRIPTION
        "Numbering Plan (NP) for the Prefix Conversion Table."
    DEFVAL          { 253 } 
    ::= { cgsccpGttPrefTableEntry 5 }

cgsccpGttPrefItemNAI OBJECT-TYPE
    SYNTAX          CItpTcNAI
    MAX-ACCESS      read-create
    STATUS          deprecated
    DESCRIPTION
        "Nature of Address Indicator (NAI) for the current
        item in this Prefix Conversion Table."
    DEFVAL          { 253 } 
    ::= { cgsccpGttPrefTableEntry 6 }

cgsccpGttPrefItemNP OBJECT-TYPE
    SYNTAX          CItpTcNumberingPlan
    MAX-ACCESS      read-create
    STATUS          deprecated
    DESCRIPTION
        "Numbering Plan (NP) for the current item in this
        Prefix Conversion Table."
    DEFVAL          { 253 } 
    ::= { cgsccpGttPrefTableEntry 7 }

cgsccpGttPrefRowStatus OBJECT-TYPE
    SYNTAX          RowStatus
    MAX-ACCESS      read-create
    STATUS          deprecated
    DESCRIPTION
        "The object is used by a management station to
        create or delete the row entry in cgsccpGttPrefTable
        following the RowStatus textual convention." 
    ::= { cgsccpGttPrefTableEntry 8 }

-- *************************************************************
-- *                                                           *
-- * SCCP - GTT Packet per Second History                      *
-- *                                                           *
-- *************************************************************

cgsccpGttTranslateTable OBJECT-TYPE
    SYNTAX          SEQUENCE OF CgsccpGttTranslateTableEntry 
    MAX-ACCESS      not-accessible
    STATUS          current
    DESCRIPTION
        "The translate table contains a history of the
        number of global title packets that were translated
        on the various processors enabled for this function.
        The ability to translate GTT is critical to many
        SS7 functions.  This table provides peak utilization
        to allow planning of maximum load on SS7 network."
    REFERENCE
        "ANSI GR-82-CORE 6.4.5 Processor Measurements Item 2."
    ::= { cgsccpGttTranslate 1 }

cgsccpGttTranslateTableEntry OBJECT-TYPE
    SYNTAX          CgsccpGttTranslateTableEntry
    MAX-ACCESS      not-accessible
    STATUS          current
    DESCRIPTION
        "A list of global title translate statistics."
    INDEX           {
                        cgsccpGttTranslateSlot,
                        cgsccpGttTranslateEntry
                    } 
    ::= { cgsccpGttTranslateTable 1 }

CgsccpGttTranslateTableEntry ::= SEQUENCE {
        cgsccpGttTranslateSlot          Unsigned32,
        cgsccpGttTranslateEntry         Unsigned32,
        cgsccpGttTranslateRate          Gauge32,
        cgsccpGttTranslateTS            TimeStamp,
        cgsccpGttTranslatePhysicalIndex EntPhysicalIndexOrZero
}

cgsccpGttTranslateSlot OBJECT-TYPE
    SYNTAX          Unsigned32 (0..32767)
    MAX-ACCESS      not-accessible
    STATUS          current
    DESCRIPTION
        "The slot number containing the CPU that is
        performing Global Title translation." 
    ::= { cgsccpGttTranslateTableEntry 1 }

cgsccpGttTranslateEntry OBJECT-TYPE
    SYNTAX          Unsigned32 (0..4294967295)
    MAX-ACCESS      not-accessible
    STATUS          current
    DESCRIPTION
        "The entry number.  Each entry represents a period
        of time as specified by the
        cgsccpGttTranslatePeriod object.  The entries are
        ordered from old to new." 
    ::= { cgsccpGttTranslateTableEntry 2 }

cgsccpGttTranslateRate OBJECT-TYPE
    SYNTAX          Gauge32 (0..2147483647)
    MAX-ACCESS      read-only
    STATUS          current
    DESCRIPTION
        "During each interval the rate of global title
        translations is calculated every second.  This object
        is the highest rate of global title translation
        encountered in the interval specified by the
        cgsccpGttTranslatePeriod object." 
    ::= { cgsccpGttTranslateTableEntry 3 }

cgsccpGttTranslateTS OBJECT-TYPE
    SYNTAX          TimeStamp
    MAX-ACCESS      read-only
    STATUS          current
    DESCRIPTION
        "This timestamp indicates when time period ended
        for this sample." 
    ::= { cgsccpGttTranslateTableEntry 4 }

cgsccpGttTranslatePhysicalIndex OBJECT-TYPE
    SYNTAX          EntPhysicalIndexOrZero
    MAX-ACCESS      read-only
    STATUS          current
    DESCRIPTION
        "The entPhysicalIndex of the physical entity for which
        the statistics in this entry are maintained.
        The physical entity can be a CPU chip, a group of CPUs,
        a CPU card etc. The exact type of this entity is described
        by its entPhysicalVendorType value. If the CPU statistics
        in this entry correspond to more than one physical entity
        (or to no physical entity), or if the entPhysicalTable is
        not supported on the SNMP agent, the value of this object
        must be zero." 
    ::= { cgsccpGttTranslateTableEntry 5 }

-- *************************************************************
-- *                                                           *
-- * SCCP - GTT Prefix2 Conversion Table                       *
-- *                                                           *
-- *************************************************************

cgsccpGttPref2Table OBJECT-TYPE
    SYNTAX          SEQUENCE OF CgsccpGttPref2TableEntry 
    MAX-ACCESS      not-accessible
    STATUS          current
    DESCRIPTION
        "A table of SCCP GTT Prefix Conversion Table entries.

        This table replaces the cgsccpGttPrefTable tables and
        allow prefix conversion to be specified per instance.

        When a packet with GTA is received, it may need
        global title translation depending on Translation
        Type (TT), Numbering Plan (NP), Network Address
        Indicator (NAI) and Global Title Indicator (GTI)
        present in the packet. To perform the translation
        a selector (cgsccpGttSelTable) corresponding to
        TT, NP, NAI and GTI is used. The selector also
        specifies prefix conversion of the GTA before (pre)
        performing the global title translation or after
        (post) performing the global title translation.

        A selector can specify any or both (pre and post)
        prefix conversion tables.

        The prefix conversion involves matching of GTA digits
        in the cgsccpGttPref2InAddr and then replacing those
        digits with the digits in cgsccpGttPref2OutAddr."
    ::= { cgsccpGttPref2 1 }

cgsccpGttPref2TableEntry OBJECT-TYPE
    SYNTAX          CgsccpGttPref2TableEntry
    MAX-ACCESS      not-accessible
    STATUS          current
    DESCRIPTION
        "A list of SCCP GTT Prefix Conversion attributes."
    INDEX           {
                        cgspInstNetwork,
                        cgsccpGttPref2Name,
                        cgsccpGttPref2InAddr
                    } 
    ::= { cgsccpGttPref2Table 1 }

CgsccpGttPref2TableEntry ::= SEQUENCE {
        cgsccpGttPref2Name           CgsccpGttPrefName,
        cgsccpGttPref2InAddr         CItpTcGtaLongAddr,
        cgsccpGttPref2OutAddr        CItpTcGtaLongAddr,
        cgsccpGttPref2TblNAI         CItpTcNAI,
        cgsccpGttPref2TblNP          CItpTcNumberingPlan,
        cgsccpGttPref2ItemNAI        CItpTcNAI,
        cgsccpGttPref2ItemNP         CItpTcNumberingPlan,
        cgsccpGttPref2RowStatus      RowStatus,
        cgsccpGttPref2EncodingScheme INTEGER
}

cgsccpGttPref2Name OBJECT-TYPE
    SYNTAX          CgsccpGttPrefName
    MAX-ACCESS      not-accessible
    STATUS          current
    DESCRIPTION
        "The GTT Prefix Conversion table name." 
    ::= { cgsccpGttPref2TableEntry 1 }

cgsccpGttPref2InAddr OBJECT-TYPE
    SYNTAX          CItpTcGtaLongAddr
    MAX-ACCESS      not-accessible
    STATUS          current
    DESCRIPTION
        "If the GTA of the Called Party Address (CDPA)
        matches the digits in this object, then the
        prefix conversion is performed." 
    ::= { cgsccpGttPref2TableEntry 2 }

cgsccpGttPref2OutAddr OBJECT-TYPE
    SYNTAX          CItpTcGtaLongAddr
    MAX-ACCESS      read-create
    STATUS          current
    DESCRIPTION
        "If the GTA of the Called Party Address (CDPA)
        matches the digits in cgsccpGttPref2InAddr
        then this object is used in the prefix
        conversion." 
    ::= { cgsccpGttPref2TableEntry 3 }

cgsccpGttPref2TblNAI OBJECT-TYPE
    SYNTAX          CItpTcNAI
    MAX-ACCESS      read-create
    STATUS          current
    DESCRIPTION
        "Nature of Address Indicator (NAI) for the Prefix
        Conversion Table."
    DEFVAL          { 253 } 
    ::= { cgsccpGttPref2TableEntry 4 }

cgsccpGttPref2TblNP OBJECT-TYPE
    SYNTAX          CItpTcNumberingPlan
    MAX-ACCESS      read-create
    STATUS          current
    DESCRIPTION
        "Numbering Plan (NP) for the Prefix Conversion Table."
    DEFVAL          { 253 } 
    ::= { cgsccpGttPref2TableEntry 5 }

cgsccpGttPref2ItemNAI OBJECT-TYPE
    SYNTAX          CItpTcNAI
    MAX-ACCESS      read-create
    STATUS          current
    DESCRIPTION
        "Nature of Address Indicator (NAI) for the current
        item in this Prefix Conversion Table."
    DEFVAL          { 253 } 
    ::= { cgsccpGttPref2TableEntry 6 }

cgsccpGttPref2ItemNP OBJECT-TYPE
    SYNTAX          CItpTcNumberingPlan
    MAX-ACCESS      read-create
    STATUS          current
    DESCRIPTION
        "Numbering Plan (NP) for the current item in this
        Prefix Conversion Table."
    DEFVAL          { 253 } 
    ::= { cgsccpGttPref2TableEntry 7 }

cgsccpGttPref2RowStatus OBJECT-TYPE
    SYNTAX          RowStatus
    MAX-ACCESS      read-create
    STATUS          current
    DESCRIPTION
        "The object is used by a management station to
        create or delete the row entry in cgsccpGttPref2Table
        following the RowStatus textual convention." 
    ::= { cgsccpGttPref2TableEntry 8 }

cgsccpGttPref2EncodingScheme OBJECT-TYPE
    SYNTAX          INTEGER  {
                        unknown(0),
                        bcdOdd(1),
                        bcdEven(2),
                        national(3)
                    }
    MAX-ACCESS      read-create
    STATUS          current
    DESCRIPTION
        "The encoding scheme to be used for output GTT address
        as follows.

        unknown  - encoding scheme is not specified at the address
                   level.
        bcdOdd   - Use BCD odd encoding scheme.
        bcdEven  - Use BCD even encoding scheme.
        national - national specific."
    REFERENCE       "E.164 and E.214 address formats and Q.713" 
    ::= { cgsccpGttPref2TableEntry 9 }

-- *************************************************************
-- *                                                           *
-- * SCCP - GTT Application Group Table                        *
-- *                                                           *
-- * This table supercedes cgsccpGttAppGrTable. The cost and   *
-- * weighting factors have been separated. The cost is in the *
-- * range of 1..8. The weighting factor is in the range of    *
-- * 0..999 when multiplicity indicator is 'cgpa'.             *
-- *************************************************************

cgsccpGttAppGr2Table OBJECT-TYPE
    SYNTAX          SEQUENCE OF CgsccpGttAppGr2TableEntry 
    MAX-ACCESS      not-accessible
    STATUS          current
    DESCRIPTION
        "A table of SCCP GTT Application Group Table entries."
    ::= { cgsccpGttAppGr2 1 }

cgsccpGttAppGr2TableEntry OBJECT-TYPE
    SYNTAX          CgsccpGttAppGr2TableEntry
    MAX-ACCESS      not-accessible
    STATUS          current
    DESCRIPTION
        "A list of SCCP GTT Application Group attributes."
    INDEX           {
                        cgspInstNetwork,
                        cgsccpGttAppGr2Name,
                        cgsccpGttAppGr2EntNum
                    } 
    ::= { cgsccpGttAppGr2Table 1 }

CgsccpGttAppGr2TableEntry ::= SEQUENCE {
        cgsccpGttAppGr2Name      CgsccpGttAppName,
        cgsccpGttAppGr2EntNum    Unsigned32,
        cgsccpGttAppGr2Mult      CgsccpGttMultInd,
        cgsccpGttAppGr2Type      CgsccpGttAppType,
        cgsccpGttAppGr2Cost      CgsccpGttAppCost,
        cgsccpGttAppGr2Weight    Unsigned32,
        cgsccpGttAppGr2Pc        CItpTcPointCode,
        cgsccpGttAppGr2Ssn       CItpTcSubSystemNumber,
        cgsccpGttAppGr2Ri        CgsccpGttRoutingInd,
        cgsccpGttAppGr2RefCount  Gauge32,
        cgsccpGttAppGr2AsName    CItpTcXuaName,
        cgsccpGttAppGr2NewSsn    CItpTcSubSystemNumber,
        cgsccpGttAppGr2NumUsed   Counter32,
        cgsccpGttAppGr2Network   CItpTcNetworkName,
        cgsccpGttAppGr2RowStatus RowStatus
}

cgsccpGttAppGr2Name OBJECT-TYPE
    SYNTAX          CgsccpGttAppName
    MAX-ACCESS      not-accessible
    STATUS          current
    DESCRIPTION
        "The GTT Application Group name." 
    ::= { cgsccpGttAppGr2TableEntry 1 }

cgsccpGttAppGr2EntNum OBJECT-TYPE
    SYNTAX          Unsigned32
    MAX-ACCESS      not-accessible
    STATUS          current
    DESCRIPTION
        "The entry number is an arbitrary number. It is used
        to identify each application group entry." 
    ::= { cgsccpGttAppGr2TableEntry 2 }

cgsccpGttAppGr2Mult OBJECT-TYPE
    SYNTAX          CgsccpGttMultInd
    MAX-ACCESS      read-create
    STATUS          current
    DESCRIPTION
        "The multiplicity of the GTT Application Group." 
    ::= { cgsccpGttAppGr2TableEntry 3 }

cgsccpGttAppGr2Type OBJECT-TYPE
    SYNTAX          CgsccpGttAppType
    MAX-ACCESS      read-create
    STATUS          current
    DESCRIPTION
        "The type of the item in the GTT Application Group." 
    ::= { cgsccpGttAppGr2TableEntry 4 }

cgsccpGttAppGr2Cost OBJECT-TYPE
    SYNTAX          CgsccpGttAppCost
    MAX-ACCESS      read-create
    STATUS          current
    DESCRIPTION
        "The cost for the item in the GTT Application Group.
        When the cgsccpGttAppGr2Mult object has 'cost'
        value, this object is required when entry is created.
        Otherwise, this value does not apply." 
    ::= { cgsccpGttAppGr2TableEntry 5 }

cgsccpGttAppGr2Weight OBJECT-TYPE
    SYNTAX          Unsigned32 (0..999)
    MAX-ACCESS      read-create
    STATUS          current
    DESCRIPTION
        "The weighting factor used for the item in the GTT
        Application Group. When the cgsccpGttAppGr2Mult
        object has 'cgpa' value, this object is required when
        entry is created. Otherwise, this value does not
        apply and can default zero."
    DEFVAL          { 0 } 
    ::= { cgsccpGttAppGr2TableEntry 6 }

cgsccpGttAppGr2Pc OBJECT-TYPE
    SYNTAX          CItpTcPointCode
    MAX-ACCESS      read-create
    STATUS          current
    DESCRIPTION
        "The point code specified by the item in the GTT
        Application Group.  When the cgsccpGttAppGr2Type
        object has 'pc' or pcssn' values this object
        is required when entry is created.  Otherwise,
        this value does not apply and can default to
        zero."
    DEFVAL          { 0 } 
    ::= { cgsccpGttAppGr2TableEntry 7 }

cgsccpGttAppGr2Ssn OBJECT-TYPE
    SYNTAX          CItpTcSubSystemNumber
    MAX-ACCESS      read-create
    STATUS          current
    DESCRIPTION
        "The subsystem number (SSN) specified by the item
        in the GTT Application Group. It is valid only when
        cgsccpGttAppGr2Type is 'pcssn'. Otherwise it is zero."
    DEFVAL          { 0 } 
    ::= { cgsccpGttAppGr2TableEntry 8 }

cgsccpGttAppGr2Ri OBJECT-TYPE
    SYNTAX          CgsccpGttRoutingInd
    MAX-ACCESS      read-create
    STATUS          current
    DESCRIPTION
        "The routing indicator (RI) specified by the item
        in the GTT Application Group." 
    ::= { cgsccpGttAppGr2TableEntry 9 }

cgsccpGttAppGr2RefCount OBJECT-TYPE
    SYNTAX          Gauge32 (0..2147483647)
    MAX-ACCESS      read-only
    STATUS          current
    DESCRIPTION
        "The number of global title addresses referring to
        this application group." 
    ::= { cgsccpGttAppGr2TableEntry 10 }

cgsccpGttAppGr2AsName OBJECT-TYPE
    SYNTAX          CItpTcXuaName
    MAX-ACCESS      read-create
    STATUS          current
    DESCRIPTION
        "The Application Server (AS) name specified by the item
        in the GTT Application Group. It is valid only when
        cgsccpGttAppGr2Type is 'as'. Otherwise it
        is a zero length string."
    DEFVAL          { "" } 
    ::= { cgsccpGttAppGr2TableEntry 11 }

cgsccpGttAppGr2NewSsn OBJECT-TYPE
    SYNTAX          CItpTcSubSystemNumber
    MAX-ACCESS      read-create
    STATUS          current
    DESCRIPTION
        "The new subsystem number (SSN) specified by the item
        in the GTT Application Group.  It is valid only when
        cgsccpGttAppGr2Type is 'as'.  Otherwise it
        is zero."
    DEFVAL          { 0 } 
    ::= { cgsccpGttAppGr2TableEntry 12 }

cgsccpGttAppGr2NumUsed OBJECT-TYPE
    SYNTAX          Counter32
    MAX-ACCESS      read-only
    STATUS          current
    DESCRIPTION
        "The number of times this item in the GTT Application
        Group is used successfully." 
    ::= { cgsccpGttAppGr2TableEntry 13 }

cgsccpGttAppGr2Network OBJECT-TYPE
    SYNTAX          CItpTcNetworkName
    MAX-ACCESS      read-create
    STATUS          current
    DESCRIPTION
        "The processing of global title translation may
        result in a packet being transferred from one
        network to another.  This object specifies
        the target network." 
    ::= { cgsccpGttAppGr2TableEntry 14 }

cgsccpGttAppGr2RowStatus OBJECT-TYPE
    SYNTAX          RowStatus
    MAX-ACCESS      read-create
    STATUS          current
    DESCRIPTION
        "The object is used by a management station to
        create or delete the row entry in cgsccpGttAppGr2Table
        following the RowStatus textual convention." 
    ::= { cgsccpGttAppGr2TableEntry 15 }

-- *************************************************************
-- *                                                           *
-- * Global Title Errors                                       *
-- *                                                           *
-- *************************************************************

cgsccpGttErrorsTable OBJECT-TYPE
    SYNTAX          SEQUENCE OF CgsccpGttErrorsTableEntry 
    MAX-ACCESS      not-accessible
    STATUS          current
    DESCRIPTION
        "This table is used to indicate errors in global title
        translation and will be used to provide information
        for ciscoGsccpGttErrors notification."
    ::= { cgsccpGttErrors 1 }

cgsccpGttErrorsTableEntry OBJECT-TYPE
    SYNTAX          CgsccpGttErrorsTableEntry
    MAX-ACCESS      not-accessible
    STATUS          current
    DESCRIPTION
        "All objects in this table are derived from other
        objects in this MIB.  At the end of each
        interval the values of these objects will be updated
        with number of errors that occurred during last
        interval.  The length of the interval is defined by
        the cgsccpGttErrorPeriod object."
    INDEX           { cgspInstNetwork } 
    ::= { cgsccpGttErrorsTable 1 }

CgsccpGttErrorsTableEntry ::= SEQUENCE {
        cgsccpGttErrorsSelectorNotFound Gauge32,
        cgsccpGttErrorsIncorrectFormat  Gauge32,
        cgsccpGttErrorsGtaNotFound      Gauge32,
        cgsccpGttErrorsHopViolation     Gauge32,
        cgsccpGttErrorsMapNotFound      Gauge32,
        cgsccpGttErrorsUnequipedSS      Gauge32,
        cgsccpGttErrorsSccpUnavailable  Gauge32,
        cgsccpGttErrorsDpcUnavailable   Gauge32,
        cgsccpGttErrorsSsUnavailable    Gauge32,
        cgsccpGttErrorsDpcCongested     Gauge32,
        cgsccpGttErrorsSsCongested      Gauge32,
        cgsccpGttErrorsRouteFailure     Gauge32,
        cgsccpGttErrorsSccpUnqualified  Gauge32,
        cgsccpGttErrorsReassUnsupported Gauge32,
        cgsccpGttErrorsReassFailure     Gauge32,
        cgsccpGttErrorsSegUnsupported   Gauge32,
        cgsccpGttErrorsSegFailure       Gauge32
}

cgsccpGttErrorsSelectorNotFound OBJECT-TYPE
    SYNTAX          Gauge32
    UNITS           "packets"
    MAX-ACCESS      accessible-for-notify
    STATUS          current
    DESCRIPTION
        "This counter is incremented every time a translation
        was requested for a combination of Translation Type,
        Numbering Plan and Nature of Address for which no
        translation exists in the signalling point.  This
        occurs when no selector is available for the
        combination of parameters provided in the MSU.
        This counter is derived from cgsccpInstQ752T7E1
        object." 
    ::= { cgsccpGttErrorsTableEntry 1 }

cgsccpGttErrorsIncorrectFormat OBJECT-TYPE
    SYNTAX          Gauge32
    UNITS           "packets"
    MAX-ACCESS      accessible-for-notify
    STATUS          current
    DESCRIPTION
        "This counter is incremented every time an invalid
        Global Title format is found while performing the
        global title translation.  This counter is derived
        from cgsccpInstInvalidGttFormat object." 
    ::= { cgsccpGttErrorsTableEntry 2 }

cgsccpGttErrorsGtaNotFound OBJECT-TYPE
    SYNTAX          Gauge32
    UNITS           "packets"
    MAX-ACCESS      accessible-for-notify
    STATUS          current
    DESCRIPTION
        "This counter is incremented every time a global title
        title translations was required and a selector was
        not found. This counter is derived from
        cgsccpGttQ752T7E2 object." 
    ::= { cgsccpGttErrorsTableEntry 3 }

cgsccpGttErrorsHopViolation OBJECT-TYPE
    SYNTAX          Gauge32
    UNITS           "packets"
    MAX-ACCESS      accessible-for-notify
    STATUS          current
    DESCRIPTION
        "This counter is incremented every time a hop count
        violation is found in the MSU.  This counter is
        derived from cgsccpInstQ752T7E13 object." 
    ::= { cgsccpGttErrorsTableEntry 4 }

cgsccpGttErrorsMapNotFound OBJECT-TYPE
    SYNTAX          Gauge32
    UNITS           "packets"
    MAX-ACCESS      accessible-for-notify
    STATUS          current
    DESCRIPTION
        "This counter is incremented every time a global
        title translation is successful to a certain
        PC/SSN but it was not found in the GTT Mated
        Application table.  This counter is derived
        from cgsccpInstMapNotFound object." 
    ::= { cgsccpGttErrorsTableEntry 5 }

cgsccpGttErrorsUnequipedSS OBJECT-TYPE
    SYNTAX          Gauge32
    UNITS           "packets"
    MAX-ACCESS      accessible-for-notify
    STATUS          current
    DESCRIPTION
        "This counter is incremented every time a global
        title translation could not be performed due to an
        unequipped subsystem (SS). This counter is derived
        from cgsccpInstQ752T7E7 object." 
    ::= { cgsccpGttErrorsTableEntry 6 }

cgsccpGttErrorsSccpUnavailable OBJECT-TYPE
    SYNTAX          Gauge32
    UNITS           "packets"
    MAX-ACCESS      accessible-for-notify
    STATUS          current
    DESCRIPTION
        "This counter is incremented every time a SCCP is
        unavailable at the GTT Mated Application. This
        counter is derived from cgsccpGttMapSccpUnavail
        object." 
    ::= { cgsccpGttErrorsTableEntry 7 }

cgsccpGttErrorsDpcUnavailable OBJECT-TYPE
    SYNTAX          Gauge32
    UNITS           "packets"
    MAX-ACCESS      accessible-for-notify
    STATUS          current
    DESCRIPTION
        "This counter is incremented every time a point code
        is unavailable at the GTT Mated Application.
        This counter is derived from cgsccpGttMapQ752T7E3Un
        object." 
    ::= { cgsccpGttErrorsTableEntry 8 }

cgsccpGttErrorsSsUnavailable OBJECT-TYPE
    SYNTAX          Gauge32
    UNITS           "packets"
    MAX-ACCESS      accessible-for-notify
    STATUS          current
    DESCRIPTION
        "This counter is incremented every time a subsystem
        is unavailable at the GTT Mated Application.  This
        counter is derived from cgsccpGttMapQ752T7E5 object." 
    ::= { cgsccpGttErrorsTableEntry 9 }

cgsccpGttErrorsDpcCongested OBJECT-TYPE
    SYNTAX          Gauge32
    UNITS           "packets"
    MAX-ACCESS      accessible-for-notify
    STATUS          current
    DESCRIPTION
        "This counter is incremented every time a point code
        is congested at the GTT Mated Application.  This
        counter is derived from cgsccpGttMapQ752T7E4 object." 
    ::= { cgsccpGttErrorsTableEntry 10 }

cgsccpGttErrorsSsCongested OBJECT-TYPE
    SYNTAX          Gauge32
    UNITS           "packets"
    MAX-ACCESS      accessible-for-notify
    STATUS          current
    DESCRIPTION
        "This counter is incremented every time a subsystem is
        congested at the GTT Mated Application.  This counter
        is derived from cgsccpGttMapQ752T7E6 object." 
    ::= { cgsccpGttErrorsTableEntry 11 }

cgsccpGttErrorsRouteFailure OBJECT-TYPE
    SYNTAX          Gauge32
    UNITS           "packets"
    MAX-ACCESS      accessible-for-notify
    STATUS          current
    DESCRIPTION
        "This counter is incremented every time a the MTP3 layer
        failed at the GTT Mated Application.  This counter is
        derived from cgsccpGttMapQ752T7E3Fail object." 
    ::= { cgsccpGttErrorsTableEntry 12 }

cgsccpGttErrorsSccpUnqualified OBJECT-TYPE
    SYNTAX          Gauge32
    UNITS           "packets"
    MAX-ACCESS      accessible-for-notify
    STATUS          current
    DESCRIPTION
        "This counter is incremented every time a global title
        translation is unsuccessful and the error type not
        covered by other specific error types.  This counter
        is derived from cgsccpInstQ752Unqualified object." 
    ::= { cgsccpGttErrorsTableEntry 13 }

cgsccpGttErrorsReassUnsupported OBJECT-TYPE
    SYNTAX          Gauge32
    UNITS           "packets"
    MAX-ACCESS      accessible-for-notify
    STATUS          current
    DESCRIPTION
        "This counter is incremented every time when the
        incoming SCCP message needs to be dropped due
        to the unsupported reassembly feature. This
        counter is derived from cgsccpInstReassUnsup
        object." 
    ::= { cgsccpGttErrorsTableEntry 14 }

cgsccpGttErrorsReassFailure OBJECT-TYPE
    SYNTAX          Gauge32
    UNITS           "packets"
    MAX-ACCESS      accessible-for-notify
    STATUS          current
    DESCRIPTION
        "This counter is incremented every time when the
        incoming SCCP message needs to be dropped due
        to the reassembly failure. This counter is derived 
        from cgsccpInstReassFail object." 
    ::= { cgsccpGttErrorsTableEntry 15 }

cgsccpGttErrorsSegUnsupported OBJECT-TYPE
    SYNTAX          Gauge32
    UNITS           "packets"
    MAX-ACCESS      accessible-for-notify
    STATUS          current
    DESCRIPTION
        "This counter is incremented every time when either
        SCCP message from a remote node or local SCCP stack
        needs to be dropped due to the unsupported
        segmentation feature. This counter is derived
        from cgsccpInstSegUnsup object." 
    ::= { cgsccpGttErrorsTableEntry 16 }

cgsccpGttErrorsSegFailure OBJECT-TYPE
    SYNTAX          Gauge32
    UNITS           "packets"
    MAX-ACCESS      accessible-for-notify
    STATUS          current
    DESCRIPTION
        "This counter is incremented every time when either
        SCCP message from a remote node or local SCCP stack
        needs to be dropped due to the segmentation failure. 
        This counter is derived from cgsccpInstSegFail object." 
    ::= { cgsccpGttErrorsTableEntry 17 }

-- *************************************************************
-- *                                                           *
-- * SSN measurements Table                                    *
-- *                                                           *
-- *************************************************************

cgsccpSSNTable OBJECT-TYPE
    SYNTAX          SEQUENCE OF CgsccpSSNEntry 
    MAX-ACCESS      not-accessible
    STATUS          current
    DESCRIPTION
        "The SSN table provides a breakdown of SCCP measurements
        at local subsystem level."
    ::= { cgsccpSSN 1 }

cgsccpSSNEntry OBJECT-TYPE
    SYNTAX          CgsccpSSNEntry
    MAX-ACCESS      not-accessible
    STATUS          current
    DESCRIPTION
        "Each table entry represents a specific local
        subsystem number(SSN)."
    INDEX           {
                        cgspInstNetwork,
                        cgsccpSsn
                    } 
    ::= { cgsccpSSNTable 1 }

CgsccpSSNEntry ::= SEQUENCE {
        cgsccpSsn             CItpTcSubSystemNumber,
        cgsccpSSNNumProhibits Counter32,
        cgsccpSSNNumAllows    Counter32
}

cgsccpSsn OBJECT-TYPE
    SYNTAX          CItpTcSubSystemNumber
    MAX-ACCESS      not-accessible
    STATUS          current
    DESCRIPTION
        "The SCCP subsystem number." 
    ::= { cgsccpSSNEntry 1 }

cgsccpSSNNumProhibits OBJECT-TYPE
    SYNTAX          Counter32
    UNITS           "occurrences"
    MAX-ACCESS      read-only
    STATUS          current
    DESCRIPTION
        "This counter is incremented every time this local subsystem
        transitions to prohibit state at this instance (Q752/8.9)."
    REFERENCE
        "ITU  Q752 Monitoring and Measurements for Signalling
         System No. 7(SS7) Network Table 8." 
    ::= { cgsccpSSNEntry 2 }

cgsccpSSNNumAllows OBJECT-TYPE
    SYNTAX          Counter32
    UNITS           "occurrences"
    MAX-ACCESS      read-only
    STATUS          current
    DESCRIPTION
        "This counter is incremented every time this local subsystem
        transitions to allowed state at this instance (Q752/8.10)."
    REFERENCE
        "ITU  Q752 Monitoring and Measurements for Signalling
         System No. 7(SS7) Network Table 8." 
    ::= { cgsccpSSNEntry 3 }

-- *************************************************************
-- *                                                           *
-- * SSN Class measurements Table                              *
-- *                                                           *
-- *************************************************************

cgsccpSSNClassTable OBJECT-TYPE
    SYNTAX          SEQUENCE OF CgsccpSSNClassEntry 
    MAX-ACCESS      not-accessible
    STATUS          current
    DESCRIPTION
        "The SSN Class table contains information about the
        number of UDT, XUDT, LUDT messages originated and 
        terminated for a specific SSN and class. This provides
        the granularity of information required by Q752 elements
        9.6 and 9.7"
    ::= { cgsccpClassSsn 1 }

cgsccpSSNClassEntry OBJECT-TYPE
    SYNTAX          CgsccpSSNClassEntry
    MAX-ACCESS      not-accessible
    STATUS          current
    DESCRIPTION
        "Each table entry represents a specific class
        and subsystem number(SSN)."
    INDEX           {
                        cgspInstNetwork,
                        cgsccpSsn,
                        cgsccpClassIdx
                    } 
    ::= { cgsccpSSNClassTable 1 }

CgsccpSSNClassEntry ::= SEQUENCE {
        cgsccpClassIdx             CgsccpClass,
        cgsccpSSNClassUDTMsgsSent  Counter32,
        cgsccpSSNClassUDTMsgsRcvd  Counter32,
        cgsccpSSNClassXUDTMsgsSent Counter32,
        cgsccpSSNClassXUDTMsgsRcvd Counter32,
        cgsccpSSNClassLUDTMsgsSent Counter32,
        cgsccpSSNClassLUDTMsgsRcvd Counter32
}

cgsccpClassIdx OBJECT-TYPE
    SYNTAX          CgsccpClass
    MAX-ACCESS      not-accessible
    STATUS          current
    DESCRIPTION
        "The SCCP Class index." 
    ::= { cgsccpSSNClassEntry 1 }

cgsccpSSNClassUDTMsgsSent OBJECT-TYPE
    SYNTAX          Counter32
    UNITS           "packets"
    MAX-ACCESS      read-only
    STATUS          current
    DESCRIPTION
        "This counter is incremented every time a unitdata (UDT)
        message is sent for this SCCP class and SSN(Q752/9.6)."
    REFERENCE
        "ITU  Q752 Monitoring and Measurements for Signalling
         System No. 7(SS7) Network Table 9." 
    ::= { cgsccpSSNClassEntry 2 }

cgsccpSSNClassUDTMsgsRcvd OBJECT-TYPE
    SYNTAX          Counter32
    UNITS           "packets"
    MAX-ACCESS      read-only
    STATUS          current
    DESCRIPTION
        "This counter is incremented every time a unitdata (UDT)
        message is received for this SCCP class and SSN(Q752/9.7)."
    REFERENCE
        "ITU  Q752 Monitoring and Measurements for Signalling
         System No. 7(SS7) Network Table 9." 
    ::= { cgsccpSSNClassEntry 3 }

cgsccpSSNClassXUDTMsgsSent OBJECT-TYPE
    SYNTAX          Counter32
    UNITS           "packets"
    MAX-ACCESS      read-only
    STATUS          current
    DESCRIPTION
        "This counter is incremented every time an extended
        unitdata (XUDT) message is sent for this SCCP class 
        and SSN (Q752/9.6)."
    REFERENCE
        "ITU  Q752 Monitoring and Measurements for Signalling
         System No. 7(SS7) Network Table 9." 
    ::= { cgsccpSSNClassEntry 4 }

cgsccpSSNClassXUDTMsgsRcvd OBJECT-TYPE
    SYNTAX          Counter32
    UNITS           "packets"
    MAX-ACCESS      read-only
    STATUS          current
    DESCRIPTION
        "This counter is incremented every time an extended
        unitdata (XUDT) message is received for this SCCP 
        class and SSN (Q752/9.7)."
    REFERENCE
        "ITU  Q752 Monitoring and Measurements for Signalling
         System No. 7(SS7) Network Table 9." 
    ::= { cgsccpSSNClassEntry 5 }

cgsccpSSNClassLUDTMsgsSent OBJECT-TYPE
    SYNTAX          Counter32
    UNITS           "packets"
    MAX-ACCESS      read-only
    STATUS          current
    DESCRIPTION
        "This counter is incremented every time a long
        unitdata (LUDT) message is sent for this SCCP 
        class and SSN (Q752/9.6)."
    REFERENCE
        "ITU  Q752 Monitoring and Measurements for Signalling
         System No. 7(SS7) Network Table 9." 
    ::= { cgsccpSSNClassEntry 6 }

cgsccpSSNClassLUDTMsgsRcvd OBJECT-TYPE
    SYNTAX          Counter32
    UNITS           "packets"
    MAX-ACCESS      read-only
    STATUS          current
    DESCRIPTION
        "This counter is incremented every time a long
        unitdata (LUDT) message is received for this 
        SCCP class and SSN (Q752/9.7)."
    REFERENCE
        "ITU  Q752 Monitoring and Measurements for Signalling
         System No. 7(SS7) Network Table 9." 
    ::= { cgsccpSSNClassEntry 7 }

-- *************************************************************
-- *                                                           *
-- * Notifications Information                                 *
-- *                                                           *
-- *************************************************************

cgsccpLocalDisplaySS OBJECT-TYPE
    SYNTAX          Unsigned32
    UNITS           "seconds"
    MAX-ACCESS      accessible-for-notify
    STATUS          current
    DESCRIPTION
        "Local subsystem in display format." 
    ::= { cgsccpNotificationsInfo 1 }

cgsccpLocalSsStatus OBJECT-TYPE
    SYNTAX          CgsccpGttMapSsStatus
    MAX-ACCESS      accessible-for-notify
    STATUS          current
    DESCRIPTION
        "Local subsystem status." 
    ::= { cgsccpNotificationsInfo 2 }

-- *************************************************************
-- *                                                           *
-- * Notifications                                             *
-- *                                                           *
-- *************************************************************

ciscoGsccpGttMapStateChange NOTIFICATION-TYPE
    OBJECTS         {
                        cgspEventSequenceNumber,
                        cgspCLLICode,
                        cgsccpGttMapDisplayPC,
                        cgsccpGttMapDisplaySS,
                        cgsccpGttMapSsStatus
                    }
    STATUS          current
    DESCRIPTION
        "The notification generated when a mated
        application subsystem changes to a new state.
        The value of cgsccpGttMapSsStatus indicates
        the new state for the subsystem."
   ::= { ciscoGsccpMIBNotifs 1 }

ciscoGsccpGttLoadTable NOTIFICATION-TYPE
    OBJECTS         {
                        cgspEventSequenceNumber,
                        cgspCLLICode,
                        cgsccpInstGttConfigStatus,
                        cgsccpInstLastURL
                    }
    STATUS          current
    DESCRIPTION
        "This notification is generated whenever a load
        operation is started or completes."
   ::= { ciscoGsccpMIBNotifs 2 }

ciscoGsccpGttErrors NOTIFICATION-TYPE
    OBJECTS         {
                        cgspEventSequenceNumber,
                        cgspCLLICode,
                        cgsccpInstErrorIndicator,
                        cgsccpGttErrorsSelectorNotFound,
                        cgsccpGttErrorsIncorrectFormat,
                        cgsccpGttErrorsGtaNotFound,
                        cgsccpGttErrorsHopViolation,
                        cgsccpGttErrorsMapNotFound,
                        cgsccpGttErrorsUnequipedSS,
                        cgsccpGttErrorsSccpUnavailable,
                        cgsccpGttErrorsDpcUnavailable,
                        cgsccpGttErrorsSsUnavailable,
                        cgsccpGttErrorsDpcCongested,
                        cgsccpGttErrorsSsCongested,
                        cgsccpGttErrorsRouteFailure,
                        cgsccpGttErrorsSccpUnqualified
                    }
    STATUS          current
    DESCRIPTION
        "This notification is generated whenever any global
        title error is encountered in last interval specified
        by the cgsccpGttErrorPeriod and the
        cgsccpInstErrorIndicator will be set to true. The
        notification will also be generated when errors have
        abated. The notification is generated after the number
        of recovery intervals as specified by the
        cgsccpGttErrorRecoveryCount object has passed without
        any global title errors."
   ::= { ciscoGsccpMIBNotifs 3 }

ciscoGsccpSegReassUnsup NOTIFICATION-TYPE
    OBJECTS         {
                        cgspEventSequenceNumber,
                        cgspCLLICode,
                        cgsccpInstErrorIndicator,
                        cgsccpGttErrorsReassUnsupported,
                        cgsccpGttErrorsReassFailure,
                        cgsccpGttErrorsSegUnsupported,
                        cgsccpGttErrorsSegFailure
                    }
    STATUS          current
    DESCRIPTION
        "This notification is generated initially when a SCCP message
        is dropped due to a segmentation or reassembly unsupported
        or failure errors in last interval specified by the
        cgsccpGttErrorPeriod and the cgsccpInstErrorIndicator will be
        set to true.  The notification will also be generated after
        the number of recovery intervals as specified by the
        cgsccpGttErrorRecoveryCount object has passed without any
        segmentation or reassembly unsupported errors."
   ::= { ciscoGsccpMIBNotifs 4 }

ciscoGsccpSOGReceived NOTIFICATION-TYPE
    OBJECTS         {
                        cgspEventSequenceNumber,
                        cgspCLLICode,
                        cgsccpGttMapDisplayPC,
                        cgsccpGttMapDisplaySS
                    }
    STATUS          current
    DESCRIPTION
        "This notification is generated initially when a Subsystem
        Out-of-Service Grant is sent in response to a Subsystem
        Out-of-Service Request message. The affected PC and affected
        SSN are provided with this notification."
   ::= { ciscoGsccpMIBNotifs 5 }

ciscoGsccpRmtCongestion NOTIFICATION-TYPE
    OBJECTS         {
                        cgspEventSequenceNumber,
                        cgspCLLICode,
                        cgsccpGttMapDisplayPC,
                        cgsccpGttMapCongStatus,
                        cgsccpGttMapCongLvl1,
                        cgsccpGttMapCongLvl2,
                        cgsccpGttMapCongLvl3
                    }
    STATUS          current
    DESCRIPTION
        "This notification is generated initially when congestion is
        experienced in the remote SCCP component for the first time in
        last interval specified by the cgsccpGttErrorPeriod.  The
        notification is generated after the number of recovery intervals
        as specified by the cgsccpGttErrorRecoveryCount object has
        passed without any congestion errors and total number of local
        congestion observed for different congestion levels at the end
        of the interval along with the latest known congestion status
        for that remote signalling point will be provided."
   ::= { ciscoGsccpMIBNotifs 6 }

ciscoGsccpLocalSsStateChange NOTIFICATION-TYPE
    OBJECTS         {
                        cgspEventSequenceNumber,
                        cgspCLLICode,
                        cgsccpLocalDisplaySS,
                        cgsccpLocalSsStatus
                    }
    STATUS          current
    DESCRIPTION
        "The notification generated when a local application subsystem
        changes to a new state.  The subsystem number and the latest
        subsystem state will be provided in this notification."
   ::= { ciscoGsccpMIBNotifs 7 }
-- *******************************************************************
-- *
-- *  Conformance Information
-- *
-- *******************************************************************

ciscoGsccpMIBCompliances  OBJECT IDENTIFIER
    ::= { ciscoGsccpMIBConform 1 }

ciscoGsccpMIBGroups  OBJECT IDENTIFIER
    ::= { ciscoGsccpMIBConform 2 }

-- Compliance

ciscoGsccpMIBCompliance MODULE-COMPLIANCE
    STATUS          deprecated
    DESCRIPTION
        "The compliance statement for entities which implement
        the CISCO-ITP-GSCCP-MIB.my MIB"
    MODULE          -- this module
    MANDATORY-GROUPS {
                        ciscoGsccpGlobalEntryGroup,
                        ciscoGsccpInstTableEntryGroup,
                        ciscoGsccpGttConPcGroup,
                        ciscoGsccpGttAppGroup,
                        ciscoGsccpGttMapGroup,
                        ciscoGsccpGttSelGroup,
                        ciscoGsccpGttGtaGroup,
                        ciscoGsccpGttPrefGroup,
                        ciscoGsccpNotificationsGroup
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGrType
    MIN-ACCESS      read-only
    DESCRIPTION
        "Create/Write access is not required."

    OBJECT          cgsccpGttAppGrPc
    MIN-ACCESS      read-only
    DESCRIPTION
        "Create/Write access is not required."

    OBJECT          cgsccpGttAppGrSsn
    MIN-ACCESS      read-only
    DESCRIPTION
        "Create/Write access is not required."

    OBJECT          cgsccpGttAppGrRi
    MIN-ACCESS      read-only
    DESCRIPTION
        "Create/Write access is not required."

    OBJECT          cgsccpGttAppGrMult
    MIN-ACCESS      read-only
    DESCRIPTION
        "Create/Write access is not required."

    OBJECT          cgsccpGttAppGrAsName
    MIN-ACCESS      read-only
    DESCRIPTION
        "Create/Write access is not required."

    OBJECT          cgsccpGttAppGrNewSsn
    MIN-ACCESS      read-only
    DESCRIPTION
        "Create/Write access is not required."

    OBJECT          cgsccpGttAppGrRowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPrefOutAddr
    MIN-ACCESS      read-only
    DESCRIPTION
        "Create/Write access is not required."

    OBJECT          cgsccpGttPrefTblNAI
    MIN-ACCESS      read-only
    DESCRIPTION
        "Create/Write access is not required."

    OBJECT          cgsccpGttPrefTblNP
    MIN-ACCESS      read-only
    DESCRIPTION
        "Create/Write access is not required."

    OBJECT          cgsccpGttPrefItemNAI
    MIN-ACCESS      read-only
    DESCRIPTION
        "Create/Write access is not required."

    OBJECT          cgsccpGttPrefItemNP
    MIN-ACCESS      read-only
    DESCRIPTION
        "Create/Write access is not required."

    OBJECT          cgsccpGttPrefRowStatus
    MIN-ACCESS      read-only
    DESCRIPTION
        "Create/Write access is not required."
    ::= { ciscoGsccpMIBCompliances 1 }

ciscoGsccpMIBComplianceRev1 MODULE-COMPLIANCE
    STATUS          deprecated
    DESCRIPTION
        "The compliance statement for entities which implement
        the CISCO-ITP-GSCCP-MIB.my MIB"
    MODULE          -- this module
    MANDATORY-GROUPS {
                        ciscoGsccpGlobalEntryGroupRev1,
                        ciscoGsccpGttConPcGroup,
                        ciscoGsccpGttAppGroup,
                        ciscoGsccpGttMapGroup,
                        ciscoGsccpGttSelGroup,
                        ciscoGsccpGttGtaGroup,
                        ciscoGsccpGttPrefGroupRev1,
                        ciscoGsccpNotificationsGroup,
                        ciscoGsccpInstTableEntryGroupRev1
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGrType
    MIN-ACCESS      read-only
    DESCRIPTION
        "Create/Write access is not required."

    OBJECT          cgsccpGttAppGrPc
    MIN-ACCESS      read-only
    DESCRIPTION
        "Create/Write access is not required."

    OBJECT          cgsccpGttAppGrSsn
    MIN-ACCESS      read-only
    DESCRIPTION
        "Create/Write access is not required."

    OBJECT          cgsccpGttAppGrRi
    MIN-ACCESS      read-only
    DESCRIPTION
        "Create/Write access is not required."

    OBJECT          cgsccpGttAppGrMult
    MIN-ACCESS      read-only
    DESCRIPTION
        "Create/Write access is not required."

    OBJECT          cgsccpGttAppGrAsName
    MIN-ACCESS      read-only
    DESCRIPTION
        "Create/Write access is not required."

    OBJECT          cgsccpGttAppGrNewSsn
    MIN-ACCESS      read-only
    DESCRIPTION
        "Create/Write access is not required."

    OBJECT          cgsccpGttAppGrRowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPref2OutAddr
    MIN-ACCESS      read-only
    DESCRIPTION
        "Create/Write access is not required."

    OBJECT          cgsccpGttPref2TblNAI
    MIN-ACCESS      read-only
    DESCRIPTION
        "Create/Write access is not required."

    OBJECT          cgsccpGttPref2TblNP
    MIN-ACCESS      read-only
    DESCRIPTION
        "Create/Write access is not required."

    OBJECT          cgsccpGttPref2ItemNAI
    MIN-ACCESS      read-only
    DESCRIPTION
        "Create/Write access is not required."

    OBJECT          cgsccpGttPref2ItemNP
    MIN-ACCESS      read-only
    DESCRIPTION
        "Create/Write access is not required."

    OBJECT          cgsccpGttPref2RowStatus
    MIN-ACCESS      read-only
    DESCRIPTION
        "Create/Write access is not required."
    ::= { ciscoGsccpMIBCompliances 2 }

ciscoGsccpMIBComplianceRev2 MODULE-COMPLIANCE
    STATUS          deprecated
    DESCRIPTION
        "The compliance statement for entities which implement
        the CISCO-ITP-GSCCP-MIB.my MIB"
    MODULE          -- this module
    MANDATORY-GROUPS {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttAppGroupRev2,
                        ciscoGsccpGttGtaGroupRev2
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGrType
    MIN-ACCESS      read-only
    DESCRIPTION
        "Create/Write access is not required."

    OBJECT          cgsccpGttAppGrPc
    MIN-ACCESS      read-only
    DESCRIPTION
        "Create/Write access is not required."

    OBJECT          cgsccpGttAppGrSsn
    MIN-ACCESS      read-only
    DESCRIPTION
        "Create/Write access is not required."

    OBJECT          cgsccpGttAppGrRi
    MIN-ACCESS      read-only
    DESCRIPTION
        "Create/Write access is not required."

    OBJECT          cgsccpGttAppGrMult
    MIN-ACCESS      read-only
    DESCRIPTION
        "Create/Write access is not required."

    OBJECT          cgsccpGttAppGrAsName
    MIN-ACCESS      read-only
    DESCRIPTION
        "Create/Write access is not required."

    OBJECT          cgsccpGttAppGrNewSsn
    MIN-ACCESS      read-only
    DESCRIPTION
        "Create/Write access is not required."

    OBJECT          cgsccpGttAppGrRowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPref2OutAddr
    MIN-ACCESS      read-only
    DESCRIPTION
        "Create/Write access is not required."

    OBJECT          cgsccpGttPref2TblNAI
    MIN-ACCESS      read-only
    DESCRIPTION
        "Create/Write access is not required."

    OBJECT          cgsccpGttPref2TblNP
    MIN-ACCESS      read-only
    DESCRIPTION
        "Create/Write access is not required."

    OBJECT          cgsccpGttPref2ItemNAI
    MIN-ACCESS      read-only
    DESCRIPTION
        "Create/Write access is not required."

    OBJECT          cgsccpGttPref2ItemNP
    MIN-ACCESS      read-only
    DESCRIPTION
        "Create/Write access is not required."

    OBJECT          cgsccpGttPref2RowStatus
    MIN-ACCESS      read-only
    DESCRIPTION
        "Create/Write access is not required."
    ::= { ciscoGsccpMIBCompliances 3 }

ciscoGsccpMIBComplianceRev3 MODULE-COMPLIANCE
    STATUS          deprecated
    DESCRIPTION
        "The compliance statement for entities which implement
        the CISCO-ITP-GSCCP-MIB.my MIB"
    MODULE          -- this module
    MANDATORY-GROUPS {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttGtaGroupRev2,
                        ciscoGsccpGttAppGroupRev3
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGr2Mult
    MIN-ACCESS      read-only
    DESCRIPTION
        "Create/Write access is not required."

    OBJECT          cgsccpGttAppGr2Type
    MIN-ACCESS      read-only
    DESCRIPTION
        "Create/Write access is not required."

    OBJECT          cgsccpGttAppGr2Cost
    MIN-ACCESS      read-only
    DESCRIPTION
        "Create/Write access is not required."

    OBJECT          cgsccpGttAppGr2Weight
    MIN-ACCESS      read-only
    DESCRIPTION
        "Create/Write access is not required."

    OBJECT          cgsccpGttAppGr2Pc
    MIN-ACCESS      read-only
    DESCRIPTION
        "Create/Write access is not required."

    OBJECT          cgsccpGttAppGr2Ssn
    MIN-ACCESS      read-only
    DESCRIPTION
        "Create/Write access is not required."

    OBJECT          cgsccpGttAppGr2Ri
    MIN-ACCESS      read-only
    DESCRIPTION
        "Create/Write access is not required."

    OBJECT          cgsccpGttAppGr2AsName
    MIN-ACCESS      read-only
    DESCRIPTION
        "Create/Write access is not required."

    OBJECT          cgsccpGttAppGr2NewSsn
    MIN-ACCESS      read-only
    DESCRIPTION
        "Create/Write access is not required."

    OBJECT          cgsccpGttAppGr2Network
    MIN-ACCESS      read-only
    DESCRIPTION
        "Create/Write access is not required."

    OBJECT          cgsccpGttAppGr2RowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPref2OutAddr
    MIN-ACCESS      read-only
    DESCRIPTION
        "Create/Write access is not required."

    OBJECT          cgsccpGttPref2TblNAI
    MIN-ACCESS      read-only
    DESCRIPTION
        "Create/Write access is not required."

    OBJECT          cgsccpGttPref2TblNP
    MIN-ACCESS      read-only
    DESCRIPTION
        "Create/Write access is not required."

    OBJECT          cgsccpGttPref2ItemNAI
    MIN-ACCESS      read-only
    DESCRIPTION
        "Create/Write access is not required."

    OBJECT          cgsccpGttPref2ItemNP
    MIN-ACCESS      read-only
    DESCRIPTION
        "Create/Write access is not required."

    OBJECT          cgsccpGttPref2RowStatus
    MIN-ACCESS      read-only
    DESCRIPTION
        "Create/Write access is not required."
    ::= { ciscoGsccpMIBCompliances 4 }

ciscoGsccpMIBComplianceRev4 MODULE-COMPLIANCE
    STATUS          deprecated
    DESCRIPTION
        "The compliance statement for entities which implement
        the CISCO-ITP-GSCCP-MIB.my MIB"
    MODULE          -- this module
    MANDATORY-GROUPS {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttGtaGroupRev2,
                        ciscoGsccpGttAppGroupRev3,
                        ciscoGsccpNotificationsGroupSup1,
                        ciscoGsccpGttErrorsGroup
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGr2Mult
    MIN-ACCESS      read-only
    DESCRIPTION
        "Create/Write access is not required."

    OBJECT          cgsccpGttAppGr2Type
    MIN-ACCESS      read-only
    DESCRIPTION
        "Create/Write access is not required."

    OBJECT          cgsccpGttAppGr2Cost
    MIN-ACCESS      read-only
    DESCRIPTION
        "Create/Write access is not required."

    OBJECT          cgsccpGttAppGr2Weight
    MIN-ACCESS      read-only
    DESCRIPTION
        "Create/Write access is not required."

    OBJECT          cgsccpGttAppGr2Pc
    MIN-ACCESS      read-only
    DESCRIPTION
        "Create/Write access is not required."

    OBJECT          cgsccpGttAppGr2Ssn
    MIN-ACCESS      read-only
    DESCRIPTION
        "Create/Write access is not required."

    OBJECT          cgsccpGttAppGr2Ri
    MIN-ACCESS      read-only
    DESCRIPTION
        "Create/Write access is not required."

    OBJECT          cgsccpGttAppGr2AsName
    MIN-ACCESS      read-only
    DESCRIPTION
        "Create/Write access is not required."

    OBJECT          cgsccpGttAppGr2NewSsn
    MIN-ACCESS      read-only
    DESCRIPTION
        "Create/Write access is not required."

    OBJECT          cgsccpGttAppGr2Network
    MIN-ACCESS      read-only
    DESCRIPTION
        "Create/Write access is not required."

    OBJECT          cgsccpGttAppGr2RowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPref2OutAddr
    MIN-ACCESS      read-only
    DESCRIPTION
        "Create/Write access is not required."

    OBJECT          cgsccpGttPref2TblNAI
    MIN-ACCESS      read-only
    DESCRIPTION
        "Create/Write access is not required."

    OBJECT          cgsccpGttPref2TblNP
    MIN-ACCESS      read-only
    DESCRIPTION
        "Create/Write access is not required."

    OBJECT          cgsccpGttPref2ItemNAI
    MIN-ACCESS      read-only
    DESCRIPTION
        "Create/Write access is not required."

    OBJECT          cgsccpGttPref2ItemNP
    MIN-ACCESS      read-only
    DESCRIPTION
        "Create/Write access is not required."

    OBJECT          cgsccpGttPref2RowStatus
    MIN-ACCESS      read-only
    DESCRIPTION
        "Create/Write access is not required."
    ::= { ciscoGsccpMIBCompliances 5 }

ciscoGsccpMIBComplianceRev5 MODULE-COMPLIANCE
    STATUS          deprecated
    DESCRIPTION
        "The compliance statement for entities which implement
        the CISCO-ITP-GSCCP-MIB.my MIB"
    MODULE          -- this module
    MANDATORY-GROUPS {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttGtaGroupRev2,
                        ciscoGsccpGttAppGroupRev3,
                        ciscoGsccpNotificationsGroupSup1,
                        ciscoGsccpGttErrorsGroup,
                        ciscoGsccpGttPrefGroupSup1
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGr2Mult
    MIN-ACCESS      read-only
    DESCRIPTION
        "Create/Write access is not required."

    OBJECT          cgsccpGttAppGr2Type
    MIN-ACCESS      read-only
    DESCRIPTION
        "Create/Write access is not required."

    OBJECT          cgsccpGttAppGr2Cost
    MIN-ACCESS      read-only
    DESCRIPTION
        "Create/Write access is not required."

    OBJECT          cgsccpGttAppGr2Weight
    MIN-ACCESS      read-only
    DESCRIPTION
        "Create/Write access is not required."

    OBJECT          cgsccpGttAppGr2Pc
    MIN-ACCESS      read-only
    DESCRIPTION
        "Create/Write access is not required."

    OBJECT          cgsccpGttAppGr2Ssn
    MIN-ACCESS      read-only
    DESCRIPTION
        "Create/Write access is not required."

    OBJECT          cgsccpGttAppGr2Ri
    MIN-ACCESS      read-only
    DESCRIPTION
        "Create/Write access is not required."

    OBJECT          cgsccpGttAppGr2AsName
    MIN-ACCESS      read-only
    DESCRIPTION
        "Create/Write access is not required."

    OBJECT          cgsccpGttAppGr2NewSsn
    MIN-ACCESS      read-only
    DESCRIPTION
        "Create/Write access is not required."

    OBJECT          cgsccpGttAppGr2Network
    MIN-ACCESS      read-only
    DESCRIPTION
        "Create/Write access is not required."

    OBJECT          cgsccpGttAppGr2RowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPref2OutAddr
    MIN-ACCESS      read-only
    DESCRIPTION
        "Create/Write access is not required."

    OBJECT          cgsccpGttPref2TblNAI
    MIN-ACCESS      read-only
    DESCRIPTION
        "Create/Write access is not required."

    OBJECT          cgsccpGttPref2TblNP
    MIN-ACCESS      read-only
    DESCRIPTION
        "Create/Write access is not required."

    OBJECT          cgsccpGttPref2ItemNAI
    MIN-ACCESS      read-only
    DESCRIPTION
        "Create/Write access is not required."

    OBJECT          cgsccpGttPref2ItemNP
    MIN-ACCESS      read-only
    DESCRIPTION
        "Create/Write access is not required."

    OBJECT          cgsccpGttPref2RowStatus
    MIN-ACCESS      read-only
    DESCRIPTION
        "Create/Write access is not required."

    OBJECT          cgsccpGttPref2EncodingScheme
    MIN-ACCESS      read-only
    DESCRIPTION
        "Create/Write access is not required."
    ::= { ciscoGsccpMIBCompliances 6 }

ciscoGsccpMIBComplianceRev6 MODULE-COMPLIANCE
    STATUS          deprecated
    DESCRIPTION
        "The compliance statement for entities which implement
        the CISCO-ITP-GSCCP-MIB.my MIB"
    MODULE          -- this module
    MANDATORY-GROUPS {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttGtaGroupRev2,
                        ciscoGsccpGttAppGroupRev3,
                        ciscoGsccpNotificationsGroupSup1,
                        ciscoGsccpGttErrorsGroup,
                        ciscoGsccpGttPrefGroupSup1,
                        ciscoGsccpGlobalEntryGroupSup1,
                        ciscoGsccpInstTableEntryGroupSup1,
                        ciscoGsccpGttMapGroupSup1,
                        ciscoGsccpGttErrorsGroupSup1,
                        ciscoGsccpGttSsnGroup,
                        ciscoGsccpGttSsnClassGroup,
                        ciscoGsccpNotificationsInfoGroup,
                        ciscoGsccpNotificationsGroupSup2
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGr2Mult
    MIN-ACCESS      read-only
    DESCRIPTION
        "Create/Write access is not required."

    OBJECT          cgsccpGttAppGr2Type
    MIN-ACCESS      read-only
    DESCRIPTION
        "Create/Write access is not required."

    OBJECT          cgsccpGttAppGr2Cost
    MIN-ACCESS      read-only
    DESCRIPTION
        "Create/Write access is not required."

    OBJECT          cgsccpGttAppGr2Weight
    MIN-ACCESS      read-only
    DESCRIPTION
        "Create/Write access is not required."

    OBJECT          cgsccpGttAppGr2Pc
    MIN-ACCESS      read-only
    DESCRIPTION
        "Create/Write access is not required."

    OBJECT          cgsccpGttAppGr2Ssn
    MIN-ACCESS      read-only
    DESCRIPTION
        "Create/Write access is not required."

    OBJECT          cgsccpGttAppGr2Ri
    MIN-ACCESS      read-only
    DESCRIPTION
        "Create/Write access is not required."

    OBJECT          cgsccpGttAppGr2AsName
    MIN-ACCESS      read-only
    DESCRIPTION
        "Create/Write access is not required."

    OBJECT          cgsccpGttAppGr2NewSsn
    MIN-ACCESS      read-only
    DESCRIPTION
        "Create/Write access is not required."

    OBJECT          cgsccpGttAppGr2Network
    MIN-ACCESS      read-only
    DESCRIPTION
        "Create/Write access is not required."

    OBJECT          cgsccpGttAppGr2RowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPref2OutAddr
    MIN-ACCESS      read-only
    DESCRIPTION
        "Create/Write access is not required."

    OBJECT          cgsccpGttPref2TblNAI
    MIN-ACCESS      read-only
    DESCRIPTION
        "Create/Write access is not required."

    OBJECT          cgsccpGttPref2TblNP
    MIN-ACCESS      read-only
    DESCRIPTION
        "Create/Write access is not required."

    OBJECT          cgsccpGttPref2ItemNAI
    MIN-ACCESS      read-only
    DESCRIPTION
        "Create/Write access is not required."

    OBJECT          cgsccpGttPref2ItemNP
    MIN-ACCESS      read-only
    DESCRIPTION
        "Create/Write access is not required."

    OBJECT          cgsccpGttPref2RowStatus
    MIN-ACCESS      read-only
    DESCRIPTION
        "Create/Write access is not required."

    OBJECT          cgsccpGttPref2EncodingScheme
    MIN-ACCESS      read-only
    DESCRIPTION
        "Create/Write access is not required."
    ::= { ciscoGsccpMIBCompliances 7 }

ciscoGsccpMIBComplianceRev7 MODULE-COMPLIANCE
    STATUS          current
    DESCRIPTION
        "The compliance statement for entities which implement
        the CISCO-ITP-GSCCP-MIB.my MIB."
    MODULE          -- this module
    MANDATORY-GROUPS {
                        ciscoGsccpGlobalEntryGroupRev1,
                        ciscoGsccpGttConPcGroup,
                        ciscoGsccpGttMapGroup,
                        ciscoGsccpGttSelGroup,
                        ciscoGsccpGttPrefGroupRev1,
                        ciscoGsccpNotificationsGroup,
                        ciscoGsccpInstTableEntryGroupRev1,
                        ciscoGsccpGttGtaGroupRev2,
                        ciscoGsccpGttAppGroupRev3,
                        ciscoGsccpNotificationsGroupSup1,
                        ciscoGsccpGttErrorsGroup,
                        ciscoGsccpGttPrefGroupSup1,
                        ciscoGsccpGlobalEntryGroupSup1,
                        ciscoGsccpInstTableEntryGroupSup1,
                        ciscoGsccpGttMapGroupSup1,
                        ciscoGsccpGttErrorsGroupSup1,
                        ciscoGsccpGttSsnGroup,
                        ciscoGsccpGttSsnClassGroup,
                        ciscoGsccpNotificationsInfoGroup,
                        ciscoGsccpNotificationsGroupSup2,
                        ciscoGsccpGttSelGroupSup1
                    }

    OBJECT          cgsccpGttTranslateSample
    MIN-ACCESS      read-only
    DESCRIPTION
        "Write access is not required."

    OBJECT          cgsccpGttTranslatePeriod
    MIN-ACCESS      read-only
    DESCRIPTION
        "Write access is not required."

    OBJECT          cgsccpInstRowStatus
    MIN-ACCESS      read-only
    DESCRIPTION
        "Create/Write access is not required."

    OBJECT          cgsccpGttAppGr2Mult
    MIN-ACCESS      read-only
    DESCRIPTION
        "Create/Write access is not required."

    OBJECT          cgsccpGttAppGr2Type
    MIN-ACCESS      read-only
    DESCRIPTION
        "Create/Write access is not required."

    OBJECT          cgsccpGttAppGr2Cost
    MIN-ACCESS      read-only
    DESCRIPTION
        "Create/Write access is not required."

    OBJECT          cgsccpGttAppGr2Weight
    MIN-ACCESS      read-only
    DESCRIPTION
        "Create/Write access is not required."

    OBJECT          cgsccpGttAppGr2Pc
    MIN-ACCESS      read-only
    DESCRIPTION
        "Create/Write access is not required."

    OBJECT          cgsccpGttAppGr2Ssn
    MIN-ACCESS      read-only
    DESCRIPTION
        "Create/Write access is not required."

    OBJECT          cgsccpGttAppGr2Ri
    MIN-ACCESS      read-only
    DESCRIPTION
        "Create/Write access is not required."

    OBJECT          cgsccpGttAppGr2AsName
    MIN-ACCESS      read-only
    DESCRIPTION
        "Create/Write access is not required."

    OBJECT          cgsccpGttAppGr2NewSsn
    MIN-ACCESS      read-only
    DESCRIPTION
        "Create/Write access is not required."

    OBJECT          cgsccpGttAppGr2Network
    MIN-ACCESS      read-only
    DESCRIPTION
        "Create/Write access is not required."

    OBJECT          cgsccpGttAppGr2RowStatus
    MIN-ACCESS      read-only
    DESCRIPTION
        "Create/Write access is not required."

    OBJECT          cgsccpGttMapType
    MIN-ACCESS      read-only
    DESCRIPTION
        "Create/Write access is not required."

    OBJECT          cgsccpGttMapMultInd
    MIN-ACCESS      read-only
    DESCRIPTION
        "Create/Write access is not required."

    OBJECT          cgsccpGttMapBackupPc
    MIN-ACCESS      read-only
    DESCRIPTION
        "Create/Write access is not required."

    OBJECT          cgsccpGttMapBackupSsn
    MIN-ACCESS      read-only
    DESCRIPTION
        "Create/Write access is not required."

    OBJECT          cgsccpGttMapConPcList
    MIN-ACCESS      read-only
    DESCRIPTION
        "Create/Write access is not required."

    OBJECT          cgsccpGttMapReRouteOnCong
    MIN-ACCESS      read-only
    DESCRIPTION
        "Create/Write access is not required."

    OBJECT          cgsccpGttMapAdjacent
    MIN-ACCESS      read-only
    DESCRIPTION
        "Create/Write access is not required."

    OBJECT          cgsccpGttMapRowStatus
    MIN-ACCESS      read-only
    DESCRIPTION
        "Create/Write access is not required."

    OBJECT          cgsccpGttSelName
    MIN-ACCESS      read-only
    DESCRIPTION
        "Create/Write access is not required."

    OBJECT          cgsccpGttSelQOS
    MIN-ACCESS      read-only
    DESCRIPTION
        "Create/Write access is not required."

    OBJECT          cgsccpGttSelPrePrefConv
    MIN-ACCESS      read-only
    DESCRIPTION
        "Create/Write access is not required."

    OBJECT          cgsccpGttSelPostPrefConv
    MIN-ACCESS      read-only
    DESCRIPTION
        "Create/Write access is not required."

    OBJECT          cgsccpGttSelRowStatus
    MIN-ACCESS      read-only
    DESCRIPTION
        "Create/Write access is not required."

    OBJECT          cgsccpGttGtaSelName
    MIN-ACCESS      read-only
    DESCRIPTION
        "Create/Write access is not required."

    OBJECT          cgsccpGttGtaResType
    MIN-ACCESS      read-only
    DESCRIPTION
        "Create/Write access is not required."

    OBJECT          cgsccpGttGtaResPc
    MIN-ACCESS      read-only
    DESCRIPTION
        "Create/Write access is not required."

    OBJECT          cgsccpGttGtaResMap
    MIN-ACCESS      read-only
    DESCRIPTION
        "Create/Write access is not required."

    OBJECT          cgsccpGttGtaResAppGroup
    MIN-ACCESS      read-only
    DESCRIPTION
        "Create/Write access is not required."

    OBJECT          cgsccpGttGtaTTorSSN
    MIN-ACCESS      read-only
    DESCRIPTION
        "Create/Write access is not required."

    OBJECT          cgsccpGttGtaTTorSSNvalue
    MIN-ACCESS      read-only
    DESCRIPTION
        "Create/Write access is not required."

    OBJECT          cgsccpGttGtaRoutingInd
    MIN-ACCESS      read-only
    DESCRIPTION
        "Create/Write access is not required."

    OBJECT          cgsccpGttGtaQOS
    MIN-ACCESS      read-only
    DESCRIPTION
        "Create/Write access is not required."

    OBJECT          cgsccpGttGtaAsName
    MIN-ACCESS      read-only
    DESCRIPTION
        "Create/Write access is not required."

    OBJECT          cgsccpGttGtaRowStatus
    MIN-ACCESS      read-only
    DESCRIPTION
        "Create/Write access is not required."

    OBJECT          cgsccpGttPref2OutAddr
    MIN-ACCESS      read-only
    DESCRIPTION
        "Create/Write access is not required."

    OBJECT          cgsccpGttPref2TblNAI
    MIN-ACCESS      read-only
    DESCRIPTION
        "Create/Write access is not required."

    OBJECT          cgsccpGttPref2TblNP
    MIN-ACCESS      read-only
    DESCRIPTION
        "Create/Write access is not required."

    OBJECT          cgsccpGttPref2ItemNAI
    MIN-ACCESS      read-only
    DESCRIPTION
        "Create/Write access is not required."

    OBJECT          cgsccpGttPref2ItemNP
    MIN-ACCESS      read-only
    DESCRIPTION
        "Create/Write access is not required."

    OBJECT          cgsccpGttPref2RowStatus
    MIN-ACCESS      read-only
    DESCRIPTION
        "Create/Write access is not required."

    OBJECT          cgsccpGttPref2EncodingScheme
    MIN-ACCESS      read-only
    DESCRIPTION
        "Create/Write access is not required."

    OBJECT          cgsccpGttNextSelName
    MIN-ACCESS      read-only
    DESCRIPTION
        "Create/Write access is not required."

    OBJECT          cgsccpGttNextSelRefed
    MIN-ACCESS      read-only
    DESCRIPTION
        "Create/Write access is not required."
    ::= { ciscoGsccpMIBCompliances 8 }

-- Units of Conformance

ciscoGsccpGlobalEntryGroup OBJECT-GROUP
    OBJECTS         {
                        cgsccpGttTranslateSample,
                        cgsccpGttTranslatePeriod,
                        cgsccpGttTranslateRate,
                        cgsccpGttMapStateNotifEnabled,
                        cgsccpGttLoadTableNotifEnabled
                    }
    STATUS          deprecated
    DESCRIPTION
        "Gateway SCCP Scalar objects."
    ::= { ciscoGsccpMIBGroups 1 }

ciscoGsccpInstTableEntryGroup OBJECT-GROUP
    OBJECTS         {
                        cgsccpInstTotalMsgs,
                        cgsccpInstLocalMsgs,
                        cgsccpInstTotalGttMsgs,
                        cgsccpInstUDTMsgsSent,
                        cgsccpInstUDTSMsgsSent,
                        cgsccpInstUDTSMsgsAttempted,
                        cgsccpInstUDTMsgsRcvd,
                        cgsccpInstUDTSMsgsRcvd,
                        cgsccpInstXUDTMsgsSent,
                        cgsccpInstXUDTSMsgsAttempted,
                        cgsccpInstXUDTSMsgsSent,
                        cgsccpInstXUDTMsgsRcvd,
                        cgsccpInstXUDTSMsgsRcvd,
                        cgsccpInstLUDTMsgsSent,
                        cgsccpInstLUDTSMsgsSent,
                        cgsccpInstLUDTMsgsRcvd,
                        cgsccpInstLUDTSMsgsRcvd,
                        cgsccpInstCrToMtp,
                        cgsccpInstCrefToMtp,
                        cgsccpInstCrFromMtp,
                        cgsccpInstCrefFromMtp,
                        cgsccpInstRsrToMtp,
                        cgsccpInstRsrFromMtp,
                        cgsccpInstErrToMtp,
                        cgsccpInstErrFromMtp,
                        cgsccpInstQ752T7E1,
                        cgsccpInstInvalidGttFormat,
                        cgsccpInstQ752T7E13,
                        cgsccpInstMapNotFound,
                        cgsccpInstQ752T7E7,
                        cgsccpInstGttConfigStatus,
                        cgsccpInstConfigTS,
                        cgsccpInstGttConfigTS,
                        cgsccpInstLastURL,
                        cgsccpInstConPcTableEntries,
                        cgsccpInstMapTableEntries,
                        cgsccpInstGtaTableEntries,
                        cgsccpInstSelTableEntries,
                        cgsccpInstAppGrTableEntries,
                        cgsccpInstRowStatus
                    }
    STATUS          deprecated
    DESCRIPTION
        "SCCP main objects."
    ::= { ciscoGsccpMIBGroups 2 }

ciscoGsccpGttConPcGroup OBJECT-GROUP
    OBJECTS         { cgsccpGttConPcRowStatus }
    STATUS          current
    DESCRIPTION
        "SCCP Concerned Point Code objects."
    ::= { ciscoGsccpMIBGroups 3 }

ciscoGsccpGttAppGroup OBJECT-GROUP
    OBJECTS         {
                        cgsccpGttAppGrType,
                        cgsccpGttAppGrPc,
                        cgsccpGttAppGrSsn,
                        cgsccpGttAppGrRi,
                        cgsccpGttAppGrMult,
                        cgsccpGttAppGrRefCount,
                        cgsccpGttAppGrAsName,
                        cgsccpGttAppGrNewSsn,
                        cgsccpGttAppGrNumUsed,
                        cgsccpGttAppGrRowStatus
                    }
    STATUS          deprecated
    DESCRIPTION
        "SCCP GTT Application Group objects."
    ::= { ciscoGsccpMIBGroups 4 }

ciscoGsccpGttMapGroup OBJECT-GROUP
    OBJECTS         {
                        cgsccpGttMapDisplayPC,
                        cgsccpGttMapDisplaySS,
                        cgsccpGttMapType,
                        cgsccpGttMapPcStatus,
                        cgsccpGttMapSsStatus,
                        cgsccpGttMapMultInd,
                        cgsccpGttMapBackupPc,
                        cgsccpGttMapBackupSsn,
                        cgsccpGttMapConPcList,
                        cgsccpGttMapReRouteOnCong,
                        cgsccpGttMapAdjacent,
                        cgsccpGttMapLastSsUsed,
                        cgsccpGttMapUsed,
                        cgsccpGttMapAltUsed,
                        cgsccpGttMapSccpUnavail,
                        cgsccpGttMapQ752T7E3Fail,
                        cgsccpGttMapQ752T7E3Un,
                        cgsccpGttMapQ752T7E4,
                        cgsccpGttMapQ752T7E5,
                        cgsccpGttMapQ752T7E6,
                        cgsccpGttMapRefCount,
                        cgsccpGttMapCongStatus,
                        cgsccpGttMapRowStatus
                    }
    STATUS          current
    DESCRIPTION
        "SCCP GTT Mated Application objects."
    ::= { ciscoGsccpMIBGroups 5 }

ciscoGsccpGttSelGroup OBJECT-GROUP
    OBJECTS         {
                        cgsccpGttSelName,
                        cgsccpGttSelNumPerf,
                        cgsccpGttQ752T7E2,
                        cgsccpGttSelQOS,
                        cgsccpGttSelRefCount,
                        cgsccpGttSelPrePrefConv,
                        cgsccpGttSelPostPrefConv,
                        cgsccpGttSelRowStatus
                    }
    STATUS          current
    DESCRIPTION
        "SCCP GTT Selector objects."
    ::= { ciscoGsccpMIBGroups 6 }

ciscoGsccpGttGtaGroup OBJECT-GROUP
    OBJECTS         {
                        cgsccpGttGtaSelName,
                        cgsccpGttGtaResType,
                        cgsccpGttGtaResPc,
                        cgsccpGttGtaResMap,
                        cgsccpGttGtaResAppGroup,
                        cgsccpGttGtaTTorSSN,
                        cgsccpGttGtaTTorSSNvalue,
                        cgsccpGttGtaRoutingInd,
                        cgsccpGttGtaQOS,
                        cgsccpGttGtaAddrDisp,
                        cgsccpGttGtaAddrLen,
                        cgsccpGttGtaAsName,
                        cgsccpGttGtaRowStatus
                    }
    STATUS          deprecated
    DESCRIPTION
        "SCCP GTT Global Title Address objects."
    ::= { ciscoGsccpMIBGroups 7 }

ciscoGsccpGttPrefGroup OBJECT-GROUP
    OBJECTS         {
                        cgsccpGttPrefOutAddr,
                        cgsccpGttPrefTblNAI,
                        cgsccpGttPrefTblNP,
                        cgsccpGttPrefItemNAI,
                        cgsccpGttPrefItemNP,
                        cgsccpGttPrefRowStatus
                    }
    STATUS          deprecated
    DESCRIPTION
        "SCCP GTT Prefix Conversion Table objects."
    ::= { ciscoGsccpMIBGroups 8 }

ciscoGsccpNotificationsGroup NOTIFICATION-GROUP
   NOTIFICATIONS    {
                        ciscoGsccpGttMapStateChange,
                        ciscoGsccpGttLoadTable
                    }
    STATUS          current
    DESCRIPTION
        "SCCP notification objects."
    ::= { ciscoGsccpMIBGroups 9 }

ciscoGsccpGttPrefGroupRev1 OBJECT-GROUP
    OBJECTS         {
                        cgsccpGttPref2OutAddr,
                        cgsccpGttPref2TblNAI,
                        cgsccpGttPref2TblNP,
                        cgsccpGttPref2ItemNAI,
                        cgsccpGttPref2ItemNP,
                        cgsccpGttPref2RowStatus
                    }
    STATUS          current
    DESCRIPTION
        "SCCP GTT Prefix Conversion Table objects."
    ::= { ciscoGsccpMIBGroups 10 }

ciscoGsccpInstTableEntryGroupRev1 OBJECT-GROUP
    OBJECTS         {
                        cgsccpInstTotalMsgs,
                        cgsccpInstLocalMsgs,
                        cgsccpInstTotalGttMsgs,
                        cgsccpInstUDTMsgsSent,
                        cgsccpInstUDTSMsgsSent,
                        cgsccpInstUDTSMsgsAttempted,
                        cgsccpInstUDTMsgsRcvd,
                        cgsccpInstUDTSMsgsRcvd,
                        cgsccpInstXUDTMsgsSent,
                        cgsccpInstXUDTSMsgsAttempted,
                        cgsccpInstXUDTSMsgsSent,
                        cgsccpInstXUDTMsgsRcvd,
                        cgsccpInstXUDTSMsgsRcvd,
                        cgsccpInstLUDTMsgsSent,
                        cgsccpInstLUDTSMsgsSent,
                        cgsccpInstLUDTMsgsRcvd,
                        cgsccpInstLUDTSMsgsRcvd,
                        cgsccpInstCrToMtp,
                        cgsccpInstCrefToMtp,
                        cgsccpInstCrFromMtp,
                        cgsccpInstCrefFromMtp,
                        cgsccpInstRsrToMtp,
                        cgsccpInstRsrFromMtp,
                        cgsccpInstErrToMtp,
                        cgsccpInstErrFromMtp,
                        cgsccpInstQ752T7E1,
                        cgsccpInstInvalidGttFormat,
                        cgsccpInstQ752T7E13,
                        cgsccpInstMapNotFound,
                        cgsccpInstQ752T7E7,
                        cgsccpInstGttConfigStatus,
                        cgsccpInstConfigTS,
                        cgsccpInstGttConfigTS,
                        cgsccpInstLastURL,
                        cgsccpInstConPcTableEntries,
                        cgsccpInstMapTableEntries,
                        cgsccpInstGtaTableEntries,
                        cgsccpInstSelTableEntries,
                        cgsccpInstAppGrTableEntries,
                        cgsccpInstRowStatus,
                        cgsccpInstPrefTableEntries,
                        cgsccpInstQ752Unqualified
                    }
    STATUS          current
    DESCRIPTION
        "SCCP main objects."
    ::= { ciscoGsccpMIBGroups 11 }

ciscoGsccpGlobalEntryGroupRev1 OBJECT-GROUP
    OBJECTS         {
                        cgsccpGttTranslateSample,
                        cgsccpGttTranslatePeriod,
                        cgsccpGttTranslateRate,
                        cgsccpGttMapStateNotifEnabled,
                        cgsccpGttLoadTableNotifEnabled,
                        cgsccpGttTranslateTS
                    }
    STATUS          current
    DESCRIPTION
        "Gateway SCCP Scalar objects."
    ::= { ciscoGsccpMIBGroups 12 }

ciscoGsccpGttAppGroupRev2 OBJECT-GROUP
    OBJECTS         {
                        cgsccpGttAppGrType,
                        cgsccpGttAppGrPc,
                        cgsccpGttAppGrSsn,
                        cgsccpGttAppGrRi,
                        cgsccpGttAppGrMult,
                        cgsccpGttAppGrRefCount,
                        cgsccpGttAppGrAsName,
                        cgsccpGttAppGrNewSsn,
                        cgsccpGttAppGrNumUsed,
                        cgsccpGttAppGrRowStatus,
                        cgsccpGttAppGrNetwork
                    }
    STATUS          deprecated
    DESCRIPTION
        "SCCP GTT Application Group objects."
    ::= { ciscoGsccpMIBGroups 13 }

ciscoGsccpGttGtaGroupRev2 OBJECT-GROUP
    OBJECTS         {
                        cgsccpGttGtaSelName,
                        cgsccpGttGtaResType,
                        cgsccpGttGtaResPc,
                        cgsccpGttGtaResMap,
                        cgsccpGttGtaResAppGroup,
                        cgsccpGttGtaTTorSSN,
                        cgsccpGttGtaTTorSSNvalue,
                        cgsccpGttGtaRoutingInd,
                        cgsccpGttGtaQOS,
                        cgsccpGttGtaAddrDisp,
                        cgsccpGttGtaAddrLen,
                        cgsccpGttGtaAsName,
                        cgsccpGttGtaRowStatus,
                        cgsccpGttGtaNetwork
                    }
    STATUS          current
    DESCRIPTION
        "SCCP GTT Global Title Address objects."
    ::= { ciscoGsccpMIBGroups 14 }

ciscoGsccpGttAppGroupRev3 OBJECT-GROUP
    OBJECTS         {
                        cgsccpGttAppGr2Mult,
                        cgsccpGttAppGr2Type,
                        cgsccpGttAppGr2Cost,
                        cgsccpGttAppGr2Weight,
                        cgsccpGttAppGr2Pc,
                        cgsccpGttAppGr2Ssn,
                        cgsccpGttAppGr2Ri,
                        cgsccpGttAppGr2RefCount,
                        cgsccpGttAppGr2AsName,
                        cgsccpGttAppGr2NewSsn,
                        cgsccpGttAppGr2NumUsed,
                        cgsccpGttAppGr2Network,
                        cgsccpGttAppGr2RowStatus
                    }
    STATUS          current
    DESCRIPTION
        "SCCP GTT Application Group objects."
    ::= { ciscoGsccpMIBGroups 15 }

ciscoGsccpNotificationsGroupSup1 NOTIFICATION-GROUP
   NOTIFICATIONS    { ciscoGsccpGttErrors }
    STATUS          current
    DESCRIPTION
        "SCCP Error notification objects."
    ::= { ciscoGsccpMIBGroups 16 }

ciscoGsccpGttErrorsGroup OBJECT-GROUP
    OBJECTS         {
                        cgsccpGttErrorPeriod,
                        cgsccpGttErrorRecoveryCount,
                        cgsccpInstErrorIndicator,
                        cgsccpGttTransErrorsNotifEnabled,
                        cgsccpGttErrorsSelectorNotFound,
                        cgsccpGttErrorsIncorrectFormat,
                        cgsccpGttErrorsGtaNotFound,
                        cgsccpGttErrorsHopViolation,
                        cgsccpGttErrorsMapNotFound,
                        cgsccpGttErrorsUnequipedSS,
                        cgsccpGttErrorsSccpUnavailable,
                        cgsccpGttErrorsDpcUnavailable,
                        cgsccpGttErrorsSsUnavailable,
                        cgsccpGttErrorsDpcCongested,
                        cgsccpGttErrorsSsCongested,
                        cgsccpGttErrorsRouteFailure,
                        cgsccpGttErrorsSccpUnqualified
                    }
    STATUS          current
    DESCRIPTION
        "SCCP GTT Application Group objects."
    ::= { ciscoGsccpMIBGroups 17 }

ciscoGsccpGttPrefGroupSup1 OBJECT-GROUP
    OBJECTS         { cgsccpGttPref2EncodingScheme }
    STATUS          current
    DESCRIPTION
        "SCCP GTT additional prefix conversion objects."
    ::= { ciscoGsccpMIBGroups 18 }

ciscoGsccpGlobalEntryGroupSup1 OBJECT-GROUP
    OBJECTS         { cgsccpGttTranslatePhysicalIndex }
    STATUS          current
    DESCRIPTION
        "SCCP translation physical index."
    ::= { ciscoGsccpMIBGroups 19 }

ciscoGsccpInstTableEntryGroupSup1 OBJECT-GROUP
    OBJECTS         {
                        cgsccpInstReassUnsup,
                        cgsccpInstReassFail,
                        cgsccpInstSegUnsup,
                        cgsccpInstSegFail
                    }
    STATUS          current
    DESCRIPTION
        "SCCP Instance table additional objects."
    ::= { ciscoGsccpMIBGroups 20 }

ciscoGsccpGttMapGroupSup1 OBJECT-GROUP
    OBJECTS         {
                        cgsccpGttMapCongLvl1,
                        cgsccpGttMapCongLvl2,
                        cgsccpGttMapCongLvl3,
                        cgsccpGttMapSSPRcvd,
                        cgsccpGttMapSSARcvd
                    }
    STATUS          current
    DESCRIPTION
        "SCCP GTT Mated Application additional objects."
    ::= { ciscoGsccpMIBGroups 21 }

ciscoGsccpGttErrorsGroupSup1 OBJECT-GROUP
    OBJECTS         {
                        cgsccpGttErrorsReassUnsupported,
                        cgsccpGttErrorsReassFailure,
                        cgsccpGttErrorsSegUnsupported,
                        cgsccpGttErrorsSegFailure
                    }
    STATUS          current
    DESCRIPTION
        "SCCP GTT additional error objects."
    ::= { ciscoGsccpMIBGroups 22 }

ciscoGsccpGttSsnGroup OBJECT-GROUP
    OBJECTS         {
                        cgsccpSSNNumProhibits,
                        cgsccpSSNNumAllows
                    }
    STATUS          current
    DESCRIPTION
        "SCCP SSN measurement objects."
    ::= { ciscoGsccpMIBGroups 23 }

ciscoGsccpGttSsnClassGroup OBJECT-GROUP
    OBJECTS         {
                        cgsccpSSNClassUDTMsgsSent,
                        cgsccpSSNClassUDTMsgsRcvd,
                        cgsccpSSNClassXUDTMsgsSent,
                        cgsccpSSNClassXUDTMsgsRcvd,
                        cgsccpSSNClassLUDTMsgsSent,
                        cgsccpSSNClassLUDTMsgsRcvd
                    }
    STATUS          current
    DESCRIPTION
        "SCCP SSN Class measurement objects."
    ::= { ciscoGsccpMIBGroups 24 }

ciscoGsccpNotificationsInfoGroup OBJECT-GROUP
    OBJECTS         {
                        cgsccpLocalDisplaySS,
                        cgsccpLocalSsStatus
                    }
    STATUS          current
    DESCRIPTION
        "SCCP notification information objects."
    ::= { ciscoGsccpMIBGroups 25 }

ciscoGsccpNotificationsGroupSup2 NOTIFICATION-GROUP
   NOTIFICATIONS    {
                        ciscoGsccpSegReassUnsup,
                        ciscoGsccpSOGReceived,
                        ciscoGsccpRmtCongestion,
                        ciscoGsccpLocalSsStateChange
                    }
    STATUS          current
    DESCRIPTION
        "SCCP additional notification objects."
    ::= { ciscoGsccpMIBGroups 26 }

ciscoGsccpGttSelGroupSup1 OBJECT-GROUP
    OBJECTS         {
                        cgsccpGttNextSelName,
                        cgsccpGttNextSelRefed
                    }
    STATUS          current
    DESCRIPTION
        "SCCP GTT selector table additional objects."
    ::= { ciscoGsccpMIBGroups 27 }

END
