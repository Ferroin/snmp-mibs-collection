CISCO-DDP-IAPP-MIB DEFINITIONS ::= BEGIN

IMPORTS
        MODULE-IDENTITY,
        NOTIFICATION-TYPE,
        OBJECT-TYPE
                FROM SNMPv2-SMI
        MODULE-COMPLIANCE,
        NOTIFICATION-GROUP,
        OBJECT-GROUP
                FROM SNMPv2-CONF
        MacAddress,
        TruthValue
                FROM SNMPv2-TC
        InetAddressType,
        InetAddress
                FROM INET-ADDRESS-MIB
        CiscoPort
                FROM CISCO-TC
        ciscoMgmt
                FROM CISCO-SMI;

ciscoDdpIappMIB MODULE-IDENTITY
        LAST-UPDATED    "200207310000Z"
        ORGANIZATION    "Cisco System Inc."
        CONTACT-INFO
                "       Cisco Systems
                        Customer Service

                Postal: 170 West Tasman Drive,
                        San Jose CA 95134-1706.
                        USA

                   Tel: +1 800 553-NETS

                E-mail: cs-dot11@cisco.com"
        DESCRIPTION
                "This MIB module describes the management support for
                the Inter-Access Point Protocol (IAPP).  IAPP is a 
                Cisco propriety Data Delivery Protocol (DDP), and the
                protocol defines the function and frame formats for 
                communication between IEEE 802.11 Standard wireless 
                LAN stations, i.e. access point (AP), work-group 
                bridge, and repeater.  The IAPP supports wireless 
                station LAN attachment, client roaming, association
                management, and diagnostic services."  
        REVISION        "200207310000Z"
        DESCRIPTION
                "Correct DEFVAL for cDdpIappMcastIpAddr." 
        REVISION        "200207170000Z"
        DESCRIPTION
                "Removed cDdpIappP802dot1XVersion, added
                cDdpIappLastRogueApMacAddr, cDdpIappLastRogueApNotif,
                and cDdpIappRogueApNotifEnabled objects. Changed
                cDdpIappPort object to read-only access."
        REVISION        "200203190000Z"
        DESCRIPTION
                "Changing the description for cDdpIappPort to be a
                UDP port and Email contact address."
        REVISION        "200203070000Z"
        DESCRIPTION
                "Changing DEFVALs for cDdpIappMcastIpAddr and 
                cDdpIappPort."
        REVISION        "200109280000Z"
        DESCRIPTION
                "Initial version of this MIB module."
        ::= { ciscoMgmt 277 }

ciscoDdpIappMIBNotifications  OBJECT IDENTIFIER
        ::= { ciscoDdpIappMIB 0 }

ciscoDdpIappMIBObjects        OBJECT IDENTIFIER 
        ::= { ciscoDdpIappMIB 1 }

ciscoDdpIappMIBConformance    OBJECT IDENTIFIER 
        ::= { ciscoDdpIappMIB 2 }

cDdpIappGlobalConfig OBJECT IDENTIFIER ::= { ciscoDdpIappMIBObjects 1 }

cDdpIappRogueApInfo  OBJECT IDENTIFIER ::= { ciscoDdpIappMIBObjects 2 }

cDdpIappMcastIpAddrType OBJECT-TYPE
        SYNTAX InetAddressType
        MAX-ACCESS read-write
        STATUS current
        DESCRIPTION
                "Represents the type of address stored in
                cDdpIappMcastIpAddr."
        ::= { cDdpIappGlobalConfig 1 }

cDdpIappMcastIpAddr OBJECT-TYPE
        SYNTAX InetAddress
        MAX-ACCESS read-write
        STATUS current
        DESCRIPTION 
                "Multicast IP network address over which applicable 
                 IAPP packets are exchanged between stations." 
        DEFVAL { 'e0000128'H }          -- 224.0.1.40 
        ::= { cDdpIappGlobalConfig 2 }

cDdpIappPort OBJECT-TYPE
        SYNTAX CiscoPort
        MAX-ACCESS read-only
        STATUS current
        DESCRIPTION 
                "UPD port identifier through which applicable IAPP
                 packets are exchanged between stations."
        DEFVAL { 2887 } 
        ::= { cDdpIappGlobalConfig 3 }

cDdpIappRogueApNotifEnabled OBJECT-TYPE
        SYNTAX     TruthValue
        MAX-ACCESS read-write
        STATUS     current
        DESCRIPTION
                "Indicates whether rogue access point notifications
                including cDdpIappLastRogueApNotif notification 
                will or will not be sent by the agent when a rogue
                access point is detected.  If it is true(1), 
                notifications will be sent.  If it is false(2), 
                notifications will not be sent."
        DEFVAL     { false }
        ::= { cDdpIappGlobalConfig 4 }

cDdpIappLastRogueApMacAddr OBJECT-TYPE
        SYNTAX MacAddress
        MAX-ACCESS read-only
        STATUS current
        DESCRIPTION
                "This is the MAC address of the last detected rogue
                access point for this device.  The value is zero if 
                there has not been any rogue access point detected 
                since system reload."
        DEFVAL     { '000000000000'h }
        ::= { cDdpIappRogueApInfo 1 }

-- *****************************************************************
-- Notifications
-- *****************************************************************

cDdpIappLastRogueApNotif NOTIFICATION-TYPE
        OBJECTS {
                cDdpIappLastRogueApMacAddr }
        STATUS     current
        DESCRIPTION
                "This notification will be sent when a rogue 
                access point is detected, that is the object value
                of cDdpIappLastRogueApMacAddr had changed. The 
                cDdpIappLastRogueApMacAddr specify the latest 
                rogue access point MAC address.  The sending
                of notifications can be enabled or disabled
                via the cDdpIappRogueApNotifEnabled object."
        ::= { ciscoDdpIappMIBNotifications 1 }

-- *****************************************************************
--   Conformance information
-- *****************************************************************

ciscoDdpIappMIBCompliances
              OBJECT IDENTIFIER ::= { ciscoDdpIappMIBConformance 1 }
ciscoDdpIappMIBGroups
              OBJECT IDENTIFIER ::= { ciscoDdpIappMIBConformance 2 }

-- *****************************************************************
--   Compliance statements
-- *****************************************************************

ciscoDdpIappCompliance MODULE-COMPLIANCE
        STATUS  current
        DESCRIPTION
                "The compliance statement for entities implementing
                the CISCO-DDP-IAPP-MIB."
        MODULE  
                MANDATORY-GROUPS {
                        ciscoDdpIappConfigGroup,
                        ciscoDdpIappRogueApInfoGroup
                }

        GROUP ciscoDdpIappNotificationGroup
        DESCRIPTION
                "This group is mandatory if notification is
                supported on devices implementing IAPP."

        OBJECT  cDdpIappMcastIpAddrType
        SYNTAX  InetAddressType 
        DESCRIPTION
                "An implementation is only required to
                support IPv4 addresses."

        OBJECT  cDdpIappMcastIpAddr
        SYNTAX  InetAddress (SIZE(4))
        DESCRIPTION
                "An implementation is only required to
                 support IPv4 addresses."
        ::= { ciscoDdpIappMIBCompliances 1 }

-- *****************************************************************
--   Units of conformance
-- *****************************************************************

ciscoDdpIappConfigGroup OBJECT-GROUP
        OBJECTS {
                cDdpIappMcastIpAddrType,
                cDdpIappMcastIpAddr,
                cDdpIappPort,
                cDdpIappRogueApNotifEnabled 
        }
        STATUS  current
        DESCRIPTION
                "Configurations to support operation of the IAPP 
                protocols and subsystem."
        ::= { ciscoDdpIappMIBGroups 1 }

ciscoDdpIappRogueApInfoGroup OBJECT-GROUP
        OBJECTS {
                cDdpIappLastRogueApMacAddr
        }
        STATUS  current
        DESCRIPTION
                "Rogue AP information from the operation of the 
                IAPP subsystem."
        ::= { ciscoDdpIappMIBGroups 2 }

ciscoDdpIappNotificationGroup NOTIFICATION-GROUP
        NOTIFICATIONS {
                cDdpIappLastRogueApNotif } 
        STATUS     current
        DESCRIPTION
                "This is the notification group for the
                CISCO-DDP-IAPP-MIB."
        ::= { ciscoDdpIappMIBGroups 3 }

END
