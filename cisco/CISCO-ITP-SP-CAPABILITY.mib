CISCO-ITP-SP-CAPABILITY DEFINITIONS ::= BEGIN

IMPORTS
        MODULE-IDENTITY
                FROM SNMPv2-SMI

        AGENT-CAPABILITIES
                FROM SNMPv2-CONF

        ciscoAgentCapability
                FROM CISCO-SMI; 

ciscoItpSpCapability MODULE-IDENTITY
                LAST-UPDATED    "200201210000Z"
                ORGANIZATION    "Cisco Systems, Inc."
                CONTACT-INFO
                        "       Cisco Systems
                                Customer Service

                        Postal: 170 West Tasman Drive
                                San Jose, CA  95134
                                USA

                           Tel: +1 800 553-NETS

                        E-mail: cs-ss7@cisco.com"
                DESCRIPTION
                        "Agent capabilities for the CISCO-ITP-SP-MIB."

                REVISION        "200201210000Z"
                DESCRIPTION
                        "Updated capabilities MIB as required for 
                         new group.

                         cItpSpStatsGroup"

                REVISION        "200110240000Z"
                DESCRIPTION
                        "Initial version of this MIB module."
        ::= { ciscoAgentCapability 217 }

ciscoItpSpCapabilityV12R024MB1 AGENT-CAPABILITIES

    PRODUCT-RELEASE "Cisco IOS 12.2(4)MB1"
    STATUS           current
    DESCRIPTION     "IOS 12.2(4)MB1 Cisco CISCO-ITP-SP-MIB.my User Agent
                     MIB capabilities."

    SUPPORTS        CISCO-ITP-SP-MIB
        INCLUDES    { 
                      cItpSpScalarsGroup, 
                      cItpSpPointCodeGroup,
                      cItpSpLinksetGroup,           
                      cItpSpLinkGroup,              
                      cItpSpNotificationsEnableGroup,
                      cItpSpNotificationsGroup
                    }  

        -- Entries not supported in cItpSpLinkTable ----
        VARIATION     cItpSpLinkQ752T1E3
            ACCESS       not-implemented
            DESCRIPTION "Not implemented."

        VARIATION     cItpSpLinkQ752T1E4
            ACCESS       not-implemented
            DESCRIPTION "Not implemented."

        VARIATION     cItpSpLinkQ752T1E5
            ACCESS       not-implemented
            DESCRIPTION "Not implemented."

        VARIATION     cItpSpLinkQ752T1E6
            ACCESS       not-implemented
            DESCRIPTION "Not implemented."

        VARIATION     cItpSpLinkQ752T1E8
            ACCESS       not-implemented
            DESCRIPTION "Not implemented."

        VARIATION     cItpSpLinkQ752T1E10
            ACCESS       not-implemented
            DESCRIPTION "Not implemented."

        VARIATION     cItpSpLinkQ752T1E11
            ACCESS       not-implemented
            DESCRIPTION "Not implemented."

        VARIATION     cItpSpLinkQ752T2E7
            ACCESS       not-implemented
            DESCRIPTION "Not implemented."

        VARIATION     cItpSpLinkQ752T2E9
            ACCESS       not-implemented
            DESCRIPTION "Not implemented."

        VARIATION     cItpSpLinkQ752T2E10
            ACCESS       not-implemented
            DESCRIPTION "Not implemented."

        VARIATION     cItpSpLinkQ752T2E15
            ACCESS       not-implemented
            DESCRIPTION "Not implemented."

        VARIATION     cItpSpLinksetActPriority
            ACCESS       not-implemented
            DESCRIPTION "Not implemented."

        VARIATION     cItpSpLinksetType
            ACCESS       not-implemented
            DESCRIPTION "Not implemented."
    ::= { ciscoItpSpCapability 1 }

ciscoItpSpCapabilityV12R0204MB3 AGENT-CAPABILITIES

    PRODUCT-RELEASE "Cisco IOS 12.2(4)MB3"
    STATUS          current
    DESCRIPTION     "IOS 12.2(4)MB3 Cisco CISCO-ITP-SP-MIB.my User 
                     Agent MIB capabilities."

    SUPPORTS        CISCO-ITP-SP-MIB
        INCLUDES    { 
                      cItpSpScalarsGroup, 
                      cItpSpPointCodeGroup,
                      cItpSpLinksetGroup,           
                      cItpSpLinkGroup,              
                      cItpSpNotificationsEnableGroup,
                      cItpSpNotificationsGroup,
                      cItpSpStatsGroup
                    }  

        -- Entries not supported in cItpSpLinkTable ----
        VARIATION     cItpSpLinkQ752T1E3
            ACCESS       not-implemented
            DESCRIPTION "Not implemented."

        VARIATION     cItpSpLinkQ752T1E4
            ACCESS       not-implemented
            DESCRIPTION "Not implemented."

        VARIATION     cItpSpLinkQ752T1E5
            ACCESS       not-implemented
            DESCRIPTION "Not implemented."

        VARIATION     cItpSpLinkQ752T1E6
            ACCESS       not-implemented
            DESCRIPTION "Not implemented."

        VARIATION     cItpSpLinkQ752T1E8
            ACCESS       not-implemented
            DESCRIPTION "Not implemented."

        VARIATION     cItpSpLinkQ752T1E10
            ACCESS       not-implemented
            DESCRIPTION "Not implemented."

        VARIATION     cItpSpLinkQ752T1E11
            ACCESS       not-implemented
            DESCRIPTION "Not implemented."

        VARIATION     cItpSpLinkQ752T2E7
            ACCESS       not-implemented
            DESCRIPTION "Not implemented."

        VARIATION     cItpSpLinkQ752T2E9
            ACCESS       not-implemented
            DESCRIPTION "Not implemented."

        VARIATION     cItpSpLinkQ752T2E10
            ACCESS       not-implemented
            DESCRIPTION "Not implemented."

        VARIATION     cItpSpLinkQ752T2E15
            ACCESS       not-implemented
            DESCRIPTION "Not implemented."

        VARIATION     cItpSpLinksetActPriority
            ACCESS       not-implemented
            DESCRIPTION "Not implemented."

        VARIATION     cItpSpLinksetType
            ACCESS       not-implemented
            DESCRIPTION "Not implemented."
    ::= { ciscoItpSpCapability 2 }

END
