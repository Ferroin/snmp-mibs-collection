CISCO-IP-UPLINK-REDIRECT-MIB DEFINITIONS ::= BEGIN

IMPORTS
        MODULE-IDENTITY,
        OBJECT-TYPE
                FROM SNMPv2-SMI
        MODULE-COMPLIANCE,
        OBJECT-GROUP
                FROM SNMPv2-CONF
        TruthValue
                FROM SNMPv2-TC
        ciscoMgmt
                FROM CISCO-SMI;

ciscoIpUplinkRedirectMIB MODULE-IDENTITY
        LAST-UPDATED    "200101220000Z"
        ORGANIZATION    "Cisco Systems, Inc."
        CONTACT-INFO
                "       Cisco Systems
                        Customer Service

                Postal: 170 W Tasman Drive
                        San Jose, CA  95134
                        USA

                   Tel: +1 800 553-NETS

                E-mail: cs-cat2948g-l3@cisco.com"
        DESCRIPTION
                "This MIB module is for the configuration of  
                Cisco IP Uplink Redirect feature."
        REVISION        "200101220000Z"
        DESCRIPTION
                "Initial version of this MIB module."
        ::= { ciscoMgmt 191 }

ciscoIpUplinkRedirectMIBObjects OBJECT IDENTIFIER 
        ::= { ciscoIpUplinkRedirectMIB 1 }

-- IP Uplink Redirect Status

ciurStartupStatus OBJECT-TYPE
        SYNTAX          TruthValue
        MAX-ACCESS      read-write
        STATUS          current
        DESCRIPTION
                "The indication of whether IP Uplink Redirect
                feature will be enabled or disabled on this
                entity after reboot.

                IP uplink redirect enables traffic between
                Fast Ethernet interfaces to be switched through
                the Gigabit Ethernet interface. Then ACLs applied
                on the Gigabit Ethernet interface filter traffic
                switched between Fast Ethernet interfaces.

                Once the IP Uplink Redirect feature is enabled
                and saved, the switch has to be rebooted for 
                it to take effect."
        ::= { ciscoIpUplinkRedirectMIBObjects 1 }

ciurOperStatus OBJECT-TYPE
        SYNTAX          TruthValue
        MAX-ACCESS      read-only
        STATUS          current
        DESCRIPTION
                "Indicates whether or not IP Uplink Redirect
                is currently operational on this entity."
        ::= { ciscoIpUplinkRedirectMIBObjects 2 }

-- Notifications

ciscoIpUplinkRedirectMIBNotificationPrefix OBJECT IDENTIFIER 
        ::= { ciscoIpUplinkRedirectMIB 2 }

-- (no notifications are currently defined)

-- Conformance

ciscoIpUplinkRedirectMIBConformance OBJECT IDENTIFIER 
        ::= { ciscoIpUplinkRedirectMIB 3 }
ciscoIpUplinkRedirectMIBCompliances OBJECT IDENTIFIER 
        ::= { ciscoIpUplinkRedirectMIBConformance 1 }
ciscoIpUplinkRedirectMIBGroups      OBJECT IDENTIFIER 
        ::= { ciscoIpUplinkRedirectMIBConformance 2 }

-- Compliance statement

ciscoIpUplinkRedirectMIBCompliance MODULE-COMPLIANCE
        STATUS  current
        DESCRIPTION
                "The compliance statement for the Cisco 
                L3 Switch/Router IP Uplink Redirect group."
        MODULE  -- this module
                MANDATORY-GROUPS { ciscoIpUplinkRedirectMIBGroup }
        OBJECT          ciurStartupStatus 
        MIN-ACCESS      read-only 
        DESCRIPTION 
                "If the device doesn't support the ability to 
                enable/disable IP Uplink Redirection feature, 
                the object is only required to be read-only." 
        ::= { ciscoIpUplinkRedirectMIBCompliances 1 }

-- Units of conformance

ciscoIpUplinkRedirectMIBGroup OBJECT-GROUP
        OBJECTS {
                ciurStartupStatus,
                ciurOperStatus
        }
        STATUS  current
        DESCRIPTION
                "The Object Group for IP Uplink Redirect"
        ::= { ciscoIpUplinkRedirectMIBGroups 1 }

END
