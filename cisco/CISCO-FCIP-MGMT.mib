CISCO-FCIP-MGMT-MIB DEFINITIONS ::= BEGIN

IMPORTS
     OBJECT-TYPE,
     MODULE-IDENTITY,
     Unsigned32,
     Counter64,
     Integer32                  FROM SNMPv2-SMI
     TEXTUAL-CONVENTION,
     TruthValue,
     RowStatus                  FROM SNMPv2-TC
     InetAddressType,
     InetAddress                FROM INET-ADDRESS-MIB
     DomainId, FcNameIdOrZero,
     FcNameId                   FROM CISCO-ST-TC
     MODULE-COMPLIANCE,
     OBJECT-GROUP               FROM SNMPv2-CONF
     ciscoExperiment            FROM CISCO-SMI;

 ciscoFcipMgmtMIB MODULE-IDENTITY
     LAST-UPDATED "200305190000Z"
     ORGANIZATION "Cisco Systems Inc."
     CONTACT-INFO 
                "     Cisco Systems
                      Customer Service
                Postal: 170 W Tasman Drive
                      San Jose, CA  95134
                      USA
                Tel: +1 800 553 -NETS
                E-mail: cs-san@cisco.com"
     DESCRIPTION 
         "The Fibre Channel Over TCP/IP management MIB module.
          This mib module is the Cisco version of the FCIP MIB draft
          , draft-ietf-ips-fcip-mib-02.txt, from the IETF. "
     REVISION    "200305190000Z"
     DESCRIPTION
         "Changed the MAX-ACCESS of cfmFcipStaRtRemFcipEntWWN from
         read-create to read-write."
     REVISION    "200210050000Z"
     DESCRIPTION
         "Initial version of this MIB module."
     ::= { ciscoExperiment 96 } 

 ciscoFcipObjects       OBJECT IDENTIFIER ::= { ciscoFcipMgmtMIB 1 }
 cfmFcipConformance     OBJECT IDENTIFIER ::= { ciscoFcipMgmtMIB 2 }

 cfmFcipConfig          OBJECT IDENTIFIER ::= { ciscoFcipObjects 1 }
 cfmFcipNotification    OBJECT IDENTIFIER ::= { ciscoFcipObjects 2 }
 cfmFcipNotifications   OBJECT IDENTIFIER ::= { cfmFcipNotification 0 }

 CfmFcEntityMode ::= TEXTUAL-CONVENTION
     STATUS current
     DESCRIPTION    
         "The type of port mode provided by an FCIP Entity
          for a FCIP Link. An FCIP Entity can be an E-Port
          mode for one of its FCIP Link Endpoints, an B-Port
          mode for another of its FCIP Link Endpoints.
          ePortMode(1) - entity mode is e_port.
          bPortMode(2) - entity mode is b_port.
          other(3) -  entity mode is some other port."
     SYNTAX INTEGER {
 		ePortMode(1),
                bPortMode(2),
                other(3)
     }

 -- 
 -- The FCIP group
 --
 -- This group defines the global scalar objects applicable to FCIP
 -- devices only
 --

 cfmFcipDynIpConfType  OBJECT-TYPE
     SYNTAX     INTEGER {
 		      slpv2(1),
 		      none(2)
     }
     MAX-ACCESS read-write
     STATUS     current
     DESCRIPTION
 	   "The type of discovery protocol used to discover remote
 	    FCIP entities.
          slpv2(1) - Service Location Protocol.
          none(2)  - nothing is used. "
     ::= { cfmFcipConfig 1 }

 cfmFcipFabricWWN   OBJECT-TYPE
     SYNTAX     FcNameIdOrZero
     MAX-ACCESS read-only
     STATUS     current
     DESCRIPTION
         "The World Wide Name of this FCIP device. The zero-length
          string value is used in circumstances where the WWN is
          unassigned/unknown. "
     ::= { cfmFcipConfig 2 }

 -- 
 -- cfmFcipEntityInstanceTable
 --

 cfmFcipEntityInstanceTable OBJECT-TYPE
     SYNTAX     SEQUENCE OF CfmFcipEntityInstanceEntry
     MAX-ACCESS not-accessible
     STATUS     current
     DESCRIPTION
 	   "A table containing FCIP entity specific information. "
     ::= { cfmFcipConfig 3 }

 cfmFcipEntityInstanceEntry OBJECT-TYPE
     SYNTAX     CfmFcipEntityInstanceEntry
     MAX-ACCESS not-accessible
     STATUS     current
     DESCRIPTION
 	   "A conceptual row of the FCIP entity table containing 
          information about a particular FCIP entity. "
     INDEX { cfmFcipEntityId }
     ::= { cfmFcipEntityInstanceTable 1 }

 CfmFcipEntityInstanceEntry ::=
     SEQUENCE {
 		cfmFcipEntityId                  Unsigned32,
 		cfmFcipEntityAddressType         InetAddressType,
 		cfmFcipEntityAddress             InetAddress,
 		cfmFcipEntityTcpConnPort         Unsigned32,
 		cfmFcipEntitySACKOption          INTEGER,
 		cfmFcipEntitySeqNumWrap          TruthValue,
 		cfmFcipEntityPHBSupport          TruthValue,
 		cfmFcipEntityStatus              RowStatus
 }

 cfmFcipEntityId   OBJECT-TYPE
     SYNTAX     Unsigned32
     MAX-ACCESS not-accessible
     STATUS     current
     DESCRIPTION
         "The FCIP entity identifier. "
     ::= { cfmFcipEntityInstanceEntry 1 }

 cfmFcipEntityAddressType   OBJECT-TYPE
     SYNTAX     InetAddressType
     MAX-ACCESS read-create
     STATUS     current
     DESCRIPTION
         "The type of Internet address by which the entity is
          reachable. "
     ::= { cfmFcipEntityInstanceEntry 2 }

 cfmFcipEntityAddress   OBJECT-TYPE
     SYNTAX     InetAddress
     MAX-ACCESS read-create
     STATUS     current
     DESCRIPTION
         "The Internet address for this entity. "
     ::= { cfmFcipEntityInstanceEntry 3 }

 cfmFcipEntityTcpConnPort   OBJECT-TYPE
     SYNTAX     Unsigned32 (0..65535)
     MAX-ACCESS read-create
     STATUS     current
     DESCRIPTION
         "A TCP port other than the FCIP Well-Known port on which the 
          FCIP entity listens for new TCP connection requests. It
          contains the value zero (0) if the FCIP Entity only listens on
          the Well-Known port. "
     ::= { cfmFcipEntityInstanceEntry 4 }

 cfmFcipEntitySACKOption   OBJECT-TYPE
     SYNTAX INTEGER {
 		enabled(1),
 		disabled(2)
     }
     MAX-ACCESS read-create
     STATUS     current
     DESCRIPTION
         "An indication of whether the TCP Selective Acknowledgement 
          Option is enabled to allow the receiver end to acknowledge 
          multiple lost packets in a singel ACK, enabling faster
          recovery.
          enabled(1) - acknowledge option is enabled.
          disabled(2) - acknowledge option is disabled. "
     ::= { cfmFcipEntityInstanceEntry 5 }

 cfmFcipEntitySeqNumWrap   OBJECT-TYPE
     SYNTAX     TruthValue
     MAX-ACCESS read-only
     STATUS     current
     DESCRIPTION
 	   "An indication of whether the FCIP Entity supports the
          protection against sequence number wrap. 
          If true(1), the FCIP Entity supports protection against
          sequence number wrap. If false(2), the FCIP Entity does not
          support protection against sequence number wrap. "
     ::= { cfmFcipEntityInstanceEntry 6 }

 cfmFcipEntityPHBSupport   OBJECT-TYPE
     SYNTAX     TruthValue
     MAX-ACCESS read-only
     STATUS     current
     DESCRIPTION
 	   "An indication of whether the FCIP Entity supports PHB IP
          QoS. "
     ::= { cfmFcipEntityInstanceEntry 7 }

 cfmFcipEntityStatus   OBJECT-TYPE
     SYNTAX     RowStatus
     MAX-ACCESS read-create
     STATUS     current
     DESCRIPTION
         "The status of this conceptual row. "
     ::= { cfmFcipEntityInstanceEntry 8 }

 -- 
 -- cfmFcipLinkTable
 --

 cfmFcipLinkTable OBJECT-TYPE
     SYNTAX     SEQUENCE OF CfmFcipLinkEntry
     MAX-ACCESS not-accessible
     STATUS     current
     DESCRIPTION
 	   "A table containing FCIP link specific information. "
     ::= { cfmFcipConfig 4 }

 cfmFcipLinkEntry OBJECT-TYPE
     SYNTAX     CfmFcipLinkEntry
     MAX-ACCESS not-accessible
     STATUS     current
     DESCRIPTION
 	   "A conceptual row of the FCIP link table containing
          information about a particular FCIP link. "
     INDEX { cfmFcipEntityId, cfmFcipLinkIndex }
     ::= { cfmFcipLinkTable 1 }

 CfmFcipLinkEntry ::=
     SEQUENCE {
 		cfmFcipLinkIndex                       Unsigned32,
 		cfmFcipLinkIfIndex                     Integer32,
 		cfmFcipLinkCost                        Unsigned32,
 		cfmFcipLinkLocalFcipEntityMode         CfmFcEntityMode,
 		cfmFcipLinkRemFcipEntityWWN            FcNameIdOrZero,
 		cfmFcipLinkRemFcipEntityId             Unsigned32,
 		cfmFcipLinkRemFcipEntityAddrType       InetAddressType,
 		cfmFcipLinkRemFcipEntityAddress        InetAddress,
 		cfmFcipLinkRemFcipEntityMode           CfmFcEntityMode,
 		cfmFcipLinkStatus                      RowStatus
     }

 cfmFcipLinkIndex     OBJECT-TYPE
     SYNTAX     Unsigned32
     MAX-ACCESS not-accessible
     STATUS     current
     DESCRIPTION
         "An arbitrary integer which uniquely identifies one FCIP link
          within a FCIP entity. "
     ::= { cfmFcipLinkEntry 1 }

 cfmFcipLinkIfIndex     OBJECT-TYPE
     SYNTAX     Integer32 (1..2147483647)
     MAX-ACCESS read-only
     STATUS     current
     DESCRIPTION
 	   "A unique value that identifies the interface on this FCIP
          device to which this link pertains. The interface identified
          by a particular value of this object is the same interface as 
          identified by the same value of the ifIndex object, defined 
          in IF-MIB. "
     ::= { cfmFcipLinkEntry 2 }

 cfmFcipLinkCost     OBJECT-TYPE
     SYNTAX     Unsigned32 (0..65535)
     MAX-ACCESS read-create
     STATUS     current
     DESCRIPTION
         "The cost associated with this FCIP Link. The link cost is 
          used to select lowest cost route. "
     REFERENCE
          "FC-SW-2 REV 5.3 Section 8.5.5"
     ::= { cfmFcipLinkEntry 3 }

 cfmFcipLinkLocalFcipEntityMode   OBJECT-TYPE
     SYNTAX     CfmFcEntityMode
     MAX-ACCESS read-only
     STATUS     current
     DESCRIPTION
         "The mode of the local FCIP Entity to which this FCIP Link
          pertains. "
     ::= { cfmFcipLinkEntry 4 }

 cfmFcipLinkRemFcipEntityWWN   OBJECT-TYPE
     SYNTAX     FcNameIdOrZero
     MAX-ACCESS read-create
     STATUS     current
     DESCRIPTION
         "The World Wide Name of the remote FC Fabric Entity. If this
          is a zero length string then this link would accept 
          connections from any remote entity. If a WWN is specified
          then this link would accept connections from a remote entity
          with this WWN. "
     ::= { cfmFcipLinkEntry 5 }

 cfmFcipLinkRemFcipEntityId   OBJECT-TYPE
     SYNTAX     Unsigned32 (0..4294967295)
     MAX-ACCESS read-create
     STATUS     current
     DESCRIPTION
         "The remote FCIP entity's identifier. "
     ::= { cfmFcipLinkEntry 6 }

 cfmFcipLinkRemFcipEntityAddrType   OBJECT-TYPE
     SYNTAX     InetAddressType
     MAX-ACCESS read-create
     STATUS     current
     DESCRIPTION
         "The type of Internet address by which the remote FCIP entity
          is reachable. "
     ::= { cfmFcipLinkEntry 7 }

 cfmFcipLinkRemFcipEntityAddress   OBJECT-TYPE
     SYNTAX     InetAddress
     MAX-ACCESS read-create
     STATUS     current
     DESCRIPTION
         "The Internet address for the remote FCIP entity. "
     ::= { cfmFcipLinkEntry 8 }

 cfmFcipLinkRemFcipEntityMode   OBJECT-TYPE
     SYNTAX     CfmFcEntityMode
     MAX-ACCESS read-only
     STATUS     current
     DESCRIPTION
         "The mode of the remote FCIP Entity to which this FCIP Link
          pertains. "
     ::= { cfmFcipLinkEntry 9 }

 cfmFcipLinkStatus   OBJECT-TYPE
     SYNTAX     RowStatus
     MAX-ACCESS read-create
     STATUS     current
     DESCRIPTION
         "The status of this conceptual row. "
     ::= { cfmFcipLinkEntry 10 }

 -- 
 -- cfmFcipTcpConnTable
 --

 cfmFcipTcpConnTable OBJECT-TYPE
     SYNTAX     SEQUENCE OF CfmFcipTcpConnEntry
     MAX-ACCESS not-accessible
     STATUS     current
     DESCRIPTION
         "A table containing FCIP specific information about this FCIP
          device's existing TCP connections. The FCIP TCP Connection 
          table contains information about existing TCP connections. 
          Each FCIP link within a FCIP entity manages one or more TCP
          connections. The FCIP entity employs a Data Engine for each
          TCP connection for handling FC frame encapsulation,
          de-encapsulation and transmission of FCIP frames on the 
          connection. "
     ::= { cfmFcipConfig 5 }

 cfmFcipTcpConnEntry OBJECT-TYPE
     SYNTAX     CfmFcipTcpConnEntry
     MAX-ACCESS not-accessible
     STATUS     current
     DESCRIPTION
 	   "A conceptual row of the FCIP TCP Connection table containing
          information about a particular TCP connection. "
     INDEX { cfmFcipEntityId, 
 		 cfmFcipLinkIndex,
 		 cfmFcipTcpConnLocalPort,
             cfmFcipTcpConnRemPort }
     ::= { cfmFcipTcpConnTable 1 }

 CfmFcipTcpConnEntry ::=
     SEQUENCE {
 		cfmFcipTcpConnLocalPort      Integer32,
 		cfmFcipTcpConnRemPort        Integer32,
 		cfmFcipTcpConnPurpose        INTEGER,
 		cfmFcipTcpConnRWSize         Unsigned32,
 		cfmFcipTcpConnMSS            Unsigned32,
 		cfmFcipTcpConnTimeOut        Unsigned32
     }

 cfmFcipTcpConnLocalPort     OBJECT-TYPE
     SYNTAX Integer32 (0..65535)
     MAX-ACCESS not-accessible
     STATUS current
     DESCRIPTION
         "The local port number for this TCP connection. "
     ::= { cfmFcipTcpConnEntry 1 }

 cfmFcipTcpConnRemPort     OBJECT-TYPE
     SYNTAX     Integer32 (0..65535)
     MAX-ACCESS not-accessible
     STATUS     current
     DESCRIPTION
         "The remote port number for this TCP connection. "
     ::= { cfmFcipTcpConnEntry 2 }

 cfmFcipTcpConnPurpose    OBJECT-TYPE
     SYNTAX INTEGER {
 		control(1),
 		data(2),
 		both(3)
     }
     MAX-ACCESS read-only
     STATUS     current
     DESCRIPTION
         "The nature of messages that get transmitted on this TCP
          connection.
          control(1) - TCP connection is for control purpose.
          data(2)    - TCP connection is for data purpose.
          both(3)    - TCP connection is for control and data 
                       purpose. "
     ::= { cfmFcipTcpConnEntry 3 }

 cfmFcipTcpConnRWSize     OBJECT-TYPE
     SYNTAX     Unsigned32
     MAX-ACCESS read-only
     STATUS     current
     DESCRIPTION
         "The default maximum TCP Receiver Window size for this TCP
          connection. "
     ::= { cfmFcipTcpConnEntry 4 }

 cfmFcipTcpConnMSS     OBJECT-TYPE
     SYNTAX     Unsigned32
     MAX-ACCESS read-only
     STATUS     current
     DESCRIPTION
         "The TCP Maximum Segment Size (MSS) for this TCP connection. "
     ::= { cfmFcipTcpConnEntry 5 }

 cfmFcipTcpConnTimeOut    OBJECT-TYPE
     SYNTAX     Unsigned32
     UNITS      "seconds"
     MAX-ACCESS read-only
     STATUS     current
     DESCRIPTION
         "The timeout value for this TCP connection. "
     ::= { cfmFcipTcpConnEntry 6 }

 --
 -- cfmFcipDynamicRouteTable
 --

cfmFcipDynamicRouteTable OBJECT-TYPE
     SYNTAX SEQUENCE OF CfmFcipDynamicRouteEntry
     MAX-ACCESS not-accessible
     STATUS     current
     DESCRIPTION
         "A table containing FCIP Route specific information.
          The FCIP dynamic route table contains information about this 
          FCIP device's routing information that is dynamically 
          discovered. The FCIP device may use SLPv2 protocol in 
          conjunction with other protocols, say FSPF, for dynamically
          discovering other FCIP entities, and populate this table for
          Destination Address Identifier to connecting FCIP link
          information. "
     ::= { cfmFcipConfig 6 }

 cfmFcipDynamicRouteEntry OBJECT-TYPE
     SYNTAX     CfmFcipDynamicRouteEntry
     MAX-ACCESS not-accessible
     STATUS     current
     DESCRIPTION
         "A conceptual row of the FCIP Dynamic Route Table containing
          information about a particular FCIP route. "
     INDEX { cfmFcipEntityId, cfmFcipDynamicRouteDID,
             cfmFcipDynamicRouteIndex }
     ::= { cfmFcipDynamicRouteTable 1 }

 CfmFcipDynamicRouteEntry ::=
     SEQUENCE {
         cfmFcipDynamicRouteIndex        Unsigned32,
         cfmFcipDynamicRouteDID          DomainId,
         cfmFcipDynamicRouteLinkIndex    Unsigned32
     }

 cfmFcipDynamicRouteIndex    OBJECT-TYPE
     SYNTAX     Unsigned32
     MAX-ACCESS not-accessible
     STATUS     current
     DESCRIPTION
         "An index that uniquely identifies an entry in the FCIP dynamic
 	    Route table. "
     ::= { cfmFcipDynamicRouteEntry  1 }

 cfmFcipDynamicRouteDID    OBJECT-TYPE
     SYNTAX     DomainId
     MAX-ACCESS not-accessible
     STATUS     current 
     DESCRIPTION
         "The 8 bit ID of a Fibre Channel Domain that is reachable from
 	    this FCIP device. "
     ::= { cfmFcipDynamicRouteEntry  2 }

 cfmFcipDynamicRouteLinkIndex    OBJECT-TYPE
     SYNTAX     Unsigned32
     MAX-ACCESS read-only
     STATUS     current
     DESCRIPTION
         "The FCIP Link that is represented by this value in the FCIP 
          Link table used to reach this domain (specified by the 
          previous object 'cfmFcipDynamicRouteDID') on the remote FCIP
          device. "
     ::= { cfmFcipDynamicRouteEntry  3 }

 -- 
 -- cfmFcipStaticRouteTable
 --

 cfmFcipStaticRouteTable OBJECT-TYPE
     SYNTAX SEQUENCE OF CfmFcipStaticRouteEntry
     MAX-ACCESS not-accessible
     STATUS     current
     DESCRIPTION
         "A table containing FCIP Route specific information.
          The FCIP static route table contains information about this 
          FCIP device's routing information that is created by the
          Network Admin. In the absence of dynamic discovery of remote
          FCIP entities, the Network Manager will figure out all the 
          remote FCIP devices that are reachable from this device, and
          populate this table with FCIP link information for each 
          Domain Id. "
     ::= { cfmFcipConfig 7 }

 cfmFcipStaticRouteEntry OBJECT-TYPE
     SYNTAX CfmFcipStaticRouteEntry
     MAX-ACCESS not-accessible
     STATUS current
     DESCRIPTION
         "A conceptual row of the FCIP Static Route Table containing
          information about a particular FCIP route. "
     INDEX { cfmFcipEntityId, cfmFcipStaRtDID, cfmFcipStaRtIndex }
     ::= { cfmFcipStaticRouteTable 1 }

 CfmFcipStaticRouteEntry ::=
     SEQUENCE {
 		cfmFcipStaRtIndex                 Unsigned32,
 		cfmFcipStaRtDID                   DomainId, 
 		cfmFcipStaRtRemFcipEntWWN         FcNameId,
 		cfmFcipStaRtRemFcipEntId          Unsigned32,
 		cfmFcipStaRtRemFcipEntAddrType    InetAddressType,
 		cfmFcipStaRtRemFcipEntAddr        InetAddress,
 		cfmFcipStaRtStatus                RowStatus
     }

 cfmFcipStaRtIndex    OBJECT-TYPE
     SYNTAX Unsigned32
     MAX-ACCESS not-accessible
     STATUS current
     DESCRIPTION
         "An index that uniquely identifies an entry in the FCIP static
          Route table. "
     ::= { cfmFcipStaticRouteEntry  1 }

 cfmFcipStaRtDID    OBJECT-TYPE
     SYNTAX     DomainId
     MAX-ACCESS not-accessible
     STATUS     current
     DESCRIPTION
         "The 8 bit ID of a Fibre Channel Domain that is reachable from
 	    this FCIP device. "
     ::= { cfmFcipStaticRouteEntry  2 }

 cfmFcipStaRtRemFcipEntWWN   OBJECT-TYPE
     SYNTAX FcNameId
     MAX-ACCESS read-create
     STATUS current
     DESCRIPTION
         "The World Wide Name of the remote FC Entity to which this
          route applies. "
     ::= { cfmFcipStaticRouteEntry  3 }

 cfmFcipStaRtRemFcipEntId   OBJECT-TYPE
     SYNTAX     Unsigned32
     MAX-ACCESS read-create
     STATUS current
     DESCRIPTION
         "The identifier of the remote FCIP entity to which this route
          pertains. "
     ::= { cfmFcipStaticRouteEntry  4 }

 cfmFcipStaRtRemFcipEntAddrType   OBJECT-TYPE
     SYNTAX     InetAddressType
     MAX-ACCESS read-create
     STATUS current
     DESCRIPTION
         "The type of Internet address used by the remote FCIP entity
          to which this route pertains. "
     ::= { cfmFcipStaticRouteEntry 5 }

 cfmFcipStaRtRemFcipEntAddr   OBJECT-TYPE
     SYNTAX     InetAddress
     MAX-ACCESS read-create
     STATUS     current
     DESCRIPTION
         "The Internet address for the remote FCIP entity."
     ::= { cfmFcipStaticRouteEntry 6 }

 cfmFcipStaRtStatus   OBJECT-TYPE
     SYNTAX     RowStatus
     MAX-ACCESS read-create
     STATUS     current
     DESCRIPTION
         "The status of this conceptual row. "
     ::= { cfmFcipStaticRouteEntry  7 }

 -- 
 -- cfmFcipLinkErrorsTable
 --

 cfmFcipLinkErrorsTable OBJECT-TYPE
     SYNTAX SEQUENCE OF CfmFcipLinkErrorsEntry
     MAX-ACCESS not-accessible
     STATUS current
     DESCRIPTION
         "A table containing error counters for FCIP Links.
          The FCIP Link Errors Table contains counters that indicate the
          number of times each error case happened that caused closing
          down a TCP connection. "
     ::= { cfmFcipConfig 8 }

 cfmFcipLinkErrorsEntry OBJECT-TYPE
     SYNTAX     CfmFcipLinkErrorsEntry
     MAX-ACCESS not-accessible
     STATUS current
     DESCRIPTION
         "A conceptual row of the FCIP Link Errors Table containing
          error counters for a FCIP Link. "
     INDEX { cfmFcipEntityId, cfmFcipLinkIndex }
     ::= { cfmFcipLinkErrorsTable 1 }

 CfmFcipLinkErrorsEntry ::=
     SEQUENCE {
         cfmFcipLinkFcipLossofFcSynchs            Counter64,
         cfmFcipLinkFcipSfNotRcv                  Counter64,
         cfmFcipLinkFcipSfRespNotRcv              Counter64,
         cfmFcipLinkFcipSfRespMismatch            Counter64,
         cfmFcipLinkFcipSfInvalidNonce            Counter64,
         cfmFcipLinkFcipDuplicateSfRcv            Counter64,
         cfmFcipLinkFcipSfInvalidWWN              Counter64,
         cfmFcipLinkFcipBB2LkaTimeOut             Counter64,
         cfmFcipLinkFcipSntpTimeStampExp          Counter64,
         cfmFcipLinkTcpTooManyErrors              Counter64,
         cfmFcipLinkTcpKeepAliveTimeOut           Counter64,
         cfmFcipLinkTcpExDatagramsDropped         Counter64,
         cfmFcipLinkTcpSaParamMismatch            Counter64
     }

 cfmFcipLinkFcipLossofFcSynchs OBJECT-TYPE
     SYNTAX     Counter64
     MAX-ACCESS read-only
     STATUS     current
     DESCRIPTION
         "The number of times FC synchronization lost on this FCIP
          Link. "
     ::= { cfmFcipLinkErrorsEntry 1 }

 cfmFcipLinkFcipSfNotRcv OBJECT-TYPE
     SYNTAX     Counter64
     MAX-ACCESS read-only
     STATUS     current
     DESCRIPTION
         "The number of times FCIP Special Frame not received on
          this FCIP Link. "
     ::= { cfmFcipLinkErrorsEntry 2 }

 cfmFcipLinkFcipSfRespNotRcv OBJECT-TYPE
     SYNTAX     Counter64
     MAX-ACCESS read-only
     STATUS     current
     DESCRIPTION
         "The number of times FCIP Special Frame Response not 
          received on this FCIP Link. "
     ::= { cfmFcipLinkErrorsEntry 3 }

 cfmFcipLinkFcipSfRespMismatch OBJECT-TYPE
     SYNTAX     Counter64
     MAX-ACCESS read-only
     STATUS     current
     DESCRIPTION
         "The number of times FCIP Special Frame Bytes mismatch
          happened on this FCIP Link. "
     ::= { cfmFcipLinkErrorsEntry 4 }

 cfmFcipLinkFcipSfInvalidNonce OBJECT-TYPE
     SYNTAX     Counter64
     MAX-ACCESS read-only
     STATUS     current
     DESCRIPTION
         "The number of times FCIP Special Frame Invalid connections
          once happened on this FCIP Link. "
     ::= { cfmFcipLinkErrorsEntry 5 }

 cfmFcipLinkFcipDuplicateSfRcv OBJECT-TYPE
     SYNTAX     Counter64
     MAX-ACCESS read-only
     STATUS     current
     DESCRIPTION
         "The number of times duplicate FCIP Special Frames received
          on this FCIP Link. "
     ::= { cfmFcipLinkErrorsEntry 6 }

 cfmFcipLinkFcipSfInvalidWWN OBJECT-TYPE
     SYNTAX     Counter64
     MAX-ACCESS read-only
     STATUS     current
     DESCRIPTION
         "The number of times FCIP Special Frames with invalid
          destination FC Fabric Entity WWN received on this FCIP Link. "
     ::= { cfmFcipLinkErrorsEntry 7 }

 cfmFcipLinkFcipBB2LkaTimeOut OBJECT-TYPE
     SYNTAX     Counter64
     MAX-ACCESS read-only
     STATUS     current
     DESCRIPTION
         "The number of times B_Access Link Keep Alive Time out
          happened on this FCIP Link. "
     ::= { cfmFcipLinkErrorsEntry 8 }

 cfmFcipLinkFcipSntpTimeStampExp OBJECT-TYPE
     SYNTAX     Counter64
     MAX-ACCESS read-only
     STATUS     current
     DESCRIPTION
         "The number of times SNTP Time Stamp expired on this FCIP
          Link. "
     ::= { cfmFcipLinkErrorsEntry 9 }

 cfmFcipLinkTcpTooManyErrors OBJECT-TYPE
     SYNTAX     Counter64
     MAX-ACCESS read-only
     STATUS     current
     DESCRIPTION
         "The number of times TCP connections with too many errors
          closed down on this FCIP Link. "
     ::= { cfmFcipLinkErrorsEntry 10  }

 cfmFcipLinkTcpKeepAliveTimeOut OBJECT-TYPE
     SYNTAX     Counter64
     MAX-ACCESS read-only
     STATUS     current
     DESCRIPTION
         "The number of times TCP connections that experienced TCP
          Keep Alive Time outs closed down on this FCIP Link. "
     ::= { cfmFcipLinkErrorsEntry 11  }

 cfmFcipLinkTcpExDatagramsDropped OBJECT-TYPE
     SYNTAX     Counter64
     MAX-ACCESS read-only
     STATUS     current
     DESCRIPTION
         "The number of times TCP connections that dropped excessive
          number of datagrams closed down on this FCIP Link. "
     ::= { cfmFcipLinkErrorsEntry 12  }

 cfmFcipLinkTcpSaParamMismatch OBJECT-TYPE
     SYNTAX     Counter64
     MAX-ACCESS read-only
     STATUS     current
     DESCRIPTION
         "The number of times TCP connections with SA parameter
          mismatches closed down on this FCIP Link. "
     ::= { cfmFcipLinkErrorsEntry 13  }

 -- 
 -- Conformance 
 --
 cfmFcipCompliances     OBJECT IDENTIFIER ::= { cfmFcipConformance 1 }
 cfmFcipGroups          OBJECT IDENTIFIER ::= { cfmFcipConformance 2 }

 cfmFcipCompliance MODULE-COMPLIANCE
     STATUS current
     DESCRIPTION
         "Compliance statement for FCIP MIB. "
     MODULE       -- this module
     MANDATORY-GROUPS {
         cfmFcipEntityScalarGroup,
         cfmFcipEntityInstanceGroup,
         cfmFcipLinkGroup,
         cfmFcipTcpConnGroup,
         cfmFcipDynamicRouteGroup,
         cfmFcipStaticRouteGroup,
         cfmFcipLinkErrorsGroup
     }
 ::= { cfmFcipCompliances 1 }

-- Units of Conformance

cfmFcipEntityScalarGroup OBJECT-GROUP
     OBJECTS {
 		cfmFcipDynIpConfType,
 		cfmFcipFabricWWN
     }
     STATUS current
     DESCRIPTION
         "A collection of scalar objects applicable to all FCIP
          instances. " 
     ::= { cfmFcipGroups 1 }

cfmFcipEntityInstanceGroup OBJECT-GROUP
     OBJECTS {
 		cfmFcipEntityAddressType,
 		cfmFcipEntityAddress,
 		cfmFcipEntityTcpConnPort,
 		cfmFcipEntitySACKOption,
 		cfmFcipEntitySeqNumWrap,
 		cfmFcipEntityPHBSupport,
 		cfmFcipEntityStatus
     }
     STATUS current
     DESCRIPTION
         "A collection of objects providing information about FCIP
          instances. "
 ::= { cfmFcipGroups 2 }

 cfmFcipLinkGroup OBJECT-GROUP
     OBJECTS {
 		cfmFcipLinkIfIndex,
 		cfmFcipLinkCost,
 		cfmFcipLinkLocalFcipEntityMode,
 		cfmFcipLinkRemFcipEntityWWN,
 		cfmFcipLinkRemFcipEntityId,
 		cfmFcipLinkRemFcipEntityAddrType,
 		cfmFcipLinkRemFcipEntityAddress,
 		cfmFcipLinkRemFcipEntityMode,
 		cfmFcipLinkStatus
     }
     STATUS current
     DESCRIPTION
         "A collection of objects providing information about FCIP
          Links. "
 ::= { cfmFcipGroups 3 }

 cfmFcipTcpConnGroup OBJECT-GROUP
     OBJECTS {
 		cfmFcipTcpConnPurpose,
 		cfmFcipTcpConnRWSize,
 		cfmFcipTcpConnMSS, 
 		cfmFcipTcpConnTimeOut
     }
     STATUS current
     DESCRIPTION
         "A collection of objects providing information about FCIP TCP
          conections. "
 ::= { cfmFcipGroups 4 }

 cfmFcipDynamicRouteGroup OBJECT-GROUP
     OBJECTS {
            cfmFcipDynamicRouteLinkIndex
     }
     STATUS current
     DESCRIPTION
         "A collection of objects providing information about FCIP
          dynamic routes. "
 ::= { cfmFcipGroups 5 }

 cfmFcipStaticRouteGroup OBJECT-GROUP
     OBJECTS {
 		cfmFcipStaRtRemFcipEntWWN,
 		cfmFcipStaRtRemFcipEntId,
 		cfmFcipStaRtRemFcipEntAddrType,
 		cfmFcipStaRtRemFcipEntAddr,
 		cfmFcipStaRtStatus
     }
     STATUS current
     DESCRIPTION
         "A collection of objects providing information about FCIP
          static routes. "
 ::= { cfmFcipGroups 6 }

 cfmFcipLinkErrorsGroup OBJECT-GROUP
     OBJECTS {
            cfmFcipLinkFcipLossofFcSynchs,
            cfmFcipLinkFcipSfNotRcv,
            cfmFcipLinkFcipSfRespNotRcv,
            cfmFcipLinkFcipSfRespMismatch,
            cfmFcipLinkFcipSfInvalidNonce,
            cfmFcipLinkFcipDuplicateSfRcv,
            cfmFcipLinkFcipSfInvalidWWN,
            cfmFcipLinkFcipBB2LkaTimeOut,
            cfmFcipLinkFcipSntpTimeStampExp,
            cfmFcipLinkTcpTooManyErrors,
            cfmFcipLinkTcpKeepAliveTimeOut,
            cfmFcipLinkTcpExDatagramsDropped,
            cfmFcipLinkTcpSaParamMismatch
     }
     STATUS current
     DESCRIPTION
         "A collection of objects providing information about FCIP
          link errors. "
 ::= { cfmFcipGroups 7 }

 END
