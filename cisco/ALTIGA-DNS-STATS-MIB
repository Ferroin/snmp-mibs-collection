ALTIGA-DNS-STATS-MIB DEFINITIONS ::= BEGIN

   IMPORTS
	   MODULE-IDENTITY, OBJECT-TYPE, Gauge32
		   FROM SNMPv2-SMI
	   OBJECT-GROUP, MODULE-COMPLIANCE
		   FROM SNMPv2-CONF
	   alStatsDns, alDnsGroup
		   FROM ALTIGA-MIB
	   alDnsMibModule
		   FROM ALTIGA-GLOBAL-REG;

   altigaDnsStatsMibModule MODULE-IDENTITY
      LAST-UPDATED   "200209051300Z"
      ORGANIZATION   "Cisco Systems, Inc."
      CONTACT-INFO
         "Cisco Systems
          170 W Tasman Drive
          San Jose, CA  95134
          USA

          Tel: +1 800 553-NETS
          E-mail: cs-cvpn3000@cisco.com"
      DESCRIPTION
         "The Altiga DNS Statistics MIB models counters and objects that are
          of management interest for DNS.

          Acronyms
          The following acronyms are used in this document:

            DNS:        Domain Name Service

            MIB:        Management Information Base
         "

        REVISION "200209051300Z"
        DESCRIPTION
                "Added module compliance."

        REVISION "200207100000Z"
        DESCRIPTION
                "Updated with new header"
      ::= { alDnsMibModule 2 }

-- +++++++++++++++++++++++++++++++++++++++++++++++++++++++
-- MIB Objects
-- +++++++++++++++++++++++++++++++++++++++++++++++++++++++

alStatsDnsResolverGlobal	OBJECT IDENTIFIER ::= { alStatsDns 1 }

alDnsStatsAttemptedQueries	OBJECT-TYPE
	SYNTAX			Gauge32
	MAX-ACCESS		read-only
	STATUS			current
	DESCRIPTION
      "The number of DNS queries that were attempted."
	::= { alStatsDnsResolverGlobal 1 }

alDnsStatsSuccessfulResponses	OBJECT-TYPE
	SYNTAX			Gauge32
	MAX-ACCESS		read-only
	STATUS			current
	DESCRIPTION
      "The number of queries that were successfully resolved."
	::= { alStatsDnsResolverGlobal 2 }

alDnsStatsTimeoutFailures	OBJECT-TYPE
	SYNTAX			Gauge32
	MAX-ACCESS		read-only
	STATUS			current
	DESCRIPTION
      "The number of failures because there was no response from 
       the server."
	::= { alStatsDnsResolverGlobal 3 }

alDnsStatsUnreachableServerFailures	OBJECT-TYPE
	SYNTAX			Gauge32
	MAX-ACCESS		read-only
	STATUS			current
	DESCRIPTION
      "The number of failures because the address of the server
       is not reachable according to the Concentrator's routing 
       table."
	::= { alStatsDnsResolverGlobal 4 }

alDnsStatsMiscFailures		OBJECT-TYPE
	SYNTAX			Gauge32
	MAX-ACCESS		read-only
	STATUS			current
	DESCRIPTION
	       "The number of failures for an unspecified reason."
	::= { alStatsDnsResolverGlobal 5 }

altigaDnsStatsMibConformance OBJECT IDENTIFIER ::= { altigaDnsStatsMibModule 1 }
altigaDnsStatsMibCompliances OBJECT IDENTIFIER ::= { altigaDnsStatsMibConformance 1 }

altigaDnsStatsMibCompliance MODULE-COMPLIANCE
   STATUS         current
   DESCRIPTION
      "The compliance statement for agents which 
       implement the Altiga DNS Statistics MIB."
   MODULE
   MANDATORY-GROUPS { 
      altigaDnsStatsGroup
   }
   ::= { altigaDnsStatsMibCompliances 1 }

altigaDnsStatsGroup OBJECT-GROUP
	OBJECTS
	{
		alDnsStatsAttemptedQueries,
		alDnsStatsSuccessfulResponses,
		alDnsStatsTimeoutFailures,
		alDnsStatsUnreachableServerFailures,
		alDnsStatsMiscFailures
	}
	STATUS 	current
	DESCRIPTION
      "The objects for the DNS resolver module statistics."
	::= { alDnsGroup 2 }

END
