CISCO-GPRS-CHARGING-CAPABILITY DEFINITIONS ::= BEGIN

IMPORTS
        MODULE-IDENTITY
                FROM SNMPv2-SMI
        AGENT-CAPABILITIES
                FROM SNMPv2-CONF
        ciscoAgentCapability
                FROM CISCO-SMI;

ciscoGprschargingCapability MODULE-IDENTITY
        LAST-UPDATED    "200402032230Z"
        ORGANIZATION    "Cisco Systems, Inc."
        CONTACT-INFO
                "       Cisco Systems
                        Customer Service

                        Postal: 170 West Tasman Drive
                                San Jose, CA  95134
                                USA
                                Tel: +1 800 553-NETS

                        E-mail: cs-gprs@cisco.com"
        DESCRIPTION
                "Agent capabilities for CISCO-GPRS-CHARGING-MIB"
        REVISION        "200402032230Z"
        DESCRIPTION
                "Added variations for cgprsCgAlarmHistType to
                cGprschargingCapabilityV12R2M8YW and also added
                a variations for new version
                cGprschargingCapabilityV12R3M2XB1"
        REVISION        "200304081730Z"
        DESCRIPTION
                "Initial version of this MIB module."
        ::= { ciscoAgentCapability 297 }

cGprschargingCapabilityV12R2M8YD AGENT-CAPABILITIES
    PRODUCT-RELEASE  "Cisco IOS 12.2(4)MX & 12.2(8)YD"
    STATUS           current
    DESCRIPTION      "Cisco GPRS CHARGING MIB capabilities."
    SUPPORTS         CISCO-GPRS-CHARGING-MIB
    INCLUDES         { cgprsCgMIBConfigGroupRev2 }

    VARIATION        cgprsCgTariffTimeRowStatus
    SYNTAX           INTEGER { active(1), 
                               createAndGo(4),
                               destroy(6) 
                             }
    DESCRIPTION      "Creation of new entries using createAndWait(5) and
                     suspension of entries using notInService(2) is not
                     supported. Modification of existing row is not
                     supported."

    VARIATION        cgprsCgGatewayRowStatus
    SYNTAX           INTEGER { active(1), 
                               createAndGo(4),
                               destroy(6) 
                             }
    DESCRIPTION      "Creation of new entries using createAndWait(5) and
                     suspension of entries using notInService(2) is not
                     supported."
    ::= { ciscoGprschargingCapability 1 }

cGprschargingCapabilityV12R2M8YY1 AGENT-CAPABILITIES
    PRODUCT-RELEASE  "Cisco IOS 12.2(8)YY1"
    STATUS           current
    DESCRIPTION      "Cisco GPRS CHARGING MIB capabilities."
    SUPPORTS         CISCO-GPRS-CHARGING-MIB
    INCLUDES         { cgprsCgMIBConfigGroupRev2 }

    VARIATION        cgprsCgTariffTimeRowStatus
    SYNTAX           INTEGER { active(1), 
                               createAndGo(4),
                               destroy(6) 
                             }
    DESCRIPTION      "Creation of new entries using createAndWait(5) and
                     suspension of entries using notInService(2) is not
                     supported. Modification of existing row is not
                     supported."

    VARIATION        cgprsCgGatewayRowStatus
    SYNTAX           INTEGER { active(1), 
                               createAndGo(4),
                               destroy(6) 
                             }
    DESCRIPTION      "Creation of new entries using createAndWait(5) and
                     suspension of entries using notInService(2) is not
                     supported."
    ::= { ciscoGprschargingCapability 2 }

cGprschargingCapabilityV12R2M8YW AGENT-CAPABILITIES
    PRODUCT-RELEASE  "Cisco IOS 12.2(8)YW"
    STATUS           current
    DESCRIPTION      "Cisco GPRS CHARGING MIB capabilities."
    SUPPORTS         CISCO-GPRS-CHARGING-MIB
    INCLUDES         { cgprsCgMIBConfigGroupRev2,
                       cgprsCgMIBNotifGroup }

    VARIATION        cgprsCgTariffTimeRowStatus
    SYNTAX           INTEGER { active(1), 
                               createAndGo(4),
                               destroy(6) 
                             }
    DESCRIPTION      "Creation of new entries using createAndWait(5) and
                     suspension of entries using notInService(2) is not
                     supported. Modification of existing row is not
                     supported."

    VARIATION        cgprsCgGatewayRowStatus
    SYNTAX           INTEGER { active(1), 
                               createAndGo(4),
                               destroy(6) 
                             }
    DESCRIPTION      "Creation of new entries using createAndWait(5) and
                     suspension of entries using notInService(2) is not
                     supported."

    VARIATION        cgprsCgAlarmHistType
    SYNTAX           INTEGER {
                          cgprsCgAlarmCgDown(1),
                          cgprsCgAlarmCgUp(2),
                          cgprsCgAlarmTransFailure(3),
                          cgprsCgAlarmTransSuccess(4),
                          cgprsCgAlarmCapacityFree(6),
                          cgprsCgAlarmEchoFailure(7),
                          cgprsCgAlarmEchoRestored(8),
                          cgprsCgAlarmCdrBuffered(10),
                          cgprsCgAlarmChargingDisabled(11),
                          cgprsCgAlarmChargingEnabled(12)
                     }
    DESCRIPTION      "Notification of type cgprsCgAlarmCapacityFull(5) 
                     and cgprsCgAlarmCdrDiscard(9) are not supported."
    ::= { ciscoGprschargingCapability 3 }

cGprschargingCapabilityV12R3M2XB1 AGENT-CAPABILITIES
    PRODUCT-RELEASE  "Cisco IOS 12.3(2)XB1"
    STATUS           current
    DESCRIPTION      "Cisco GPRS CHARGING MIB capabilities."
    SUPPORTS         CISCO-GPRS-CHARGING-MIB
    INCLUDES         { cgprsCgMIBConfigGroupRev2,
                       cgprsCgMIBNotifGroup }

    VARIATION        cgprsCgTariffTimeRowStatus
    SYNTAX           INTEGER { active(1), 
                               createAndGo(4),
                               destroy(6) 
                             }
    DESCRIPTION      "Creation of new entries using createAndWait(5) and
                     suspension of entries using notInService(2) is not
                     supported. Modification of existing row is not
                     supported."

    VARIATION        cgprsCgGatewayRowStatus
    SYNTAX           INTEGER { active(1), 
                               createAndGo(4),
                               destroy(6) 
                             }
    DESCRIPTION      "Creation of new entries using createAndWait(5) and
                     suspension of entries using notInService(2) is not
                     supported."

    VARIATION        cgprsCgAlarmHistType
    SYNTAX           INTEGER {
                          cgprsCgAlarmCgDown(1),
                          cgprsCgAlarmCgUp(2),
                          cgprsCgAlarmTransFailure(3),
                          cgprsCgAlarmTransSuccess(4),
                          cgprsCgAlarmCapacityFree(6),
                          cgprsCgAlarmEchoFailure(7),
                          cgprsCgAlarmEchoRestored(8),
                          cgprsCgAlarmCdrBuffered(10),
                          cgprsCgAlarmChargingDisabled(11),
                          cgprsCgAlarmChargingEnabled(12)
                     }
    DESCRIPTION      "Notification of type cgprsCgAlarmCapacityFull(5)
                     and cgprsCgAlarmCdrDiscard(9) are not supported."
    ::= { ciscoGprschargingCapability 4 }
END
