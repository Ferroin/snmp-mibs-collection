CISCO-SONET-EXT-CAPABILITY DEFINITIONS ::= BEGIN

IMPORTS
 MODULE-IDENTITY,
 Unsigned32 
        FROM SNMPv2-SMI
 AGENT-CAPABILITIES
        FROM SNMPv2-CONF
 ciscoAgentCapability
        FROM CISCO-SMI;

ciscoSonetExtCapability MODULE-IDENTITY
    LAST-UPDATED "200312230000Z"
    ORGANIZATION "Cisco Systems, Inc."
    CONTACT-INFO
        "    Cisco Systems
             Customer Service

        Postal: 170 W Tasman Drive
             San Jose, CA  95134
             USA

             Tel: +1 800 553-NETS

        E-mail: cs-snmp@cisco.com"
 DESCRIPTION
     "The Agent Capabilities for CISCO-SONET-MIB.

      - ciscoSonetExtAxsmCapabilityV2R00 is for 
        ATM Switch Service Module(AXSM).

      - ciscoSonetExtAxsmCapabilityV2R11 is for 
        ATM Switch Service Module(AXSM).

      - ciscoSonetExtAxsmeCapabilityV21R60 is for
        Enhanced ATM Switch Service Module(AXSM-E).

      - ciscoSonetExtCapabilityV5R000 is for
        Service Resource Module(SRM-E).

      - ciscoSonetExtSrmeCapabilityV3R00 is for
        Voice Switch Service Module(VXSM)

      - ciscoSonetExtSrmeCapabilityV3R00 is for
        Service Resource Module(SRM-E).

      - ciscoSonetExtCapabilityV4R00 is for
        10 Gig. ATM Switch Service Module(AXSM-XG) and
        Enhanced ATM Switch Service Module(AXSM-E).

      - ciscoSonetExtCapabilityV5R000 is for
        Voice Switch Service Module(VXSM) and MPSM."

 REVISION "200312230000Z"
 DESCRIPTION
     "Added ciscoSonetExtCapabilityV5R00."

 REVISION "200303130000Z"
 DESCRIPTION
     "Added ciscoSonetExtCapabilityV4R00 for modules:
      ATM Switch Service Module(AXSM),
      10 Gig. ATM Switch Service Module(AXSM-XG),
      Enhanced ATM Switch Service Module(AXSM-E) and
      Processor Switch Module Enhanced (PXM1E)."

 REVISION "200202170000Z"
 DESCRIPTION
     "Initial Version of the MIB module."
 ::= { ciscoAgentCapability 261 }

ciscoSonetExtAxsmCapabilityV2R00 AGENT-CAPABILITIES
    PRODUCT-RELEASE  "MGX8850 Release 2.0.00"
    STATUS           current
    DESCRIPTION      "CISCO-SONET-MIB Capabilities for
                     ATM Switch Service Module(AXSM)."

    SUPPORTS CISCO-SONET-MIB
    INCLUDES { ciscoSonetConfMIBGroup, ciscoSonetStatsMIBGroup,
               ciscoSonetTraceMIBGroup, ciscoSonetApsMIBGroup
             }

     VARIATION   csApsWaitToRestore 
     SYNTAX      Unsigned32(5..12)
     DESCRIPTION "WTR time interval is 5-12 minutes."

     VARIATION   csApsArchMode 
     SYNTAX  INTEGER {
                 onePlusOne(1),
                 oneToOne(2)
             } 
     DESCRIPTION "Does not support values anexBOnePlusOne(3),
                  ycableOnePlusOneNok1k2(4),
                  straightOnePlusOneNok1k2(5)."

     VARIATION   cssTraceReceived   
     ACCESS      not-implemented      
     DESCRIPTION "Not supported."

     VARIATION   cspTraceReceived   
     ACCESS      not-implemented 
     DESCRIPTION "Not supported."
    ::= { ciscoSonetExtCapability 1 }

ciscoSonetExtAxsmCapabilityV2R11 AGENT-CAPABILITIES
    PRODUCT-RELEASE  "MGX8850 Release 2.0.11"
    STATUS     current
    DESCRIPTION   "CISCO-SONET-MIB Capabilities for
                  ATM Switch Service Module(AXSM)."

    SUPPORTS CISCO-SONET-MIB
    INCLUDES { ciscoSonetConfMIBGroup, ciscoSonetStatsMIBGroup,
               ciscoSonetTraceMIBGroup, ciscoSonetApsMIBGroup
             }

     VARIATION   csConfigFrameScramble
     SYNTAX      INTEGER { enabled(2) }
     DESCRIPTION  "Does not support disabled(1)."

     VARIATION   csApsWaitToRestore 
     SYNTAX      Unsigned32(5..12)
     DESCRIPTION "WTR time interval is 5-12 minutes."

     VARIATION   csApsArchMode 
     SYNTAX  INTEGER {
                 onePlusOne(1),
                 oneToOne(2)
             } 
     DESCRIPTION "Does not support values anexBOnePlusOne(3),
                  ycableOnePlusOneNok1k2(4),
                  straightOnePlusOneNok1k2(5)."

     VARIATION   cssTraceReceived   
     ACCESS      not-implemented      
     DESCRIPTION "Not supported."

     VARIATION   cspTraceReceived   
     ACCESS      not-implemented 
     DESCRIPTION "Not supported."
    ::= { ciscoSonetExtCapability 2 }

ciscoSonetExtAxsmeCapabilityV21R60 AGENT-CAPABILITIES
    PRODUCT-RELEASE  "MGX8850 Release 2.1.60."
    STATUS     current
    DESCRIPTION   "CISCO-SONET-MIB Capabilities for
                  AXSM-E Service Modules."

    SUPPORTS CISCO-SONET-MIB
    INCLUDES { ciscoSonetConfMIBGroup, ciscoSonetStatsMIBGroup,
               ciscoSonetTraceMIBGroup, ciscoSonetApsMIBGroup
             }

     VARIATION   csConfigFrameScramble
     SYNTAX      INTEGER {
                     enabled(2) 
                 }
     DESCRIPTION  "Does not support disabled(1)."

     VARIATION   csApsArchMode 
     SYNTAX  INTEGER {
                 onePlusOne(1),
                 oneToOne(2),
                 anexBOnePlusOne(3),
                 straightOnePlusOneNok1k2(5)
             } 
     DESCRIPTION "Does not support value
                  ycableOnePlusOneNok1k2(4)"

     VARIATION    csApsDirection
     DESCRIPTION  "The value uniDirectional(1) is ignored
                   for the following case:
                   csApsArchMode        = annexBOnePlusOne(3) and
                   csApsChannelProtocol = itu(2)"

     VARIATION    csApsRevertive
     DESCRIPTION  "The value revertive(2) is ignored
                   for the following case:
                   csApsArchMode        = annexBOnePlusOne(3) and
                   csApsChannelProtocol = itu(2)"

     VARIATION   cssTraceReceived   
     ACCESS      not-implemented      
     DESCRIPTION "Not supported."

     VARIATION   cspTraceReceived   
     ACCESS      not-implemented 
     DESCRIPTION "Not supported."
    ::= { ciscoSonetExtCapability 3 }

ciscoSonetExtSrmeCapabilityV3R00 AGENT-CAPABILITIES
    PRODUCT-RELEASE  "MGX8800 Release 3.0"
    STATUS     current
    DESCRIPTION   "CISCO-SONET-MIB Capabilities of 
                  Enhanced Service Resource Module(SRM-E)."

    SUPPORTS CISCO-SONET-MIB
    INCLUDES { ciscoSonetConfMIBGroup1, ciscoSonetStatsMIBGroup,
               ciscoSonetApsMIBGroup1, ciscoSonetVTConfMIBGroup
             }

     VARIATION   csConfigType
     SYNTAX      INTEGER {
                         sonetStm1(2),
                         sonetSts3(9)
                         }
     DESCRIPTION "Only sonetStm1(2), sonetSts3(9) are supported"

     VARIATION   csApsArchMode 
     SYNTAX  INTEGER {
                 onePlusOne(1),
                 anexBOnePlusOne(3)
             } 
     DESCRIPTION "Only onePlusOne(1) and anexBOnePlusOne(3)
                  are supported."

     VARIATION cslFarEndTotalESs 
     ACCESS      not-implemented 
     DESCRIPTION "Not supported."

     VARIATION cslFarEndTotalSESs
     ACCESS      not-implemented 
     DESCRIPTION "Not supported."

     VARIATION cslFarEndTotalCVs
     ACCESS      not-implemented 
     DESCRIPTION "Not supported."

     VARIATION cslFarEndTotalUASs
     ACCESS      not-implemented 
     DESCRIPTION "Not supported."

     VARIATION cspFarEndTotalESs
     ACCESS      not-implemented 
     DESCRIPTION "Not supported."

     VARIATION cspFarEndTotalSESs
     ACCESS      not-implemented 
     DESCRIPTION "Not supported."

     VARIATION cspFarEndTotalCVs
     ACCESS      not-implemented 
     DESCRIPTION "Not supported."

     VARIATION cspFarEndTotalUASs
     ACCESS      not-implemented 
     DESCRIPTION "Not supported."
    ::= { ciscoSonetExtCapability 4 }

ciscoSonetExtCapabilityV4R00 AGENT-CAPABILITIES
    PRODUCT-RELEASE  "MGX8850, MGX8950 Release 4.0.00."
    STATUS           current
    DESCRIPTION      "CISCO-SONET-MIB Capabilities for
                     AXSM, AXSM-E, AXSM-XG and PXM1E 
                     Modules."

    SUPPORTS CISCO-SONET-MIB
    INCLUDES { ciscoSonetConfMIBGroup1, ciscoSonetStatsMIBGroup,
               ciscoSonetTraceMIBGroup, ciscoSonetApsMIBGroup1,
               ciscoSonetPathConfMIBGroup
             }

--
-- Variations applicable for AXSM.
--
     VARIATION   csConfigFrameScramble
     ACCESS      read-only
     DESCRIPTION "Write access not supported. 
                 Read always returns 'enabled(1)'."

     VARIATION   cspSonetPathPayload   
     ACCESS      not-implemented 
     DESCRIPTION "Not supported."

--
-- Variations applicable for AXSM-XG.
--
     VARIATION   cspSonetPathPayload 
     SYNTAX      INTEGER {
                     unequipped(1),
                     ds3(3),
                     atmCell(6)
                 } 
     DESCRIPTION "Following values not supported:
                 unspecified(2),
                 vt15vc11(4),
                 vt2vc12(5),
                 hdlcFr(7)"

--
-- Variations applicable for AXSM-E, PXM1E.
--
     VARIATION   cspSonetPathPayload
     SYNTAX      INTEGER {
                     unequipped(1),
                     atmCell(6)
                 } 
     ACCESS      read-only
     DESCRIPTION "Following values not supported:
                 unspecified(2),
                 ds3(3), 
                 vt15vc11(4),
                 vt2vc12(5),
                 hdlcFr(7)"

--
-- Variations applicable for AXSM-E, AXSM-XG, PXM1E.
--
     VARIATION   csConfigFrameScramble
     SYNTAX      INTEGER {
                     enabled(2) 
                 }
     DESCRIPTION "Does not support disabled(1)."

     VARIATION   csApsDirection
     DESCRIPTION "The value uniDirectional(1) is ignored
                 for the following case:
                 csApsArchMode        = annexBOnePlusOne(3) and
                 csApsChannelProtocol = itu(2)"

     VARIATION   csApsRevertive
     DESCRIPTION "The value revertive(2) is ignored
                 for the following case:
                 csApsArchMode        = annexBOnePlusOne(3) and
                 csApsChannelProtocol = itu(2)"

--
-- Variations applicable for AXSM, AXSM-E, AXSM-XG, PXM1E.
--
     VARIATION   csApsArchMode 
     SYNTAX      INTEGER {
                     onePlusOne(1),
                     oneToOne(2),
                     anexBOnePlusOne(3),
                     straightOnePlusOneNok1k2(5)
                 } 
     DESCRIPTION "Does not support value
                 ycableOnePlusOneNok1k2(4)"

     VARIATION   cssTraceReceived   
     ACCESS      not-implemented      
     DESCRIPTION "Not supported."

     VARIATION   cspTraceReceived   
     ACCESS      not-implemented 
     DESCRIPTION "Not supported."

     VARIATION   csConfigRDIPType   
     ACCESS      not-implemented 
     DESCRIPTION "Not supported."

     VARIATION   csConfigRDIVType   
     ACCESS      not-implemented 
     DESCRIPTION "Not supported."
    ::= { ciscoSonetExtCapability 5 }

ciscoSonetExtCapabilityV5R00 AGENT-CAPABILITIES
    PRODUCT-RELEASE  "MGX8850 Release 5.0.0"
    STATUS           current
    DESCRIPTION      "Cisco Sonet Ext MIB capabilities for Voice 
                      Switch Service Module(VXSM) and 
                      MPSM in release 5.0.0."

    SUPPORTS    CISCO-SONET-MIB
    INCLUDES    { ciscoSonetConfMIBGroup1, 
                  ciscoSonetApsMIBGroup1,
                  ciscoSonetStatsMIBGroup, 
                  ciscoSonetTraceMIBGroup,
                  ciscoSonetPathConfMIBGroup,
                  ciscoSonetPathConfMIBGroup1
                }
--
-- VXSM VARIATION
--
    VARIATION   cslFarEndTotalESs
    ACCESS      not-implemented
    DESCRIPTION "Not supported."

--
-- VXSM VARIATION
--
    VARIATION   cslFarEndTotalSESs
    ACCESS      not-implemented
    DESCRIPTION "Not supported."

--
-- VXSM VARIATION
--
    VARIATION   cslFarEndTotalCVs
    ACCESS      not-implemented
    DESCRIPTION "Not supported."

--
-- VXSM VARIATION
--
    VARIATION   cslFarEndTotalUASs
    ACCESS      not-implemented
    DESCRIPTION "Not supported."

--
-- VXSM VARIATION
--
    VARIATION   cspFarEndTotalESs
    ACCESS      not-implemented
    DESCRIPTION "Not supported."

--
-- VXSM VARIATION
--
    VARIATION   cspFarEndTotalSESs
    ACCESS      not-implemented
    DESCRIPTION "Not supported."

--
-- VXSM VARIATION
--
    VARIATION   cspFarEndTotalCVs
    ACCESS      not-implemented
    DESCRIPTION "Not supported."

--
-- VXSM VARIATION
--
    VARIATION   cspFarEndTotalUASs
    ACCESS      not-implemented
    DESCRIPTION "Not supported."

    VARIATION   csConfigType
    SYNTAX      INTEGER {
                          sonetStm1(2),
                          sonetSts3(9)
                        }
    DESCRIPTION "sonetSts3c(1),
                 sonetSts12c(3),
                 sonetStm4(4),
                 sonetSts48c(5),
                 sonetStm16(6),
                 sonetSts192c(7),
                 sonetStm64(8) are not supported."

--
-- VXSM VARIATION
--
    VARIATION   csApsArchMode
    SYNTAX      INTEGER {
                   onePlusOne     (1), 
                   oneToOne       (2),
                   anexBOnePlusOne(3)
                }
    DESCRIPTION "ycableOnePlusOneNok1k2(4),
                 straightOnePlusOneNok1k2(5) are not supported."
--
-- MPSM VARIATION
--
    VARIATION   csApsArchMode
    SYNTAX      INTEGER {
                   onePlusOne     (1), 
                   oneToOne       (2),
                   anexBOnePlusOne(3),
                   straightOnePlusOneNok1k2(5)
                }
    DESCRIPTION "ycableOnePlusOneNok1k2(4) is not supported."

--
-- MPSM VARIATION
--
    VARIATION    csApsDirection
    DESCRIPTION  "The value uniDirectional(1) is ignored
                   for the following case:
                   csApsArchMode        = annexBOnePlusOne(3) and
                   csApsChannelProtocol = itu(2)"

--
-- MPSM VARIATION
--
    VARIATION    csApsRevertive
    DESCRIPTION  "The value revertive(2) is ignored
                   for the following case:
                   csApsArchMode        = annexBOnePlusOne(3) and
                   csApsChannelProtocol = itu(2)"

--
-- VXSM VARIATION
--
    VARIATION   cspSonetPathPayload
    SYNTAX      INTEGER {
                   ds3     (3), 
                   vt15vc11(4),
                   vt2vc12 (5)
                }
    DEFVAL      { vt15vc11 }
    DESCRIPTION "unequipped(1),
                 unspecified(2),
                 atmCell(6),
                 hdlcFr(7),
                 e3(8),
                 vtStructured(9) are not supported.
                 The ds3(3) is not valid for SDH."

--
-- VXSM VARIATION
--
    VARIATION   cspTributaryMappingType
    DESCRIPTION "The byteSynchronous(2) is not valid for DS3."

--
-- VXSM VARIATION
--
    VARIATION   cspTributaryGroupingType
    DESCRIPTION "The notApplicable(1) is only valid for Sonet.
                 The au3Grouping(2) and au4Grouping(3) are 
                 only valid for SDH."
    ::= { ciscoSonetExtCapability 6 }

END
